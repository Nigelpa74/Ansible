/*
Copyright (C) 2025 Huawei Technologies Co., Ltd. All rights reserved.
*/
module huawei-bfd-fwm-deviations-ar5710s {
  yang-version 1;
  namespace "urn:huawei:yang:huawei-bfd-fwm-deviations-ar5710s";
  prefix bfd-fwm-devs-ar5710s;

  import huawei-bfd-fwm {
    prefix bfd-fwm;
  }
  import huawei-bfd {
    prefix bfd;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd-fwm module.";

  revision 2025-02-24 {
    description
      "Initial revision.";
    reference "Huawei private.";
  }

  deviation "/bfd:bfd/bfd-fwm:forwarding-match" {
    deviate not-supported;
  }
}
