/*
Copyright (C) 2020-2024 Huawei Technologies Co., Ltd. All rights reserved.
module: huawei-dtls-server
   +--rw dtls-server!
      +--rw enable?         boolean
      +--rw listen
      |  +--rw port?             uint16
      |  +--rw ipv4-addresses
      |  |  +--rw ipv4-address* [vpn-instance ipv4-address]
      |  |     +--rw vpn-instance    -> /ni:network-instance/instances/instance/name
      |  |     +--rw ipv4-address    inet:ipv4-address-no-zone
      |  +--rw ipv6-addresses
      |     +--rw ipv6-address* [vpn-instance ipv6-address]
      |        +--rw vpn-instance    -> /ni:network-instance/instances/instance/name
      |        +--rw ipv6-address    inet:ipv6-address-no-zone
      +--rw cipher-suite*   cipher-suite-mode
      +--rw esn-authenticate         -> /da:dtls-authen/da:esn-lists/da:esn-list/da:name
      +--rw pki-realm?               -> /pki:pki/domains/domain/name
*/


module huawei-dtls-server {
  yang-version 1.1;

  namespace "urn:huawei:yang:huawei-dtls-server";
  prefix dtls-server;

  import ietf-inet-types {
    prefix inet;
  }

  import huawei-network-instance {
    prefix ni;
  }
  
  import huawei-extension {
    prefix ext;
  }
  
  import huawei-dtls-authen {
    prefix da;
  }

  import huawei-pki {
    prefix pki;
  }

  organization
    "Huawei Technologies Co., Ltd.";
     
  contact
    "Huawei Industrial Base
     Bantian, Longgang
     Shenzhen 518129
     People's Republic of China
     Website: http://www.huawei.com
     Email: support@huawei.com";

  description
    "This module contains a collection of YANG definitions for
     dtls server implementations.";

  revision 2024-12-05 {
    description "Remove cipher-suite's generated-by system tag.";
    reference "";
  }

  revision 2024-05-22 {
    description "Sync cipher-suite default values with yin file.";
    reference "";
  }

  revision 2024-02-18 {
    description "Correct cipher-suite names.";
    reference "";
  }
  revision 2022-12-23 {
    description "Modify task name.";
    reference "";
  }
  revision 2022-10-18 {
    description "Add cipher-suite system record.";
    reference "";
  }

  revision 2022-07-22 {
    description "Add pki realm.";
    reference "";
  }

  revision 2022-01-10 {
    description "Add dtls esn authenticate.";
    reference "";
  }

  revision 2020-05-11 {
    description "Initial revision.";
    reference "";
  }
  ext:task-name  "sdwan";    

  /*****************************************************************
  * Features
  *****************************************************************/
  
  /*****************************************************************
  * Identities
  *****************************************************************/

  /*****************************************************************
  * Type definitions
  *****************************************************************/
  
  typedef cipher-suite-mode {
    type enumeration {
      enum "rsa-with-aes-128-sha" {
        value 0;
        description
          "RSA-WITH-AES-128-SHA cipher suite.";
      }
      enum "ecdhe-rsa-with-aes-128-gcm-sha256" {
        value 1;
        description
          "ECDHE-RSA-WITH-AES-128-GCM-SHA256 cipher suite.";
      }
      enum "ecdhe-rsa-with-aes-256-gcm-sha384" {
        value 2;
        description
          "ECDHE-RSA-WITH-AES-256-GCM-SHA384 cipher suite.";
      }
    }
    description
      "Ciphersuite mode.";
  }
  
  /*****************************************************************
  * Groupings
  *****************************************************************/

  /*****************************************************************
  * Main container
  *****************************************************************/

  container dtls-server {
    presence "create dtls-server";
    description "Dtls parameters.";

    leaf enable {
      type boolean;
      default "false";
      description "Enable/disable dtls server.";
    }
      
    container listen {
      description "Configure of dtls server.";
        
      leaf port {
        type uint16 {
            range "10000..65535";
        }
        description "The listening port of dtls server.";
      }

      container ipv4-addresses {
        description
          "List of listening address.";
        list ipv4-address {
          key "vpn-instance ipv4-address" ; 

          description "Configure a listening address.";
      
          leaf vpn-instance {
            type leafref {
              path "/ni:network-instance/ni:instances/ni:instance/ni:name";
            }
            description "The vpn instance name.";
          }
      
          leaf ipv4-address {
            type inet:ipv4-address-no-zone;
            description "The listening ip-address.";
          }
        }
      }
      container ipv6-addresses {
        description
          "List of listening IPv6 address.";
        list ipv6-address {
          key "vpn-instance ipv6-address" ; 
          description 
            "Configure a IPv6 listening address.";
          leaf vpn-instance {
            type leafref {
              path "/ni:network-instance/ni:instances/ni:instance/ni:name";
            }
            description 
              "Specify the name of a VPN instance.";
          }
          leaf ipv6-address {
            type inet:ipv6-address-no-zone;
            description 
              "Specify the IPv6 address of the dtls server.";
          }
        }
      }
    }
    leaf-list cipher-suite {
      type cipher-suite-mode;
      default "ecdhe-rsa-with-aes-128-gcm-sha256";
      default "ecdhe-rsa-with-aes-256-gcm-sha384";
      description
        "Configure the cipher suite of the DTLS server.";
    }
    leaf esn-authenticate {
      type leafref{
        path "/da:dtls-authen/da:esn-lists/da:esn-list/da:name";
      }
      description
        "Configure ESN authenticate of DTLS server.";
    }
    leaf pki-realm {
      type leafref{
        path "/pki:pki/pki:domains/pki:domain/pki:name";
      }
      description "Configure PKI realm of DTLS server.";
    }
  }
}
