/*
Copyright (C) 2025 Huawei Technologies Co., Ltd. All rights reserved.
*/
module huawei-crypto-deviations-ar5710s {
  namespace "urn:huawei:yang:huawei-crypto-deviations-ar5710s";
  prefix crypto-devs-ar5710s;

  import huawei-crypto {
    prefix crypto;
  }

  organization
    "Huawei Technologies Co., Ltd.";
  contact
    "Huawei Industrial Base
     Bantian, Longgang
     Shenzhen 518129
     People's Republic of China
     Website: http://www.huawei.com
     Email: support@huawei.com";
  description
    "This module defines deviation statements for huawei-crypto module.";

  revision 2025-02-24 {
    description
      "Initial revision.";
    reference "Huawei private.";
  }

  deviation "/crypto:crypto/crypto:drbg" {
    deviate not-supported;
  }
  deviation "/crypto:crypto/crypto:encryption-algorithm" {
    deviate not-supported;
  }
  deviation "/crypto:crypto/crypto:crypto-mode" {
    deviate not-supported;
  }
  deviation "/crypto:crypto/crypto:weak-algorithm" {
    deviate not-supported;
  }
}
