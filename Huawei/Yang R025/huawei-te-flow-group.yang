/*
Copyright (C) 2021-2025 Huawei Technologies Co., Ltd. All rights reserved.
*/
module huawei-te-flow-group {
  namespace "urn:huawei:yang:huawei-te-flow-group";
  prefix teflowgroup;
  import huawei-extension {
    prefix ext;
  }
  import huawei-network-instance {
    prefix ni;
  }
  import huawei-srv6 {
    prefix srv6;
  }
  import huawei-apn {
    prefix apn;
  }
  import ietf-inet-types {
    prefix inet;
  }
  import ietf-yang-types {
    prefix yang;
  }
  import huawei-routing-policy {
    prefix rtp;
  }
  import huawei-isis {
    prefix isis;
  }
  include huawei-te-flow-group-type;

  organization
    "Huawei Technologies Co., Ltd.";
  contact
    "Huawei Industrial Base
     Bantian, Longgang
     Shenzhen 518129
     People's Republic of China
     Website: http://www.huawei.com
     Email: support@huawei.com";
  description
    "Flow groups.";
  revision 2025-05-29 {
    description
      "Modified the description of the spr-path role node.";
    reference
      "Huawei private.";
  }
  revision 2025-02-18 {
    description
      "Deleted the pattern constraints of serveral name nodes.";
    reference
      "Huawei private.";
  }
  revision 2024-07-29 {
    description
      "Modified the SRv6 TE flow group query node.";
    reference
      "Huawei private.";
  }
  revision 2023-11-16 {
    description
      "Modify the function of display SRv6 TE flow group lastdown.";
    reference
      "Huawei private.";
  }
  revision 2023-11-06 {
    description
      "Add the dscp-maps must condition.";
    reference
      "Huawei private.";
  }
  revision 2023-10-18 {
    description
      "Add the function of SRv6 TE flow group binding SID and match type APN6.";
    reference
      "Huawei private.";
  }
  revision 2023-07-21 {
    description
      "Delete the dscp-maps must condition.";
    reference
      "Huawei private.";
  }
  revision 2023-03-15 {
    description
      "Add the function of static SRv6 TE flow group.";
    reference
      "Huawei private.";
  }
  revision 2022-09-06 {
    description
      "Add key up-time and up-millisecond for container flow-maps.";
    reference
      "Huawei private.";
  }
  revision 2022-06-24 {
    description
      "Modify the flow group name length from 1..31 to 0..31.";
    reference
      "Huawei private.";
  }
  revision 2022-03-23 {
    description
      "Add apn-id-IPv6-maps container.";
    reference
      "Huawei private.";
  }
  revision 2022-02-10 {
    description
      "Submodule huawei-te-flow-group-type add enum no-endpoint.";
    reference
      "Huawei private.";
  }
  revision 2021-12-14 {
    description
      "Add spr-groups container.";
    reference
      "Huawei private.";
  }
  revision 2021-05-20 {
    description
      "Init revision.";
    reference
      "Huawei private.";
  }
  ext:task-name  "teflowgroup";

  augment /ni:network-instance/ni:instances/ni:instance/srv6:srv6 {
    description "Augment for Segment Routing te flow group.";
    container teflowgroup {
      when "../srv6:enable='true'";
      description
        "Configure flow group parameters.";
        leaf group-threshold-upper {
          type uint32 {
            range "2..100";
          }
          must "(../group-threshold-upper>../group-threshold-lower)";
          default "80";
          description
            "Upper threshold for the number of SRv6 TE flow groups.";
        }
        leaf group-threshold-lower {
          type uint32 {
            range "1..99";
          }
          default "75";
          description
            "Lower threshold for the number of SRv6 TE flow groups.";
        }
        container spr {
          presence "Enter the smart policy routing view.";
          description
           "Configure smart policy routing.";
          leaf spr-refresh-period {
            type uint32 {
              range "2..60";
            }
            units s;
            default "60";
            description
              "SPR refresh period.";
          }
          leaf measure-count-mode {
            type count-mode;
            default "one-way";
            description
              "Measure count mode, one-way or two-way-average.";
          }
          container spr-policys {
            description
              "List of SPR policies.";
            list spr-policy {
              key "name";
              description
                "Configure an SPR policy."; 
              leaf name {
                type string {
                  length "1..31";
                }
                description
                  "SPR policy name.";
              }
              leaf switch-period {
                type uint32 {
                  range "1..7200";
                }
                units s;
                default "6";
                description
                  "Switching period.";
              }	
              leaf wait-to-restore-period {
                type uint32 {
                  range "1..259200";
                }
                units s;
                default "6";
                description
                  "Wait-to-restore period.";
              }
              leaf delay-threshold {
                type uint32 {
                  range "0..5000";
                }
                default "5000";
                description
                  "Delay threshold.";
              }
              leaf jitter-threshold {
                type uint32 {
                  range "0..3000";
                }
                default "3000";
                description
                  "Jitter threshold.";
              }
              leaf loss-rate-threshold {
                type uint32 {
                  range "0..1000";
                }
                default "1000";
                description
                  "Packet loss rate threshold.";
              }
              leaf cmi-threshold {
                type uint32 {
                  range "0..9000";
                }
                default "9000";
                description
                  "CMI threshold.";
              }
              container srv6-te-policys {
                description
                  "List of SPR paths.";
                list srv6-te-policy {
                  key "color";
                  max-elements "8";
                  description
                    "Configure an SRv6 TE Policy.";
                  leaf color {
                    type uint32 {
                      range "0..4294967295";
                    }
                    description
                      "Color of an SRv6 TE Policy.";
                  }
                  leaf priority {
                    type uint8 {
                      range "1..8";
                    }
                    mandatory true;
                    description
                      "SRv6 TE Policy priority.";
                  }
                }
              }
            }
          }
        }
        container mapping-policys {
          description
            "List of mapping policys.";
          list mapping-policy {
            key "color";
            unique "name";
            description
              "Configure a mapping policy.";
            leaf color {
              type uint32 {
                range "0..4294967295";
              }
              description
                "Color of a mapping policy.";
            }
            leaf name {
              type string {
                length "1..31";
              } 
              mandatory true;
              description
                "Mapping policy name.";
            }
            leaf description {
              type string {
                length "1..242";
              }
              description
                "Description of a mapping policy.";
            }
            leaf match-type {
              type match-type;
              must "(../match-type='service-class') or (../match-type='dscp') or (../match-type='te-class') or (../match-type='apn-id-ipv6')";
              description
                "Match type of a mapping policy.";
            }
            container dscp-maps {
              when "../match-type='dscp'";
              description
                "List of dscp maps.";
              list dscp-map {
                key "default index af-type";
                max-elements "130";
                description
                  "Configure a dscp map.";
                leaf default {
                  type boolean;
                  must "(../default='true' and ../index=4294967295) or (../default='false')";
                  description
                    "Enable/disable the default DSCP.";
                }
                leaf index {
                  type uint32 {
                    range "0..4294967295";
                  }
                  description
                    "Index.";
                }
                leaf af-type {
                  type address-family-set-type;
                  description
                    "Address family type.";
                }
                leaf dscp-value {
                  when "../default='false'";
                  type dscp-type;
                  mandatory true;
                  description
                    "DSCP list.";
                }
                choice match-tunnel {
                  mandatory true;
                  description
                    "Match tunnel.";
                  case sr-policy {
                    description
                      "Flow match sr-policy.";
                    leaf color {
                      type uint32 {
                        range "0..4294967295";
                      }
                      must "not(../../dscp-map[color=current()][af-type=current()/../af-type][index=current()/../index][default!=current()/../default] or ../../dscp-map[color=current()][af-type=current()/../af-type][default=current()/../default][index!=current()/../index])";
                      description
                        "Color of an SR Policy.";
                    }
                  }
                  case ip {
                    description
                      "Flow match native-ip.";
                    leaf native-ip {
                      type empty;
                      must "not(../../dscp-map[af-type=current()/../af-type][index=current()/../index][default!=current()/../default]/native-ip or ../../dscp-map[af-type=current()/../af-type][default=current()/../default][index!=current()/../index]/native-ip)";
                      description
                        "Native-ip configured.";
                    }
                  }
                }
              }
            }
            container service-class-maps {
              when "../match-type='service-class'";
              description
                "List of service class maps.";
              list service-class-map {
                key "index";
                description
                  "Configure a service-class map.";
                leaf index {
                  type uint32 {
                    range "1..4294967295";
                  }
                  description
                    "Index.";
                }
                leaf service-class {
                  when "../index != 4294967295";
                  type service-class-type;
                  mandatory true;
                  description
                    "Service-class type.";
                }
                choice match-tunnel {
                  mandatory true;
                  description
                    "Match tunnel.";
                  case sr-policy {
                    description
                      "Flow match sr-policy.";
                    leaf color {
                      type uint32 {
                        range "0..4294967295";
                      }
                      must "not(../../service-class-map[color=current()][index!=current()/../index])";
                      description
                        "Color of an SR Policy.";
                    }
                  }
                  case ip {
                    description
                      "Flow match native-ip.";
                    leaf native-ip {
                      type empty;
                      must "not(../../service-class-map[index!=current()/../index]/native-ip)";
                      description
                        "Native-ip configured.";
                    }
                  }
                }
              }
            }
            container te-class-maps {
              when "../match-type='te-class'";
              description
                "List of TE class mappings.";
              list te-class-map {
                key "index";
                unique "te-class-id";
                unique "match-tunnel/spr-policy/spr-policy-name";
                unique "match-tunnel/sr-policy/color";
                max-elements "1024";
                description
                  "Configure a TE class mapping.";
                leaf index {
                  type uint32 {
                    range "1..4294967295";
                  }
                  description
                    "Index.";
                }
                leaf te-class-id {
                  when "../index != 4294967295";
                  type uint32 {
                    range "1..65535";
                  }
                  mandatory true;
                  description
                    "TE class ID.";
                }
                choice match-tunnel {
                  mandatory true;
                  description
                    "Matching tunnel.";
                  case spr-policy {
                    description
                      "Matching SPR policy.";
                    leaf spr-policy-name {
                       type leafref {
                        path "../../../../../spr/spr-policys/spr-policy/name";
                      }
                      description
                        "SPR policy name.";
                    }
                  }
                  case sr-policy {
                    description
                      "Matching SR Policy.";
                    leaf color {
                      type uint32 {
                        range "0..4294967295";
                      }
                      description
                        "Color of an SR Policy.";
                    }
                  }
                  case ip {
                    description
                      "Matching native-IP link.";
                    leaf native-ip {
                      type empty;
                      must "not(../../te-class-map[index!=current()/../index]/native-ip)";
                      description
                        "Native-IP link.";
                    }
                  }
                }
              }
            }
            container apn-id-ipv6-maps {
              when "../match-type='apn-id-ipv6'";
              description
                "List of IPv6 APN ID mappings.";
              list apn-id-ipv6-map {
                key "index";
                unique "instance-name";
                unique "match-tunnel/sr-policy/color";
                max-elements "1024";
                description
                  "Configure an IPv6 APN ID mapping.";
                leaf index {
                  type uint32 {
                    range "1..4294967295";
                  }
                  description
                    "Index.";
                }
                leaf instance-name {
                  when "../index != 4294967295";
                  type leafref {
                    path "/apn:apn/apn:ipv6/apn:apn-id-instances/apn:apn-id-instance/apn:name";
                  }
                  mandatory true;
                  description
                    "Instance name.";
                }
                choice match-tunnel {
                  mandatory true;
                  description
                    "Matching tunnel.";
                  case sr-policy {
                    description
                      "Matching SR Policy.";
                      leaf color {
                        type uint32;
                        description
                          "Color of an SR Policy.";
                      }
                  }
                  case ip {
                    description
                      "Matching native-IP link.";
                    leaf native-ip {
                      type empty;
                      must "not(../../apn-id-ipv6-map[index!=current()/../index]/native-ip)";
                      description
                        "Matching native-IP link.";
                    }
                  }
                }
              }
            }
          }
        }
        container locators {
          description
            "List of locators.";
          list locator {
            key "name";
            max-elements "1";
            description
              "Configure a locator.";
            leaf name {
              type leafref {
                path "/ni:network-instance/ni:instances/ni:instance/srv6:srv6/srv6:locators/srv6:locator/srv6:name";
              }
              description
                "Locator name.";
            }
          }
        }
        container te-flow-groups {
          description
            "List of SRv6 TE Flow Groups.";
          list te-flow-group {
            key "name";
            description
              "Configure an SRv6 TE Flow Group.";
            leaf name {
              type string {
                length "1..31";
              }
              description
                "SRv6 TE Flow Group name.";
            }
            leaf endpoint {
              type inet:ipv6-address-no-zone;
              description
                "SRv6 TE Flow Group endpoint address.";
            }
            leaf match-type {
              type match-type;
              must "(../match-type='dscp')";
              description
                "Match type of an SRv6 TE Flow Group.";
            }
            leaf shortcut-type {
              type shortcut-mode;
              default "disable";
              description
                "SRv6 TE Flow Group shortcut type.";
            }
            leaf route-policy-name {
              when "(../shortcut-type='isis')";
              type leafref {
                path "/rtp:routing-policy/rtp:policy-definitions/rtp:policy-definition/rtp:name";
              }
              description
                "Route policy name.";
            }
            leaf process-id {
              when "(../shortcut-type='isis')";
              type leafref {
                path "/ni:network-instance/ni:instances/ni:instance/isis:isis/isis:sites/isis:site/isis:id";
              }
              must "/ni:network-instance/ni:instances/ni:instance/isis:isis/isis:sites/isis:site[isis:id=current()]/isis:afs/isis:af[isis:type='afipv6']";
              description
                "ISIS process id.";
            }
            leaf disable-auto-select-default {
              when "../match-type='apn-id-ipv6'";
              type match-type;
              must "(../disable-auto-select-default='apn-id-ipv6')";
              description
                "Disable automatic selection of the default tunnel in an SRv6 TE flow group.";
            }
            leaf strict-match-enable {
              when "../match-type='apn-id-ipv6'";
              type match-type;
              must "(../strict-match-enable='apn-id-ipv6')";
              description
                "Enable SRv6 TE flow group strict match.";
            }
            container dscp-maps {
              when "../match-type='dscp'";
              description
                "List of dscp maps.";
              list dscp-map {
                key "index";
                unique "match-tunnel/sr-policy/color";
                description
                  "Configure a DSCP mapping.";
                leaf index {
                  type uint32 {
                    range "1..4294967295";
                  }
                  description
                    "Index.";
                }
                leaf dscp-value {
                  when "../index != 4294967295";
                  type dscp-type;
                  mandatory true;
                  description
                    "DSCP list.";
                }
                choice match-tunnel {
                  mandatory true;
                  description
                    "Matching tunnel.";
                  case sr-policy {
                    description
                      "Matching SR Policy.";
                    leaf color {
                      type uint32;
                      description
                        "Color of an SR Policy.";
                    }
                  }
                  case ip {
                    description
                      "Matching native-IP link.";
                    leaf native-ip {
                      type empty;
                      must "not(../../dscp-map[index!=current()/../index]/native-ip)";
                      description
                        "Native-IP link.";
                    }
                  }
                }
              }
            }
            container binding-sids {
              description "List of binding SIDs for an SRv6 TE flow group.";
              list binding-sid {
                must "(../../../../locators/locator) and (../../match-type='apn-id-ipv6' or not(../../match-type)) and not(../../endpoint) and not(../../shortcut-type='isis')";
                key "dataplane value";
                max-elements "1";
                description
                  "Configure a binding SID.";
                leaf dataplane {
                  type dataplane-type;
                  must "(../dataplane='srv6')";
                  description
                    "Data-plane type of a binding SID.";
                }
                leaf value {
                  type sid-value-type;
                  description
                    "Binding SID value.";
                }
              }
            }
            container apn-id-ipv6-maps {
              when "(../match-type='apn-id-ipv6')";
              description
                "List of IPv6 APN ID mappings.";
              list apn-id-ipv6-map {
                key "index";
                unique "instance-name";
                max-elements "1024";
                description
                  "Configure an IPv6 APN ID mapping.";
                leaf index {
                  type uint32 {
                    range "1..4294967295";
                  }
                  description
                    "Index.";
                }
                leaf instance-name {
                  when "../index != 4294967295";
                  type leafref {
                    path "/apn:apn/apn:ipv6/apn:apn-id-instances/apn:apn-id-instance/apn:name";
                  }
                  mandatory true;
                  description
                    "Instance name.";
                }
                choice match-tunnel {
                  mandatory true;
                  description
                    "Matching tunnel.";
                  case sr-policy {
                    description
                      "Matching SR Policy.";
                    leaf endpoint {
                      type inet:ipv6-address;
                      mandatory true;
                      description
                        "Endpoint of an SR Policy.";
                    }
                    leaf color {
                      type uint32;
                      mandatory true;
                      description
                        "Color of an SR Policy.";
                    }
                  }
                }
              }
            }
          }
        }
        container running-flow-groups {
          config false;
          description
            "List of flow groups.";
          list running-flow-group {
            key "endpoint color name";
            description
              "Operational state of a flow group.";
            leaf endpoint {
              type inet:ipv6-address-no-zone;
              description
                "Endpoint of a flow group.";
            }
            leaf color {
              type uint32;
              description
                "Color of a flow group.";
            }
            leaf name {
              type string {
                length "0..31";
              }	
              description
                "Flow group name.";
            }
            leaf type {
              type group-create-type;
              description
                "Type of a flow group, static or dynamic.";
            }
            leaf tunnel-id {
              type uint32;
              description
                "Tunnel ID.";
            }
            leaf tunnel-type {
              type tunnel-type;
              description
                "Tunnel type.";
            }
            leaf state {
              type group-state-type;
              description
                "State of a flow group.";
            }
            leaf state-change-time {
              type yang:date-and-time;
              description
                "Date and time when the state of a flow group changed.";
            }
            leaf delay-timer-remain {
              type uint32;
              units ms;
              description
                "Remaining time of the delay timer.";
            }
            leaf map-count {
              type uint32;
              description
                "Number of mappings in a flow group.";
            }
            leaf up-map-count {
              type uint32;
              description
                "Number of mappings that are up in a flow group.";
            }
            leaf interface-name {
              type string {
                length "1..31";
              }
              description
                "Interface name.";
            }
            leaf interface-index {
              type uint32;
              description
                "Interface index.";
            }
            leaf interface-state {
              type string {
                length "1..31";
              }
              description
                "Interface state.";
            }
            leaf usd-capability {
              type boolean;
              description
                "USD capability.";
            }
            container binding-sids {
              description
                "List of SRv6 TE flow group's binding SIDs.";
              list binding-sid {
                key "sid-value";
                max-elements "1";
                description
                  "Operational data of an SRv6 TE flow group's binding SID.";
                leaf sid-value {
                  type sid-value-type;
                  description
                    "Binding SID value.";
                }
                leaf encapsulation-mode {
                  type encapsulation-disp-type;
                  description
                    "Binding SID encapsulation mode.";
                }
              }
            }
            container flow-maps {
              description
                "List of flow maps.";
              list flow-map {
                key "match-type default index af-type";
                description
                  "Operational state of a flow map.";
                leaf match-type {
                  type flow-match-type;
                  description
                    "Flow match type.";
                }
                leaf default {
                  type boolean;
                  description
                    "Default.";
                }
                leaf index {
                  type uint32;
                  description
                    "Index.";
                }
                leaf af-type {
                  type address-family-type;
                  description
                    "Address family type.";
                }
                leaf dscp-value {
                  type dscp-type;
                  description
                    "DSCP list.";
                }
                leaf service-class {
                  type string {
                    length "2..30";
                  }
                  description
                    "Service class list.";
                }
                leaf apn6-instance-name {
                  type string {
                    length "1..31";
                  }
                  description
                    "IPv6 APN ID instance name.";
                }
                leaf policy-color {
                  type uint32;
                  description
                    "Color of an SR Policy.";
                }
                leaf policy-endpoint {
                  type inet:ipv6-address;
                  description
                    "Endpoint of an SR Policy.";
                }
                leaf policy-tunnel-id {
                  type uint32;
                  description
                    "Policy tunnel ID.";
                }
                leaf native-ip {
                  type boolean;
                  description
                    "Native-ip.";
                }
                leaf state {
                  type tunnel-state-type;
                  description
                    "State of the match tunnel.";
                }
                leaf te-class-id {
                  type uint32;
                  description
                    "TE class ID.";
                }
                leaf spr-policy-name {
                  type string {
                    length "1..31";
                  }
                  description
                    "SPR policy name.";
                }
                container spr-groups {
                  description
                    "List of SPR groups.";
                  list spr-group {
                    key "group-id";
                    max-elements "2";
                    description
                      "Operational data of SPR group.";
                    leaf group-id {
                      type uint32;
                      description
                        "SPR group ID.";
                    }
                    leaf state {
                      type spr-group-state-type;
                      description
                        "SPR group state.";
                    }
                    leaf delay-timer-remain {
                      type uint32;
                      units ms;
                      description
                        "Delay timer remain.";
                    }
                    container spr-paths {
                      description
                        "List of SPR paths.";
                      list spr-path {
                        key "color";
                        max-elements "8";
                        description
                          "Operational data of SPR path.";
                        leaf color {
                          type uint32;
                          description
                            "Color of an SRv6 TE Policy.";
                        }
                        leaf priority {
                          type uint8;
                          description
                            "SRv6 TE Policy priority.";
                        }
                        leaf role {
                          type role;
                          description
                            "SRv6 TE Policy role.";
                        }
                      }
                    }
                  }
                }
              }
            }
          }
        }
        container flow-group-down-reasons {
          config false;
          description
            "List of down records of flow groups.";
          list flow-group-down-reason {
            key "endpoint color name up-time up-millisecond";
            description
              "Operational state of down record of a flow group.";
            leaf endpoint {
              type inet:ipv6-address-no-zone;
              description
                "Endpoint of a flow group.";
            }
            leaf color {
              type uint32;
              description
                "Color of a flow group.";
            }
            leaf name {
              type string {
                length "0..31";
              }	
              description
                "Flow group name.";
            }
            leaf up-time {
              type yang:date-and-time;
              description
                "Date and time when a flow group went up.";
            }
            leaf up-millisecond {
              type uint32;
              units ms;
              description
                "Millisecond value of the time when a flow group went up.";
            }
            leaf tunnel-id {
              type uint32;
              description
                "Tunnel ID.";
            }
            leaf tunnel-type {
              type tunnel-type;
              description
                "Tunnel type.";
            }
            leaf create-time {
              type yang:date-and-time;
              description
                "Date and time when a flow group was created.";
            }
            leaf down-time {
              type yang:date-and-time;
              description
                "Date and time when a flow group went down.";
            }
            leaf down-reason {
              type group-down-reason-type;
              description
                "Reason why a flow group went down.";
            }
            container binding-sids {
              description
                "List of SRv6 TE flow group's binding SIDs.";
              list binding-sid {
                key "sid-value";
                description
                  "Operational data of an SRv6 TE flow group's binding SID.";
                leaf sid-value {
                  type sid-value-type;
                  description
                    "Binding SID value.";
                }
              }
            }
            container flow-maps {
              description
                "List of down records of flow maps.";
              list flow-map {
                key "match-type default index af-type up-time up-millisecond";
                description
                  "Operational state of down record of a flow map.";
                leaf match-type {
                  type flow-match-type;
                  description
                    "Flow match type.";
                }
                leaf default {
                  type boolean;
                  description
                    "Default.";
                }
                leaf index {
                  type uint32;
                  description
                    "Index.";
                }
                leaf af-type {
                  type address-family-type;
                  description
                    "Address family type.";
                }
                leaf up-time {
                  type yang:date-and-time;
                  description
                    "Date and time when a flow map went up.";
                }
                leaf up-millisecond {
                  type uint32;
                  units ms;
                  description
                    "Millisecond value of the time when a flow map went up.";
                }
                leaf policy-color {
                  type uint32;
                  description
                    "Color of an SR Policy.";
                }
                leaf policy-endpoint {
                  type inet:ipv6-address;
                  description
                    "Endpoint of an SR Policy.";
                }
                leaf native-ip {
                  type boolean;
                  description
                    "Native-ip.";
                }
                leaf down-time {
                  type yang:date-and-time;
                  description
                    "Date and time when a flow map went down.";
                }
                leaf down-reason {
                  type map-down-reason-type;
                  description
                    "Reason why a flow map went down.";
                }
              }
            }
          }
        }
        container flow-group-statistic {
          config false;
          description
            "Statistics of flow groups.";
          leaf mapping-policy-count {
            type uint32;
            description
              "Number of mapping policies.";
          }
          leaf flow-group-count {
            type uint32;
            description
              "Number of flow groups.";
          }
          leaf flow-group-up-count {
            type uint32;
            description
              "Number of flow groups that are up.";
          }
          leaf dynamic-flow-group-count {
            type uint32;
            description
              "Number of dynamic flow groups.";
          }
          leaf dynamic-flow-group-up-count {
            type uint32;
            description
              "Number of dynamic flow groups that are up.";
          }
          leaf dscp-map-count {
            type uint32;
            description
              "Number of dscp maps.";
          }
          leaf dscp-map-up-count {
            type uint32;
            description
              "Number of dscp maps that are up.";
          }
          leaf service-class-map-count {
            type uint32;
            description
              "Number of service class maps.";
          }
          leaf service-class-map-up-count {
            type uint32;
            description
              "Number of service class maps that are up.";
          }
          leaf te-class-map-count {
            type uint32;
            description
              "Number of TE class mappings.";
          }	  
          leaf te-class-map-up-count {
            type uint32;
            description
              "Number of TE class mappings that are up.";
          }
          leaf spr-tunnel-count {
            type uint32;
            description
              "Number of SPR tunnels.";
          }
          leaf spr-tunnel-up-count {
            type uint32;
            description
              "Number of SPR tunnels that are up.";
          }
          leaf apn-id-ipv6-map-count {
            type uint32;
            description
              "Number of IPv6 APN ID maps.";
          }
          leaf apn-id-ipv6-map-up-count {
            type uint32;
            description
              "Number of IPv6 APN ID maps that are up.";
          }
        }
    }
  }
}
