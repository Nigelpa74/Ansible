/*
Copyright (C) 2019-2023 Huawei Technologies Co., Ltd. All rights reserved.
*/
module huawei-netconf {
  namespace "urn:huawei:yang:huawei-netconf";
  prefix netconf;
  import huawei-extension {
    prefix ext;
  }  
  organization
    "Huawei Technologies Co., Ltd.";
  contact
    "Huawei Industrial Base
     Bantian, Longgang
     Shenzhen 518129
     People's Republic of China
     Website: http://www.huawei.com
     Email: support@huawei.com";
  description
    "The NETCONF protocol defines a simple mechanism through which a network device can be managed, configuration data information can be retrieved, and new configuration data can be uploaded and manipulated.";
  revision 2023-08-09 {
    description
      "Add running-config node.";
    reference
      "Huawei private.";
  }
  revision 2022-09-13 {
    description
      "Add the configuration cache function for the device.";
    reference
      "Huawei private.";
  }
  revision 2022-01-05 {
    description
      "Add enable-alarms node.";
    reference
      "Huawei private.";
  }
  revision 2020-02-22 {
    description
      "Add rpc to manage active YANG modules.";
    reference
      "Huawei private.";
  }
  revision 2019-05-05 {
    description
      "Init revision.";
    reference
      "Huawei private.";
  }
  ext:task-name "netconf";  
  container netconf {
    description
      "The NETCONF protocol defines a simple mechanism through which a network device can be managed, configuration data information can be retrieved, and new configuration data can be uploaded and manipulated.";
    container operation-log-switch {
      description
        "Configure to get RPC operation log.";
      leaf get {
        type boolean;
        default "false";
        description
          "Enable/disable to get operation log.";
      }
    }
    container active-modules {
      config false;
      description
        "List of active YANG modules.";
      list active-module {
        key "module-name";
        config false;
        description
          "Statistics of active YANG module.";
        leaf module-name {
          type string {
            length "1..127";
          }
          description
            "Active YANG module name.";
        }
      }
    }
    container enable-alarms {
      description
        "List of NETCONF alarm.";
      list enable-alarm {
        key "alarm-name";
        description
          "Specify the enabled alarm.";
        leaf alarm-name {
          type enumeration {
            enum "connect-interrupt" {
              value 1;
              description
                "Specify connect-interrupt alarm.";
            }
          }
          description
            "Name of an enabled alarm.";
        }
      }
    }
    container config-cache {
      description
        "Configure configuration cache for the device. After this function is enabled, the system determines whether to generate the device configuration cache based on the device running status (such as the CPU usage and memory usage).
         The configuration cache mechanism increases the memory and CPU usage, but reduces the replace or copy-config operation time and improves efficiency.";
      leaf enable {
        type boolean;
        default "false";
        description
          "Enable/disable the function for generating device configuration cache.";
      }
      leaf  with-defaults {
        when "../enable = 'true'";
        type enumeration {
          enum trim {
            value 0;
            description
              "All default data is not used to generate device configuration cache.";
          }
          enum report-all {
            value 1;
            description
              "All default data is used to generate device configuration cache.";
          }
        }
        default "trim";
        description
          "Possible modes of generating device configuration cache where the default data may be used or not used.";
      }
    }
    container running-config {
      description
        "Configure the device to query the system configuration mode. After this function is configured, the device can control whether the query result contains the system configuration.";
      leaf query-mode {
        type enumeration {
          enum include-system {
            value 0;
            description
              "The query result contains the system configuration.";
          }
          enum exclude-system {
            value 1;
            description
              "The query result does not contain the system configuration.";
          }
        }
        default "include-system";
        description
          "The options of the query mode are used to filter the system configuration in the query result.";
      }
    }
  }
  rpc activate-module {
    description
      "Activate YANG modules.";
    input  {
      leaf module-name {
          type string {
            length "1..127";
          }
          mandatory true;
          description
            "The YANG module name to activate.";
      }
    }
  }
}
