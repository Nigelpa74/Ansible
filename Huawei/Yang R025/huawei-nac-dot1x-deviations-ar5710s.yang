/*
Copyright (C) 2019 Huawei Technologies Co., Ltd. All rights reserved.
*/
module huawei-nac-dot1x-deviations-ar5710s {
  yang-version 1.1;
  namespace "urn:huawei:yang:huawei-nac-dot1x-deviations-ar5710s";
  prefix hw-nac-dot1x-devs-ar5710s;

  import huawei-nac-dot1x {
    prefix hw-nac-dot1x;
  }

  organization
    "Huawei Technologies Co., Ltd.";
  contact
    "Huawei Industrial Base
     Bantian, Longgang
     Shenzhen 518129
     People's Republic of China
     Website: http://www.huawei.com
     Email: support@huawei.com";
  description
    "This module defines deviation statements for huawei-nac-dot1x module.";

  revision 2019-11-06 {
    description
      "Initial revision.";
    reference "Huawei private.";
  }

  deviation "/hw-nac-dot1x:nac-dot1x/hw-nac-dot1x:global/hw-nac-dot1x:url" {
    deviate not-supported;
  }
  deviation "/hw-nac-dot1x:nac-dot1x/hw-nac-dot1x:dot1x-access-profiles/hw-nac-dot1x:dot1x-access-profile/hw-nac-dot1x:unicast-trigger" {
    deviate not-supported;
  }
  deviation "/hw-nac-dot1x:nac-dot1x/hw-nac-dot1x:dot1x-access-profiles/hw-nac-dot1x:dot1x-access-profile/hw-nac-dot1x:dhcp-binding" {
    deviate not-supported;
  }
  deviation "/hw-nac-dot1x:nac-dot1x/hw-nac-dot1x:dot1x-access-profiles/hw-nac-dot1x:dot1x-access-profile/hw-nac-dot1x:authorize-of-authentication-events/hw-nac-dot1x:authorize-of-authentication-event/hw-nac-dot1x:authorize-parameters/hw-nac-dot1x:ucl-group" {
    deviate not-supported;
  }
  deviation "/hw-nac-dot1x:nac-dot1x/hw-nac-dot1x:dot1x-access-profiles/hw-nac-dot1x:dot1x-access-profile/hw-nac-dot1x:handshake" {
    deviate not-supported;
  }
  deviation "/hw-nac-dot1x:nac-dot1x/hw-nac-dot1x:global/hw-nac-dot1x:identity-packet-speed-limit" {
    deviate replace {
      default "30";
    }
  }
  deviation "/hw-nac-dot1x:nac-dot1x/hw-nac-dot1x:dot1x-access-profiles/hw-nac-dot1x:dot1x-access-profile/hw-nac-dot1x:name" {
    deviate add {
      must "../name != '-' and ../name != '--'";
    }
    deviate replace {
      type string {
        length "1..31";
        pattern "([^/\\\\\":?<>|%'@\\*]{1,31})";
        pattern '[^\s?]+';
        pattern '[!-~]+';
      }
    }
  }
}
