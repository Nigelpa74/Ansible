/*
Copyright (C) 2020-2025 Huawei Technologies Co., Ltd. All rights reserved.
*/
module huawei-dhcpv6 {
  namespace "urn:huawei:yang:huawei-dhcpv6";
  prefix dhcpv6;
  import huawei-extension {
    prefix ext;
  }
  import ietf-inet-types {
    prefix inet;
  }
  import huawei-ifm {
    prefix ifm;
  }
  import huawei-network-instance {
    prefix ni;
  }
  import huawei-l3vpn {
    prefix l3vpn;
  }
  import huawei-bd {
    prefix bd;
  }
  import huawei-pub-type {
    prefix pub-type;
  }
  import huawei-ethernet {
    prefix ethernet;
  }
  import huawei-ip {
    prefix ip;
  }
  include huawei-dhcpv6-relay;
  include huawei-dhcpv6-server;
  include huawei-dhcpv6-client;
  include huawei-dhcpv6-snooping;
  organization
    "Huawei Technologies Co., Ltd.";
  contact
    "Huawei Industrial Base
     Bantian, Longgang
     Shenzhen 518129
     People's Republic of China
     Website: http://www.huawei.com
     Email: support@huawei.com";
  description
    "Dynamic Host Configuration Protocol for IPv6.";
  revision 2025-01-07 {
    description
      "Add Lightweight DHCPv6 Relay Agent (LDRA) for DHCPv6 snooping.";
    reference
      "Huawei private.";
  }
  revision 2024-12-10 {
    description
      "Add DHCPv6 client-renew.";
    reference
      "Huawei private.";
  }
  revision 2024-09-15 {
    description
      "Modify dhcpv6 server.";
    reference
      "Huawei private.";
  }
  revision 2024-08-22 {
    description
      "Modify save-file-name type, delete pattern.";
    reference
      "Huawei private.";
  }
  revision 2024-08-12 {
    description
      "Add DHCPv6 Client vendor-specific.";
    reference
      "Huawei private.";
  }
  revision 2024-07-17 {
    description
      "Add DHCPv6 Client request option24.";
    reference
      "Huawei private.";
  }
  revision 2024-07-09 {
    description
      "Add deny-dhcpv6-enable nodes.";
    reference
      "Huawei private.";
  }
  revision 2024-06-25 {
    description
      "Add DHCPv6 Client BFD.";
    reference
      "Huawei private.";
  }
  revision 2024-06-15 {
    description
      "Modify dynamic-binds node range.";
    reference
      "Huawei private.";
  }
  revision 2024-01-29 {
    description
      "Add DHCPv6 Chasten node.";
    reference
      "Huawei private.";
  }
  revision 2024-01-22 {
    description
      "Modify pd-route-track-vrrp description.";
    reference
      "Huawei private.";
  }
  revision 2024-01-18 {
    description
      "Modify dhcpv6-snooping-attribute when condition.";
    reference
      "Huawei private.";
  }
  revision 2024-01-09 {
    description
      "Add bd augment.";
    reference
      "Huawei private.";
  }
  revision 2023-07-31 {
    description
      "Add set-dhcpv6-relay-pd-route-immediate-write node.";
    reference
      "Huawei private.";
  }
  revision 2023-03-30 {
    description
      "Add file-authentication-mode node.";
    reference
      "Huawei private.";
  }
  revision 2023-02-28 {
    description
      "Modify rebuild-option node.";
    reference
      "Huawei private.";
  }
  revision 2023-02-18 {
    description
      "Expand the type of fail cause.";
    reference
      "Huawei private.";
  }
  revision 2023-02-10 {
    description
      "Modify DHCPv6 Relay.";
    reference
      "Huawei private.";
  }  
  revision 2022-08-22 {
    description
      "Modify DHCPv6 Client.";
    reference
      "Huawei private.";
  }
  revision 2022-07-18 {
    description
      "Modify dhcpv6 snooping.";
    reference
      "Huawei private.";
  }
  revision 2022-07-04 {
    description
      "Add unit to packet statistics.";
    reference
      "Huawei private.";
  }
  revision 2022-05-30 {
    description
      "Add DHCPv6 duid node.";
    reference
      "Huawei private.";
  }
  revision 2022-05-28 {
    description
      "Add must conditions for dhcpv6-snooping-attribute container under EVC interface type.";
    reference
      "Huawei private.";
  }
  revision 2022-02-19 {
    description
      "Modify userinfos node.";
    reference
      "Huawei private.";
  }
  revision 2022-02-18 {
    description
      "Modify ip prefix description for client-infos and client-fail-infos nodes.";
    reference
      "Huawei private.";
  }
  revision 2022-02-14 {
    description
      "Add client-infos and client-fail-infos nodes.";
    reference
      "Huawei private.";
  }
  revision 2022-01-26 {
    description
      "Add reset dhcpv6 relay user node.";
    reference
      "Huawei private.";
  }
  revision 2022-01-05 {
    description
      "Remove redundant config false.";
    reference
      "Huawei private.";
  }
  revision 2021-12-13 {
    description
      "Modify pattern.";
    reference
      "Huawei private.";
  }
  revision 2021-09-04 {
    description
      "Add must condition.";
    reference
      "Huawei private.";
  }
  revision 2020-04-17 {
    description
      "Add node.";
    reference
      "Huawei private.";
  }
  revision 2020-04-10 {
    description
      "Add session-car.";
    reference
      "Huawei private.";
  }
  revision 2020-03-09 {
    description
      "Modify description.";
    reference
      "Huawei private.";
  }
  revision 2020-02-25 {
    description
      "Initial revision.";
    reference
      "Huawei private.";
  }
  ext:task-name "dhcp"; 
  typedef dhcpv6-duid {
    type enumeration {
      enum "invalid" {
        value 0;
        description
          "-";
      }
      enum "llt" {
        value 1;
        description
          "Link-layer address plus time.";
      }
      enum "ll" {
        value 2;
        description
          "Link-layer address.";
      }
      enum "user-defined" {
        value 3;
        description
          "User-defined.";
      }
    }
    description
      "The type of DHCPv6 DUID.";
  }
  typedef remote-id-format {
    type enumeration {
      enum "default" {
        value 0;
        description
          "Default format.";
      }
      enum "user-defined" {
        value 1;
        description
          "User-defined format.";
      }
    }
    description
      "The type of DHCPv6 remote-id format.";
  }
  container dhcpv6 {
    description
      "Configure a Dynamic Host Configuration Protocol for IPv6.";
    container common {
      description
        "Configure basic attributes.";
      container global {
        description
          "Configure DHCPv6 global attributes.";
        leaf enable {
          type boolean;
          default "true";
          description
            "Enable/disable Dynamic Host Configuration Protocol for IPv6.";
        }
        leaf remote-id-format {
          type remote-id-format;
          default "default";
          description
            "Remote-id format.";
        }
        leaf remote-id-user-define-text {
          when "../remote-id-format='user-defined'";
          type string {
            length "0..253";
            pattern '([^\t]{0,})';
          }
          description
            "DHCPv6 remote-id format defined by users. The value can be DUID, sysname, portname, porttype, iftype, MAC, slot, subslot, port, sVLAN, or cVLAN. For example, you can configure '%duid %portname:%sVLAN.%cVLAN'. The maximum length of the remote-id option is 251.";
        }
        leaf interface-id-format {
          type remote-id-format;
          default "default";
          description
            "Configure the Interface-ID format in DHCPv6 packets.";
        }
        leaf interface-id-user-define-text {
          when "../interface-id-format='user-defined'";
          type string {
            length "0..253";
            pattern "([^\t]{0,})";
          }
          description
            "Specify a user-defined format as the Interface-ID format.";
        }
        leaf duid-format {
          type dhcpv6-duid;
          must "(../duid-format = 'user-defined' and ../duid-string) or (../duid-format != 'user-defined')";
          default "invalid";
          description
            "DHCPv6 unique identifier format.";
        }
        leaf duid-string {
          when "../duid-format='user-defined'";
          type string {
            length "8..28";
            pattern '([^\t]{8,})';
          }
          description
            "DUID string, in hexadecimal notation.";
        }
        leaf rate-limit-enable {
          type boolean;
          default "true";
          description
            "Enable/disable DHCPv6 packets rate limit.";
        }
        leaf rate-limit {
          type uint32 {
            range "1..8000";
          }
          units "pps";
          default "512";
          description
            "DHCPv6 packets rate limit value.";
        }
        leaf source-ip-adaptive {
          type boolean;
          default "false";
          description
            "Enable/disable DHCPv6 source-ip-address format adaptive.";
        }
        leaf aging-time {
          type uint32 {
            range "1..1440";
          }
          units "min";
          default "30";
          description
            "DHCPv6 session CAR aging time.";
        }
        leaf active-duid {
          type string {
            length "8..28";
            pattern '([^\t]{8,})';
          }
          config false;
          description
            "Active DUID string, in hexadecimal notation.";
        }
        leaf packet-rate {
          type uint16 {
            range "0..400";
          }
          default "0";
          description
            "Specify the rate threshold for DHCPv6 messages.";
        }
        leaf drop-alarm-enable {
          type boolean;
          default "false";
          description
            "Enable/disable the alarm function for discarding DHCPv6 messages when the rate of DHCPv6 messages exceeds the limit.";
        }
        leaf drop-alarm-threshold {
          type uint16 {
            range "1..1000";
          }
          must "../drop-alarm-enable='true'";
          default "100";
          description
            "Specify the alarm threshold for the number of DHCPv6 messages discarded when the rate of DHCPv6 messages exceeds the rate limit.";
        }
      }
      container session-car {
        must "pir-value >= cir-value and pbs-value >= cbs-value";
        description
          "Configure session CAR.";
        leaf enable {
          type boolean;
          default "true";
          description
            "Enable/disable session CAR.";
        }
        leaf cir-value{
          type uint32 {
            range "0..1000000";
          }
          units "kbit/s";
          default "256";
          description
            "Specify the session CAR CIR value.";
        }
        leaf cbs-value {
          type uint32 {
            range "0..9000000";
          }
          units "Byte";
          default "32000";
          description
            "Specify the session car cbs value.";
        }
        leaf pir-value {
          type uint32 {
            range "0..1000000";
          }
          units "kbit/s";
          default "512";
          description
          "Specify the session CAR PIR value.";
        }
        leaf pbs-value {
          type uint32 {
            range "0..9000000";
          }
          units "Byte";
          default "64000";
          description
          "Specify the session CAR PBS value.";
        }
      }
      container chasten {
        description
          "Configure DHCPv6 user connection throttling.";
        leaf enable {
          type boolean;
          default "false";
          description
            "Enable/disable DHCPv6 user connection throttling.";
        }
        leaf request-packets {
          type uint16 {
            range "1..10000";
          }
          default "10";
          description
            "Request packets.";
        }
        leaf check-period {
          type uint16 {
            range "1..3600";
          }
          units "s";
          default "180";
          description
            "Check period.";
        }
        leaf restrain-period {
          type uint16 {
            range "1..3600";
          }
          units "s";
          default "300";
          description
            "Restrain period.";
        }
      }
      container ipsec-peers {
        description
          "List of DHCPv6 IPsecs.";
        list ipsec-peer {
          must "(peer-address='::' and vpn-name='_public_') or (peer-address!='::')";
          key "peer-address vpn-name";
          description
            "Configure DHCPv6 IPsec attributes.";
          leaf peer-address {
            type inet:ipv6-address-no-zone;
            description
              "Peer address.";
          }
          leaf vpn-name {
            type leafref {
              path "/ni:network-instance/ni:instances/ni:instance/ni:name";
            }
            must "(/ni:network-instance/ni:instances/ni:instance[ni:name=current()]/l3vpn:afs/l3vpn:af[l3vpn:type='ipv6-unicast'])";
            description
              "VPN name.";
          }
          leaf sa-name {
            type string {
              length "1..15";
            }
            mandatory true;
            description
              "SA name.";
          }
        }
      }
    }
    container relay {
      description
        "Configure DHCPv6 Relay.";
      uses dhcpv6:dhcpv6-relay-type;
    }
    container server {
      description
        "Configure DHCPv6 server.";
      uses dhcpv6:dhcpv6-server-type;
    }
    container snooping {
      description
        "Configure DHCPv6 snooping.";
      uses dhcpv6:dhcpv6-snooping-type;
    }
  }
  rpc reset-dhcpv6-snooping-packet-statistics {
   description
    "Reset DHCPv6 snooping packet statistics.";
    ext:node-ref "/dhcpv6:dhcpv6/dhcpv6:snooping/dhcpv6:packet-statistics";
  }
  rpc reset-dhcpv6-snooping-discarded-packet-statistics {
   description
    "Reset DHCPv6 snooping discarded packet statistics.";
    ext:node-ref "/ifm:ifm/ifm:interfaces/ifm:interface/dhcpv6:dhcpv6-snooping-attribute/dhcpv6:basic-attribute";
    input {
      leaf if-name {
        type leafref {
          path "/ifm:ifm/ifm:interfaces/ifm:interface/ifm:name";
        }
        mandatory true;
        description
          "Interface name.";
      }
    }
  }
  rpc reset-dhcpv6-snooping-dynamic-binding-table {
   description
    "Reset DHCPv6 snooping dynamic binding table.";
    ext:node-ref "/dhcpv6:dhcpv6/dhcpv6:snooping/dhcpv6:dynamic-binds";
    input {
      leaf ipv6-address {
        type inet:ipv6-address-no-zone;
        description
          "IPv6 address.";
      }
      leaf ipv6-prefix {
        type inet:ipv6-address-no-zone;
        description
          "IPv6 prefix.";
      }
      leaf prefix-length {
        type uint16 {
          range "16..128";
        }
        description
          "IPv6 prefix.";
      }
      leaf mac-address {
        type pub-type:mac-address;
        description
          "MAC address.";
      }
      leaf if-name {
        type leafref {
          path "/ifm:ifm/ifm:interfaces/ifm:interface/ifm:name";
        }
        description
          "Interface name.";
      }
      leaf send-release {
        type boolean;
        default "false";
        description
          "Send release to DHCPv6 server.";
      }
    }
  }
  rpc reset-dhcpv6-relay-user {
   description
    "Reset DHCPv6 relay users.";
    ext:node-ref "/dhcpv6:dhcpv6/dhcpv6:relay/dhcpv6:user-infos";
  }
  rpc reset-dhcpv6-relay-user-by-if-vlan {
   description
    "Reset DHCPv6 relay users by interface and VLAN.";
    ext:node-ref "/dhcpv6:dhcpv6/dhcpv6:relay/dhcpv6:user-infos";
    input {
      leaf if-name {
        type leafref {
          path "/ifm:ifm/ifm:interfaces/ifm:interface/ifm:name";
        }
        mandatory true;
        description
          "Interface name.";
      }
      leaf start-pevlan {
        type uint16 {
          range "1..4094";
        }
        description
          "Start PE VLAN ID.";
      }
      leaf end-pevlan {
        type uint16 {
          range "1..4094";
        }
        must "../start-pevlan and (../start-pevlan <= ../end-pevlan)";
        description
          "End PE VLAN ID.";
      }
      leaf start-cevlan {
        type uint16 {
          range "1..4094";
        }
        must "../start-pevlan";
        description
          "Start CE VLAN ID.";
      }
      leaf end-cevlan {
        type uint16 {
          range "1..4094";
        }
        must "../start-pevlan and ../start-cevlan and (../start-cevlan <= ../end-cevlan)";
        description
          "End CE VLAN ID.";
      }
    }
  }
  rpc reset-dhcpv6-relay-user-by-mac {
   description
    "Reset DHCPv6 relay users by MAC address.";
    ext:node-ref "/dhcpv6:dhcpv6/dhcpv6:relay/dhcpv6:user-infos";
    input {
      leaf mac-address {
        type pub-type:mac-address {
          length "0..255";
        }
        mandatory true;
        description
          "MAC address.";
      }
    }
  }
  rpc reset-dhcpv6-relay-user-by-client-duid {
   description
    "Reset DHCPv6 relay users by client DUID.";
    ext:node-ref "/dhcpv6:dhcpv6/dhcpv6:relay/dhcpv6:user-infos";
    input {
      leaf client-duid {
        type string {
          length "1..256";
        }
        mandatory true;
        description
          "Client DUID.";
      }
    }
  }
  rpc reset-dhcpv6-relay-user-by-server-duid {
   description
    "Reset DHCPv6 relay users by server DUID.";
    ext:node-ref "/dhcpv6:dhcpv6/dhcpv6:relay/dhcpv6:user-infos";
    input {
      leaf server-duid {
        type string {
          length "1..256";
        }
        mandatory true;
        description
          "Server DUID.";
      }
    }
  }
  rpc reset-dhcpv6-relay-user-by-client-address {
   description
    "Reset DHCPv6 relay users by client address.";
    ext:node-ref "/dhcpv6:dhcpv6/dhcpv6:relay/dhcpv6:user-infos";
    input {
      leaf client-address {
        type inet:ipv6-address-no-zone;
        mandatory true;
        description
          "Client address.";
      }
      leaf vpn-name {
        type leafref {
          path "/ni:network-instance/ni:instances/ni:instance/ni:name";
        }
        description
          "VPN name.";
      }
    }
  }
  rpc reset-dhcpv6-relay-user-by-server-address {
   description
    "Reset DHCPv6 relay users by server address.";
    ext:node-ref "/dhcpv6:dhcpv6/dhcpv6:relay/dhcpv6:user-infos";
    input {
      leaf server-address {
        type inet:ipv6-address-no-zone;
        mandatory true;
        description
          "Server address.";
      }
      leaf vpn-name {
        type leafref {
          path "/ni:network-instance/ni:instances/ni:instance/ni:name";
        }
        description
          "VPN name.";
      }
    }
  }
  rpc set-dhcpv6-duid {
    description
      "Configure DHCPv6 DUID.";
    input {
      leaf duid-format {
        type dhcpv6-duid;
        mandatory true;
        description
          "DHCPv6 unique identifier format.";
      }
      leaf duid-string {
        when "../duid-format='user-defined'";
        type string {
          length "8..28";
          pattern '(([0-9a-fA-F]{2}){4,14})';
        }
        description
          "DUID string, in hexadecimal notation.";
      }
    }
  }
  rpc set-dhcpv6-relay-pd-route-immediate-write {
   description
    "Set DHCPv6 relay PD route immediate write.";
    ext:node-ref "/dhcpv6:dhcpv6/dhcpv6:relay/dhcpv6:pd-route";
  }
  rpc dhcpv6-client-renew {
    description
      "Manually renew the lease of the IP address obtained by a DHCPv6 client.";
    input  {
      leaf if-name {
        type leafref {
          path "/ifm:ifm/ifm:interfaces/ifm:interface/ifm:name";
        }
        description
          "Interface name.";
      }
    }
  }
  augment "/ifm:ifm/ifm:interfaces/ifm:interface" {
    description
      "Extend interface attribute.";
    container dhcpv6-server-if {
      when "../ip:ipv6";
      description
        "Configure DHCPv6 server interface function.";
      leaf pool-name {
        type leafref {
          path "/dhcpv6:dhcpv6/dhcpv6:server/dhcpv6:ipv6-pools/dhcpv6:ipv6-pool/dhcpv6:pool-name";
        }
        description
          "Pool name.";
      }
      leaf is-allow-hint {
        when "../pool-name";
        type boolean;
        default "false";
        description
          "Enable/disable to allow the server to assign prefix according to the client expectation.";
      }
      leaf preference {
        when "../pool-name";
        type uint8 {
          range "0..255";
        }
        default "0";
        description
          "The server priority in the advertise packet.";
      }
      leaf is-rapid {
        when "../pool-name";
        type boolean;
        default "false";
        description
          "Enable/disable to support for fast allocation.";
      }
      leaf is-unicast {
        when "../pool-name";
        type boolean;
        default "false";
        description
          "Enable/disable to specify the unicast communication between client and server in the address renewal process.";
      }
      container packet-statistics {
        config false;
        description
          "DHCPv6 server interface statistics.";
        leaf solicit-number {
          type uint32;
          config false;
          description
            "The count of slolict packet.";
        }
        leaf request-number {
          type uint32;
          config false;
          description
            "The count of request packet.";
        }
        leaf confirm-number {
          type uint32;
          config false;
          description
            "The count of confirm packet.";
        }
        leaf renew-number {
          type uint32;
          config false;
          description
            "The count of renew packet.";
        }
        leaf rebind-number {
          type uint32;
          config false;
          description
            "The count of rebind packet.";
        }
        leaf release-number {
          type uint32;
          config false;
          description
            "The count of release packet.";
        }
        leaf decline-number {
          type uint32;
          config false;
          description
            "The count of decline packet.";
        }
        leaf information-request-number {
          type uint32;
          config false;
          description
            "The count of information-request packet.";
        }
        leaf relay-forward-number {
          type uint32;
          config false;
          description
            "The count of relay-forward packet.";
        }
        leaf lease-query-number {
          type uint32;
          config false;
          description
            "The count of lease-query packet.";
        }
        leaf unknown-type-number {
          type uint32;
          config false;
          description
            "The count of unknown-type packet.";
        }
        leaf advertise-number {
          type uint32;
          config false;
          description
            "The count of advertise packet.";
        }
        leaf reply-number {
          type uint32;
          config false;
          description
            "The count of reply packet.";
        }
        leaf relay-reply-number {
          type uint32;
          config false;
          description
            "The count of relay-reply packet.";
        }
        leaf lease-reply-number {
          type uint32;
          config false;
          description
            "The count of lease-reply packet.";
        }
        leaf reconfigure-number {
          type uint32;
          config false;
          description
            "The count of reconfigure packet.";
        }
      }
    }
    container dhcpv6-if {
      description
        "Configure DHCPv6 attributes on an interface.";
      leaf is-enable {
        type boolean;
        default "false";
        description
          "Enable/disable DHCPv6 relay on an interface.";
      }
      container option {
        description
          "Configure DHCPv6 option attributes.";
        leaf insert-interface-id {
          type boolean;
          default "false";
          description
            "Enable/disable to insert the interface-id option.";
        }
        leaf insert-remote-id {
          type boolean;
          default "false";
          description
            "Enable/disable to insert the remote-id option.";
        }
        leaf insert-option79 {
          type boolean;
          default "false";
          description
            "Enable/disable inserting the Option79 field into DHCPv6 messages.";
        }
        leaf insert-vss {
          type boolean;
          default "false";
          description
            "Enable/disable to insert the OPTION_VSS flag.";
        }
        leaf insert-client-lla {
          type boolean;
          default "false";
          description
            "Enable/disable to insert client link-layer address.";
        }
      }
    }
    container dhcpv6-relay-attribute {
      must "not(source-address and source-interface)";
      description
        "Configure DHCPv6 relay attributes on an interface.";
      leaf gateway-switch-enable {
        type boolean;
        default "false";
        description
          "Enable/disable DHCPv6 gateway-switch function.";
      }
      leaf source-address {
        type inet:ipv6-address-no-zone;
        description
          "Source address.";
      }
      leaf link-address {
        type inet:ipv6-address-no-zone;
        description
          "Link address.";
      }
      leaf strict-check {
        type boolean;
        default "false";
        description
          "Enable/disable strict check on interfaces.";
      }
      leaf server-group-name {
        type leafref {
          path "/dhcpv6:dhcpv6/dhcpv6:relay/dhcpv6:server-groups/dhcpv6:server-group/dhcpv6:name";
        }
        description
          "DHCPv6 relay server group name.";
      }
      leaf source-interface {
        type leafref {
          path "/ifm:ifm/ifm:interfaces/ifm:interface/ifm:name";
        }
        description
          "Configure the IPv6 address of an interface as the source IPv6 address of packets.";
      }
      leaf pd-route {
        type boolean;
        default "false";
        description
          "Enable/disable a DHCPv6 relay agent to forward routing information of DHCPv6 prefix delegation terminals.";
      }
      leaf current-link-address {
        type inet:ipv6-address-no-zone;
        config false;
        description
        "Current link address.";
      }
      container destination-addresses {
        description
          "List of DHCPv6 relay destination addresses.";
        list destination-address {
          key "ipv6-address";
          max-elements "8";
          description
            "Configure the DHCPv6 relay destination address.";
          leaf ipv6-address {
            type inet:ipv6-address-no-zone;
            description
              "Destination address.";
          }
          choice net-type {
            default "vpn-instance";
            description
              "Choice of vpn or public net.";
            case vpn-instance {
              description
                "Case vpn instance.";
              leaf vpn-instance {
                type leafref {
                  path "/ni:network-instance/ni:instances/ni:instance/ni:name";
                }
                description
                  "VPN instance name.";
              }
            }
            case public-net {
              description
                "Case public net.";
              leaf public-net {
                type boolean;
                default "false";
                description
                  "Enable/disable that the destination VPN instance of the DHCPv6 messages is the public VPN instance.";
              }
            }
          }
        }
      }
      container destination-ifs {
        description
          "List of DHCPv6 relay destination interfaces.";
        list destination-if {
          key "if-name";
          max-elements "8";
          description
            "Configure DHCPv6 relay destination interface.";
          leaf if-name {
            type leafref {
              path "/ifm:ifm/ifm:interfaces/ifm:interface/ifm:name";
            }
            must "not(((../../../../ifm:type = 'Virtual-Ethernet') or (../../../../ifm:type = 'Global-VE')) and (../../../../ifm:class = 'main-interface'))";
            description
              "Destination interface name.";
          }
        }
      }
      container option {
        description
          "Configure DHCPv6 relay option attributes.";
        choice interface-id-mode {
          description
            "Configure the interface-id-mode.";
          case cn-telecom {
            description
              "CN-telecom interface-id mode.";
            leaf cn-telecom-mode {
              type empty;
              description
                "CN-telecom interface-id mode.";
            }
          }
          case cn-telecom-inherit {
            description
              "CN-telecom-inherit interface-id mode.";
            leaf cn-telecom-inherit-mode {
              type empty;
              description
                "CN-telecom-inherit interface-id mode.";
            }
          }
          case tr-101 {
            description
              "TR-101 interface-id mode.";
            leaf tr-101-mode {
              type empty;
              description
                "TR-101 interface-id mode.";
            }
          }
          case user-defined {
            description
              "User-defined interface-id mode.";
            leaf interface-id-text {
              type string {
                length "1..255";
                pattern '([^\t]{1,})';
              }
              description
                "DHCPv6 interface-id string defined by users.";
            }
          }
        }
        leaf insert-remote-id {
          type boolean;    
          default "false";    
          description    
            "Enable/disable to insert the remote-id option.";
        }
        choice remote-id-mode {
          description
            "Configure the remote-id mode.";
          case default {
            description
              "Default remote-id mode.";
            leaf default-format {
              type empty;
              description
                "Default remote-id mode.";
            }
          }
          case user-defined {
            description
              "User-defined remote-id mode.";
            leaf remote-id-text {
              type string {
                length "1..255";
                pattern '([^\t]{1,})';
              }
              description
                "DHCPv6 remote-id string defined by users.";
            }
          }
        }
        leaf insert-subscriber-id {
          type boolean;
          default "false";
          description
            "Enable/disable to insert the subscriber-id option.";
        }
        leaf insert-prefix-exclude {
          type boolean;
          default "false";
          description
            "Enable/disable to insert exclude prefix option.";
        }
      }      
      container rebuild-option {
        description
          "Configure DHCPv6 relay option rebuild attributes.";
        choice interface-id-mode {
          description
            "Configure the interface-id option.";
          case rebuild-interface-id-mode {
            description
              "Rebuild interface-id mode.";
            leaf rebuild-interface-id {
              type empty;
              description
              "Rebuild the interface-id option.";
            }
          }		  
          case user-defined {
            description
              "User-defined interface-id mode.";
            leaf interface-id-text {
              type string {
                length "1..255";
                pattern '([^\t]{1,})';
              }
              description
                "DHCPv6 interface-id string defined by users.";
            }
          }
        }
        choice remote-id-mode {
          description
            "Configure the remote-id mode.";
          case rebuild-remote-id-mode {
            description
              "Rebuild remote-id mode.";
            leaf rebuild-remote-id {
              type empty;
              description
              "Rebuild the remote-id option.";
            }		  
          }
          case user-defined {
            description
              "User-defined remote-id mode.";
            leaf remote-id-text {
              type string {
                length "1..255";
                pattern '([^\t]{1,})';
              }
              description
                "DHCPv6 remote-id string defined by users.";
            }
          }
        }
      }
      container access-limit-setting {
        description
          "Configure the maximum number of access users on an interface.";
        leaf access-limit {
          type uint32 {
            range "0..65536";
          }
          description
            "Maximum number of access users on an interface.";
        }
        leaf access-vlan-limit {
          when "(../../../ethernet:ethernet/ethernet:l3-sub-interface/ethernet:dot1q-termination) or (../../../ethernet:ethernet/ethernet:l3-sub-interface/ethernet:qinq-termination) or (../../../ethernet:ethernet/ethernet:l3-sub-interface/ethernet:vlan-type-dot1q)";
          type uint32 {
            range "0..65536";
          }
          description
            "Maximum number of access users in any VLAN.";
        }
      }
      container destination-vpn-addresses {
        description
          "List of DHCPv6 relay server attributes.";
        list destination-vpn-address {
          key "address vpn-name";
          max-elements "8";
          description
            "Configure DHCPv6 relay server VPN.";
          leaf address {
            type inet:ipv6-address-no-zone;
            description
              "DHCPv6 relay server VPN address.";
          }
          leaf vpn-name {
            type leafref {
              path "/ni:network-instance/ni:instances/ni:instance/ni:name";
            }
            description
              "DHCPv6 relay server VPN name.";
          }
        }
      }
      container pd-route-track-vrrp {
        description
          "Configure DHCPv6 relay PD route in dual-device hot standby scenarios.";
        leaf degrade-cost {
          type uint32 {
            range "1..4294967295";
          }
          description
            "Cost value to be adjusted for DHCPv6 relay PD route.";
        }
      }
      container option18 {
        description
          "Configure option 18 field in a DHCPv6 message.";
        leaf insert-enable {
          type boolean;
          default "false";
          description
            "Enable/disable the device to insert the Option 18 field to a DHCPv6 message.";
        }
        leaf rebuild-enable {
          type boolean;
          default "false";
          description
            "Enable/disable the device to forcibly insert the Option 18 field to a DHCPv6 message.";
        }
        container formats {
          description
            "List of the format of the Option 18 field in a DHCPv6 message.";
          list format {
            key "vlan ce-vlan";
            description
              "Configure the format of the Option 18 field in a DHCPv6 message.";
            leaf vlan {
              type uint16 {
                range "0..4094";
              }
              description
                "Specify the outer VLAN ID. Zero is no VLAN.";
            }
            leaf ce-vlan {
              type uint16 {
                range "0..4096";
              }
              description
                "Specify the inner VLAN ID.Zero is no ce VLAN.";
            }
            leaf user-defined {
              type string {
                length "1..251";
              }
              description
                "Indicate the user-defined format of the Option 18 field.";
            }
          }
        }
      }
      container option37 {
        description
          "Configure option 37 field in a DHCPv6 message.";
        leaf insert-enable {
          type boolean;
          default "false";
          description
            "Enable/disable the device to insert the Option 37 field to a DHCPv6 message.";
        }
        leaf rebuild-enable {
          type boolean;
          default "false";
          description
            "Enable/disable the device to forcibly insert the Option 37 field to a DHCPv6 message.";
        }
        container formats {
          description
            "List of the format of the Option 37 field in a DHCPv6 message.";
          list format {
            key "vlan ce-vlan";
            description
              "Configure the format of the Option 37 field in a DHCPv6 message.";
            leaf vlan {
              type uint16 {
                range "0..4094";
              }
              description
                "Specify the outer VLAN ID. Zero is no VLAN.";
            }
            leaf ce-vlan {
              type uint16 {
                range "0..4096";
              }
              description
                "Specify the inner VLAN ID.Zero is no ce VLAN.";
            }
            leaf user-defined {
              type string {
                length "1..251";
              }
              description
                "Indicate the user-defined format of the Option 37 field.";
            }
          }
        }
      }
      container access-vlans {
        config false;
        description
          "List of maximum number of access users that send VLAN tagged packets.";
        list access-vlan {
          key "access-limit pe-vlan ce-vlan";
          config false;
          max-elements "8";
          description
            "Operational state of the maximum number of access users that send VLAN tagged packets.";
          leaf access-limit {
            type uint32 {
              range "0..65536";
            }
            config false;
            description
              "Maximum number of access users.";
          }
          leaf pe-vlan {
            type uint16;
            config false;
            description
              "PE VLAN ID in QinQ.";
          }
          leaf ce-vlan {
            type boolean;
            config false;
            description
              "Permit packets with any inner VLAN IDs.";
          }
          leaf vlan-batch {
            type pub-type:vlan-range;
            config false;
            description
              "VLAN list.";
          }
        }
      }
      container packet-statistics {
        config false;
        description
          "Statistics of DHCPv6 relay interface packet.";
        leaf solicit-received-count {
          type uint32;
          default "0";
          config false;
          description
            "Solicit packets received from clients.";
        }
        leaf request-received-count {
          type uint32;
          default "0";
          config false;
          description
            "Request packets received from clients.";
        }
        leaf confirm-received-count {
          type uint32;
          default "0";
          config false;
          description
            "Confirm packets received from clients.";
        }
        leaf renew-received-count {
          type uint32;
          default "0";
          config false;
          description
            "Renew packets received from clients.";
        }
        leaf rebind-received-count {
          type uint32;
          default "0";
          config false;
          description
            "Rebind packets received from clients.";
        }
        leaf decline-received-count {
          type uint32;
          default "0";
          config false;
          description
            "Decline packets received from clients.";
        }
        leaf release-received-count {
          type uint32;
          default "0";
          config false;
          description
            "Release packets received from clients.";
        }
        leaf inform-received-count {
          type uint32;
          default "0";
          config false;
          description
            "Information-request packets received from clients.";
        }
        leaf relay-forward-received-count {
          type uint32;
          default "0";
          config false;
          description
            "Relay-forward packets received from relay agents or servers.";
        }
        leaf relay-reply-received-count {
          type uint32;
          default "0";
          config false;
          description
            "Relay-reply packets received from relay agents or servers.";
        }
        leaf advertise-send-count {
          type uint32;
          default "0";
          config false;
          description
            "Advertise packets sent to clients.";
        }
        leaf reply-send-count {
          type uint32;
          default "0";
          config false;
          description
            "Relay-reply packets sent to clients.";
        }
        leaf reconfig-send-count {
          type uint32;
          default "0";
          config false;
          description
            "Reconfigure packets sent to clients.";
        }
        leaf relay-forward-send-count {
          type uint32;
          default "0";
          config false;
          description
            "Relay-forward packets sent to relay agents or servers.";
        }
        leaf relay-reply-send-count {
          type uint32;
          default "0";
          config false;
          description
            "Relay-reply packets sent to relay agents or servers.";
        }
        leaf bad-packets-received-count {
          type uint32;
          default "0";
          config false;
          description
            "Error packets received.";
        }
        leaf drop-packets-for-table-full {
          type uint32;
          default "0";
          config false;
          description
            "Packets discarded because the table is full.";
        }
        leaf drop-packets-for-general-error {
          type uint32;
          default "0";
          config false;
          description
            "Packets discarded due to general errors.";
        }
        leaf drop-packets-for-ipsec-authentication-fail {
          type uint32;
          default "0";
          config false;
          description
            "Packets discarded due to IPsec authentication failures.";
        }
      }
      container dot1q-access-limits {
        description
          "List of maximum number of access users on dot1q interfaces.";
        list dot1q-access-limit { 
          must "(../../../ethernet:ethernet/ethernet:l3-sub-interface/ethernet:dot1q-termination) or (../../../ethernet:ethernet/ethernet:l3-sub-interface/ethernet:vlan-type-dot1q)";
          key "access-limit";
          description
            "Configure maximum number of access users on a dot1q interface.";
          leaf access-limit {
            type uint32 {
              range "0..65536";
            }
            description
              "Maximum number of users allowed.";
          }
          leaf vlan-list {
             type pub-type:vlan-range;
             mandatory true;
             description
                "VLAN list.";
           }
          } 
        }  
      container qinq-access-limits {
        description
          "List of maximum number of access users on QinQ interfaces.";
        list qinq-access-limit { 
          must "../../../ethernet:ethernet/ethernet:l3-sub-interface/ethernet:qinq-termination";
          key "access-limit pe-vlan-id";
          description
            "Configure maximum number of access users on a QinQ interface.";
          leaf access-limit {
            type uint32 {
              range "0..65536";
            }
            description
              "Maximum number of users allowed.";
          } 
          leaf pe-vlan-id {
           type uint16 {
             range "1..4094";
           }
           description
             "PE VLAN ID.";
          }
          leaf ce-vlan-list {
            type pub-type:vlan-range;
            mandatory true;
          description
             "CE VLAN ID list.";
          }
        }
      }  
      container qinq-any-access-limits {
        description
          "List of maximum number of access users on QinQ interfaces.";
        list qinq-any-access-limit {
          must "../../../ethernet:ethernet/ethernet:l3-sub-interface/ethernet:qinq-termination";
          key "pe-vlan-id";
          max-elements  "16";
          description
            "Configure maximum number of access users on a QinQ interface.";
          leaf pe-vlan-id {
           type uint16 {
             range "1..4094";
           }
           description
             "PE VLAN ID.";
          }
          leaf access-limit {
            type uint32 {
              range "0..65536";
            }
            mandatory true;
            description
              "Maximum number of users allowed.";
          } 
        }
      }
    }
    container dhcpv6-relay-if {
      presence "Enable/disable DHCPv6 relay functions on an interface.";
      status deprecated;
      description
        "Configure DHCPv6 relay attributes on an interface, it was replaced by a container named dhcpv6-relay-attribute.";
      leaf source-address {
        type inet:ipv6-address-no-zone;
        status deprecated;
        description
          "Source address.";
      }
      leaf link-address {
        type inet:ipv6-address-no-zone;
        status deprecated;
        description
          "Link address.";
      }
      leaf strict-check {
        type boolean;
        default "false";
        status deprecated;
        description
          "Enable/disable strict check on interfaces.";
      }
      leaf server-group-name {
        type leafref {
          path "/dhcpv6:dhcpv6/dhcpv6:relay/dhcpv6:server-groups/dhcpv6:server-group/dhcpv6:name";
        }
        status deprecated;
        description
          "DHCPv6 relay server group name.";
      }
    }
    container dhcpv6-snooping-attribute {
      description
        "Configure DHCPv6 snooping attributes on an interface.";
      container basic-attribute {
        when "(/dhcpv6:dhcpv6/dhcpv6:snooping/dhcpv6:global/dhcpv6:enable='true') and ((../../ifm:l2-mode-enable='false') or (../../ifm:l2-mode-enable='true' and /bd:bd/bd:instances/bd:instance/bd:service-points/bd:service-point[bd:interface-name=current()/../../ifm:name]))";
        description
        "Configure Basic DHCPv6 snooping attribute on the interface.";
        leaf enable {
          type boolean;
          default "false";
          description
            "Enable/disable DHCPv6 snooping on an interface.";
        }
        leaf alarm-ipv6-enable {
          type boolean;
          default "false";
          description
            "Enable/disable the alarm function for IPv6 packets.";
        }
        leaf alarm-ipv6-threshold {
          type uint16 {
            range "1..1000";
          }
          description
            "Alarm threshold for IPv6 packets.";
        }
        leaf check-ipv6-enable {
          type boolean;
          default "false";
          description
            "Enable/disable the check function for IPv6 packets.";
        }
        leaf nomatch-packet-forward-policy {
          type boolean;
          default "true";
          description
            "Enable/disable forward policy for checking the DHCPv6 snooping binding table.";
        }
        leaf ipv6-packet-discarded-count {
          type uint64;
          config false;
          description
            "Number of discarded IPv6 packets.";
        }
      }
      container static-binds {
        description
        "List of static binding table on an interface.";
        list static-bind {
          key "ipv6-address ipv6-mask vlan-id cevlan-id";
          description
            "Configure static binding table on an interface.";
          leaf ipv6-address {
            type inet:ipv6-address-no-zone;
            description
              "IPv6 address.";
          }
          leaf ipv6-mask {
            type uint8 {
              range "16..128";
            }
            description
              "IPv6 mask.";
          }
          leaf vlan-id {
            type uint16 {
              range "0..4094";
            }
            must "(../../../../ifm:class='main-interface' and ../vlan-id=0) or
                  (../../../../ethernet:ethernet/ethernet:l3-sub-interface/ethernet:dot1q-termination/ethernet:dot1q-vlans/ethernet:dot1q-vlans/ethernet:vlan-list and ../vlan-id!=0) or
                  (../../../../ethernet:ethernet/ethernet:l3-sub-interface/ethernet:qinq-termination/ethernet:qinq-vids/ethernet:qinq-vid and ../vlan-id!=0) or
                  (../../../../ethernet:ethernet/ethernet:l3-sub-interface/ethernet:vlan-type-dot1q and ../vlan-id=../../../../ethernet:ethernet/ethernet:l3-sub-interface/ethernet:vlan-type-dot1q/ethernet:vlan-type-vid) or
                  ((/bd:bd/bd:instances/bd:instance/bd:service-points/bd:service-point[bd:interface-name=current()/../../../../ifm:name]) and
                  ((../../../../ethernet:ethernet/ethernet:l2-sub-interface/ethernet:default) or
                  (../../../../ethernet:ethernet/ethernet:l2-sub-interface/ethernet:untag and ../vlan-id=0) or
                  (../../../../ethernet:ethernet/ethernet:l2-sub-interface/ethernet:dot1q/ethernet:vlans/ethernet:vlan-list and ../vlan-id!=0) or
                  (../../../../ethernet:ethernet/ethernet:l2-sub-interface/ethernet:qinqs/ethernet:qinq-vids/ethernet:qinq-vid[ethernet:pe-vlan-id=current()])))";
            description
              "VLAN ID, 0 means NULL.";
          }
          leaf cevlan-id {
            type uint16 {
              range "0..4094";
            }
            must "(../../../../ifm:class='main-interface' and ../cevlan-id=0) or
                  (../../../../ethernet:ethernet/ethernet:l3-sub-interface/ethernet:dot1q-termination/ethernet:dot1q-vlans/ethernet:dot1q-vlans/ethernet:vlan-list and ../cevlan-id=0) or
                  (../../../../ethernet:ethernet/ethernet:l3-sub-interface/ethernet:qinq-termination/ethernet:qinq-vids/ethernet:qinq-vid and ../cevlan-id!=0) or
                  (../../../../ethernet:ethernet/ethernet:l3-sub-interface/ethernet:vlan-type-dot1q and ../cevlan-id=0) or
                  ((/bd:bd/bd:instances/bd:instance/bd:service-points/bd:service-point[bd:interface-name=current()/../../../../ifm:name]) and
                  ((../../../../ethernet:ethernet/ethernet:l2-sub-interface/ethernet:default) or
                  (../../../../ethernet:ethernet/ethernet:l2-sub-interface/ethernet:untag and ../cevlan-id=0) or
                  (../../../../ethernet:ethernet/ethernet:l2-sub-interface/ethernet:dot1q/ethernet:vlans/ethernet:vlan-list and ../cevlan-id=0) or
                  (../../../../ethernet:ethernet/ethernet:l2-sub-interface/ethernet:qinqs/ethernet:qinq-vids/ethernet:qinq-vid/ethernet:ce-vlan-list and ../cevlan-id!=0)))";
            description
              "CE VLAN ID, 0 means NULL.";
          }
          leaf mac-address {
            type pub-type:mac-address {
              length "0..255";
              pattern '([0-9a-f][0|2|4|6|8|a|c|e][0-9a-f]{2}(-[0-9a-f]{4}){2})';
            }
            must "../ipv6-mask=128";
            description
              "MAC address.";
          }
        }
      }
    }
  }
  augment "/bd:bd/bd:instances/bd:instance" {
    description "Extend BD attribute.";
    container dhcpv6-snooping-bd {
      description
        "Configure DHCPv6 snooping BD attributes.";
      leaf alarm-reply-enable {
        type boolean;
        default "false";
        description
          "Enable/disable the alarm function for discarded untrusted packets.";
      }
      leaf alarm-reply-threshold {
        type uint16 {
          range "1..1000";
        }
        description
          "The alarm threshold is configured for discarded untrusted packets.";
      }
    }
  }
}
