/*
Copyright (C) 2019-2024 Huawei Technologies Co., Ltd. All rights reserved.
*/
module huawei-srv6 {
  namespace "urn:huawei:yang:huawei-srv6";
  prefix srv6;
  import huawei-network-instance {
    prefix ni;
  }
  import ietf-inet-types {
    prefix inet;
  }
  import huawei-extension {
    prefix ext;
  }
  import huawei-ifm {
    prefix ifm;
  }
  import huawei-evpl {
    prefix evpl;
  }
  import huawei-bd {
    prefix bd;
  }
  import huawei-pub-type {
    prefix pub-type;
  }
  import huawei-routing-policy {
    prefix rtp;
  }
  import ietf-yang-types {
    prefix yang;
  }
  include huawei-srv6-type;

  organization
    "Huawei Technologies Co., Ltd.";
  contact
    "Huawei Industrial Base
     Bantian, Longgang
     Shenzhen 518129
     People's Republic of China
     Website: http://www.huawei.com
     Email: support@huawei.com";
  description
    "Segment routing IPv6.";
  revision 2024-12-11 {
    description
      "Modify must condition of end-extensions. Add end-uncompressed-extensions container. Modify must condition of end-x-extensions. Add end-x-uncompressed-extensions container.
       Add leaf nodes for SRv6 protected End.X. Modifying the end-xs, end-x-psps, end-x-psp-usp-usds, end-x-psp-usp-usd-cocs, end-x-cocs, end-x-psp-cocs, and end-x-extensions containers. Add leaf nodes for end-b6s container.
       Add afr-enable leaf node.
       Update bak-compress-mode leaf node.
       Add inherit-slice-enable leaf node.";
    reference
      "Huawei private.";
  }
  revision 2024-06-06 {
    description
      "Add leaf nodes for SRv6 protected End.X. Modify the type of protocol in end-dx4 and end-dx6. Modify global-id-block leaf node and add local-id-block leaf node in attribute container. Modify global-id-block leaf node and add space leaf node in csid-proportion container. Add xsid container in local-sids. Add sid-begin-value leaf in input of get-available-local-block. Add begin-value leaf in srv6lb.";
    reference
      "Huawei private.";
  }
  revision 2024-01-18 {
    description
      "Modify must condition of end-x-psp-usp-usd-cocs, end-x-cocs, end-x-psp-cocs, end-psp-usp-usd-cocs, end-cocs, end-psp-cocs.";
    reference
      "Huawei private.";
  }
  revision 2024-01-03 {
    description
      "Modify the must condition of end-dt2ms in locators.";
    reference
      "Huawei private.";
  }
  revision 2023-09-04 {
    description
      "Add behavior and compress leaf nodes for end-dt2ms in local-sids.";
    reference
      "Huawei private.";
  }
  revision 2023-08-24 {
    description
      "Modify global-info container.";
    reference
      "Huawei private.";
  }
  revision 2023-08-15 {
    description
      "Add SRv6 TE-FRR trust domain container and leaf node.";
    reference
      "Huawei private.";
  }
  revision 2023-08-07 {
    description
      "Add behavior and compress leaf nodes for end-dt2ms.";
    reference
      "Huawei private.";
  }
  revision 2023-04-12 {
    description
      "Modify must condition of opcodes container and lists within the container.";
    reference
      "Huawei private.";
  }
  revision 2023-03-28 {
    description
      "Add local-end-x-encapsulation leaf node. Modify must condition of reduce-srh-enable.";
    reference
      "Huawei private.";
  }
  revision 2023-03-15 {
    description
      "Add s-flag leaf node.";
    reference
      "Huawei private.";
  }
  revision 2023-03-02 {
    description
      "Modify unique tag of end-x-extension.";
    reference
      "Huawei private.";
  }
  revision 2023-02-28 {
    description
      "Modify must condition of end-dx2.";
    reference
      "Huawei private.";
  }
  revision 2023-02-15 {
    description
      "Modify when condition of opcodes.";
    reference
      "Huawei private.";
  }
  revision 2022-12-28 {
    description
      "Add update-time leaf node.";
    reference
      "Huawei private.";
  }
  revision 2022-12-15 {
    description
      "Modify compress leaf of vpn sids.";
    reference
      "Huawei private.";
  }
  revision 2022-11-17 {
    description
      "Add containers for 16-bit compression.";
    reference
      "Huawei private.";
  }
  revision 2022-11-15 {
    description
      "Add global-info container.";
    reference 
      "Huawei private.";
  }    
  revision 2022-10-28 {
    description
      "Modify l3-fwds interface type.";
    reference
      "Huawei private.";
  }
  revision 2022-10-11 {
    description
      "Add locator preference container.";
    reference
      "Huawei private.";
  }
  revision 2022-04-21 {
    description
      "Add end-dt46 container.";
    reference
      "Huawei private.";
  }
  revision 2022-04-14 {
    description
      "Add end-cocs end-psp-cocs end-x-cocs end-x-psp-cocs container.";
    reference
      "Huawei private.";
  }
  revision 2022-03-15 {
    description
      "Add source-interface leaf.";
    reference
      "Huawei private.";
  }
  revision 2022-02-18 {
    description
      "Add ipv6-prefix leaf.";
    reference
      "Huawei private.";
  }
  revision 2022-01-27 {
    description
      "Add te frr function leaf.";
    reference
      "Huawei private.";
  }
  revision 2021-08-26 {
    description
      "Add end-dt2us container.";
    reference
      "Huawei private.";
  }
  revision 2020-06-17 {
    description
      "Add leaf units.";
    reference "Huawei private.";
  }
  revision 2020-05-25 {
    description
      "Add mapping-policys container.";
    reference
      "Huawei private.";
  }
  revision 2020-05-18 {
    description
      "Modify the default value of path-mtu leaf.";
    reference
      "Huawei private.";
  }
  revision 2020-05-10 {
    description
      "Modify the description.";
    reference
      "Huawei private.";
  }
  revision 2020-03-09 {
    description
      "Modify the description.";
    reference
      "Huawei private.";
  }
  revision 2020-03-03 {
    description
      "Modify the description.";
    reference
      "Huawei private.";
  }
  revision 2020-02-24 {
    description
      "Add end-ass container.";
    reference
      "Huawei private.";
  }
  revision 2020-02-14 {
    description
      "Add path-mtu-compensation leaf.";
    reference
      "Huawei private.";
  }
  revision 2020-02-04 {
    description
      "Add new leaf.";
    reference
      "Huawei private.";
  }
  revision 2020-01-20 {
    description
      "Add path-mtu leaf.";
    reference
      "Huawei private.";
  }
  revision 2019-12-27 {
    description
      "Modify the default value about leaf protocol of end-dt6s.";
    reference
      "Huawei private.";
  }
  revision 2019-11-30 {
    description
      "Add end-dt6s container.";
    reference
      "Huawei private.";
  }
  revision 2019-11-22 {
    description
      "Reconstructing Yang file by yin mechanism.";
    reference
      "Huawei private.";
  }
  revision 2019-04-04 {
    description
      "Initial revision.";
    reference
      "Huawei private.";
  }
  ext:task-name "segr";
  rpc get-available-static-sid {
    description
      "Query a maximum of 10 available SRv6 static SIDs for a specified locator name.";
    input  {
      leaf locator-name {
        type string {
          length "1..31";
        }
        mandatory true;
        description
          "Locator name.";
      }
      leaf begin-value {
        type inet:ipv6-address-no-zone;
        description
          "Start value in the range of available SRv6 static SIDs.";
      }
    }
    output  {
      leaf sid-value1 {
        type inet:ipv6-address-no-zone;
        description
          "The first available SRv6 static SID.";
      }
      leaf sid-value2 {
        type inet:ipv6-address-no-zone;
        description
          "The second available SRv6 static SID.";
      }
      leaf sid-value3 {
        type inet:ipv6-address-no-zone;
        description
          "The third available SRv6 static SID.";
      }
      leaf sid-value4 {
        type inet:ipv6-address-no-zone;
        description
          "The fourth available SRv6 static SID.";
      }
      leaf sid-value5 {
        type inet:ipv6-address-no-zone;
        description
          "The fifth available SRv6 static SID.";
      }
      leaf sid-value6 {
        type inet:ipv6-address-no-zone;
        description
          "The sixth available SRv6 static SID.";
      }
      leaf sid-value7 {
        type inet:ipv6-address-no-zone;
        description
          "The seventh available SRv6 static SID.";
      }
      leaf sid-value8 {
        type inet:ipv6-address-no-zone;
        description
          "The eighth available SRv6 static SID.";
      }
      leaf sid-value9 {
        type inet:ipv6-address-no-zone;
        description
          "The ninth available SRv6 static SID.";
      }
      leaf sid-value10 {
        type inet:ipv6-address-no-zone;
        description
          "The tenth available SRv6 static SID.";
      }
    }
  }
  rpc get-available-local-block {
    description
      "Query available local block sid begin and end value for a specified locator name and reserve range.";
    input  {
      leaf locator-name {
        type string {
          length "1..31";
        }
        mandatory true;
        description
          "Locator name.";
      }
      leaf sid-begin-value {
        type inet:ipv6-address-no-zone;
        description "Begin value of the local block for SRv6 SIDs.";
      }
      leaf sid-reserve-number {
        type uint32 {
          range "1..200000";
        }
        description
          "The total number of available SIDs in SRv6 local block.";
      }
    }
    output  {
      container local-block-ranges {
        description
          "List of the available range of srv6 local block reserved fro BSIDs.";
        list local-block-range {
          key "sid-begin-value sid-end-value";
          description
            "The available range of srv6 local block reserved for BSIDs.";
          leaf sid-begin-value {
            type inet:ipv6-address-no-zone;
            description
              "The begin value of available SRv6 local block SIDs.";
          }
          leaf sid-end-value {
            type inet:ipv6-address-no-zone;
            description
              "The end value of available SRv6 local block SIDs.";
          }
          leaf available-sid-reserve-number {
            type uint32 {
              range "1..200000";
            }
            description
              "The total number of available SIDs in SRv6 local block.";
          }
        }
      }
    }
  }
  augment /ni:network-instance/ni:instances/ni:instance {
    description
        "Segment routing IPv6 augment to L3VPN.";
    container srv6 {
      when "../ni:name='_public_'";
      description
        "Configure segment routing IPv6.";
      leaf enable {
        type boolean;
        default "false";
        description
          "Enable/disable segment routing IPv6.";
      }
      leaf te-frr-enable {
        type boolean;
        must "../te-frr-enable='false' or ../enable='true'";
        default "false";
        description
          "Enable/disable SR TE FRR.";
      }
      leaf te-frr-enable-downgrade {
        when "../te-frr-enable='true'";
        type boolean;
        default "false";
        description
          "Enable/disable fast re-route mode.";
      }
      leaf te-frr-verify-trusted-domain {
        type boolean;
        must "../te-frr-verify-trusted-domain='false' or ((../enable='true') and count(../trusted-domains/trusted-domain-destinations/trusted-domain-destination)>0)";
        default "false";
        description
          "Enable/disable SRv6 TE FRR with trusted domain verification.";
      }
      leaf end-x-delay-time {
        when "../enable='true'";
        type uint32 {
          range "0..600000";
        }
        units "ms";
        default "0";
        description
          "End.X delay time.";
      }
      leaf te-frr-delay-time {
        when "../enable='true'";
        type uint32 {
          range "1..600000";
        }
        units "ms";
        description
          "TE FRR delay time.";
      }
      leaf path-mtu {
        when "../enable='true'";
        type uint32 {
          range "1280..9600";
        }
        must "(../path-mtu-reserved and (../path-mtu)-(../path-mtu-reserved)>=1280) or not(../path-mtu-reserved)";
        default "9600";
        description
          "Path MTU value.";
      }
      leaf path-mtu-reserved {
        when "../enable='true'";
        type uint32 {
          range "1..9600";
        }
        must "(../path-mtu)-(../path-mtu-reserved)>=1280";
        description
          "Path MTU reserved value.";
      }
      leaf proxy-peer-sid {
        when "../enable='true'";
        type inet:ipv6-address-no-zone;
        description
          "Peer SID of SFC for anycast.";
      }
      leaf reduce-srh-enable {
        when "../enable='true'";
        type boolean;
        default "false";
        description
          "Enable/disable reduce SRH.";
      }
      leaf local-end-x-encapsulation {
        when "../enable='true'";
        type boolean;
        default "false";
        description
          "Enable/disable local End.X SID encapsulation.";
      }
      leaf compress-16-mode {
        when "../enable='true'";
        type compress-16-mode-type;
        description
          "Configure the SRv6 compress-16 mode.";
      }
      leaf protected-end-x-delete-delay {
        when "../enable='true'";
        type uint32 {
          range "30..1800";
        }
        units "s";
        default "900";
        description
          "Protected End.X delete delay time.";
      }
      container csid-proportion{
        when "../enable='true'";
        description
          "Configure the proportion of compressed SIDs.";
        leaf global-id-block {
          type uint8 {
            range "1..255";
          }
          must "(../space=4 and ../global-id-block<16) or (../space=5 and ../global-id-block<32) or (../space=6 and ../global-id-block<64) or (../space=7 and ../global-id-block<128) or (../space=8)";
          default "14";
          description
            "Ratio of GIBs in compressed SIDs.";
        }
        leaf space {
          type uint8 {
            range "4..8";
          }
          default "4";
          description
            "Configure the proportion space of compressed SIDs.";
        }
      }
      container bfd {
        when "../enable='true'";
        description
          "Configure SRv6 locator BFD parameters.";
        leaf sbfd-enable {
          type boolean;
          default "false";
          description
            "Enable/disable seamless BFD on all locators.";
        }
        leaf min-tx {
          type uint32 {
            range "3..20000";
          }
          units "ms";
          description
            "Set the minimum interval at which BFD packets are sent.";
          ext:dynamic-default;
        }
        leaf min-rx {
          type uint32 {
            range "3..20000";
          }
          units "ms";
          description
            "Set the minimum interval at which BFD packets are received.";
          ext:dynamic-default;
        }
        leaf detect-multiplier {
          type uint32 {
            range "3..50";
          }
          default "3";
          description
            "Set the detection multiplier of a BFD session.";
        }
        leaf ipv6-prefix {
          when "../sbfd-enable='true'";
          type leafref {
            path "/rtp:routing-policy/rtp:ipv6-prefix-filters/rtp:ipv6-prefix-filter/rtp:name";
          }
          description
            "Set the name of an IPv6 prefix list.";
        }
      }
      container encapsulation {
        when "../enable='true'";
        description
          "Configure IPv6 encapsulation configuration.";
        choice mode{
          description
            "Configure the SRv6 encapsulation model.";
          case address {
            description
              "Source address mode.";
            leaf source-address {
              type inet:ipv6-address-no-zone;
              description
                "SRv6 VPN encapsulation source address.";
            }
          }
          case interface {
            description
              "Source interface mode.";
            leaf source-interface {
              type leafref {
                path "/ifm:ifm/ifm:interfaces/ifm:interface/ifm:name";
              }
              must "/ifm:ifm/ifm:interfaces/ifm:interface[ifm:name=current()]/ifm:type='LoopBack'";
              description
                "This interface is specified as the interface for SRv6 source address encapsulation.";
            }
          }
        }
        leaf hop-limit {
          when "../source-address or ../source-interface";
          type uint8 {
            range "1..255";
          }
          default "255";
          description
            "Encapsulation IPv6 header TTL value.";
        }
      }
      container trusted-domains {
        when "../enable='true'";
        presence "TE FRR trusted domain view.";
        description
          "Configure SRv6 TE FRR trusted domains.";
        container trusted-domain-destinations {
          description
            "List of SRv6 TE FRR trusted domain destinations.";
          list trusted-domain-destination {
            key "destination mask-length";
            max-elements "1024";
            description
              "Configure SRv6 TE FRR trusted domain.";
            leaf destination {
              type inet:ipv6-address-no-zone;
              description
                "Destination IPv6 prefix.";
            }
            leaf mask-length {
              type uint8 {
                range "1..128";
              }
              description
                "Destination mask length.";
            }
          }
        }
      }
      container locators {
        when "../enable='true'";
        description
          "List of SRv6 locator configuration.";
        list locator {
          key "name";
          unique "prefix";
          description
            "Configure SRv6 locator configuration.";
          leaf name {
            type string {
              length "1..31";
            }
            description
              "Locator name.";
          }
          leaf prefix {
            ext:operation-exclude update;
            type inet:ipv6-address-no-zone;
            mandatory true;
            description
              "IPv6 prefix.";
          }
          leaf prefix-length {
            ext:operation-exclude update;
            type uint8 {
              range "32..120";
            }
            must "../prefix-length+../static-length+../args-length<=128";
            mandatory true;
            description
              "Mask length. The maximum sum value of the mask length, static segment length, and argument segment length is 128.";
          }
          leaf static-length {
            ext:operation-exclude update;
            type uint8 {
              range "0..96";
            }
            must "../prefix-length+../static-length+../args-length<=128";
            default "0";
            description
              "The static segment length determines the range of opcode. The maximum sum value of the mask length, static segment length, and argument segment length is 128.";
          }
          leaf args-length {
            ext:operation-exclude update;
            type uint8 {
              range "0..64";
            }
            must "../prefix-length+../static-length+../args-length<=128";
            default "0";
            description
              "Argument segment length. The maximum sum value of the mask length, static segment length, and argument segment length is 128.";
          }
          choice compress-mode {
            description
              "Configure compress mode.";
            case compress-block-length {
              description
                "The compression type is 32-bit compression.";
              leaf compress-block-length {
                ext:operation-exclude update;
                type uint8 {
                  range "1..88";
                }
                must "((../compress-block-length mod 4)=0) and (../compress-block-length>=4) and (../compress-block-length<=128) and (../prefix-length - ../compress-block-length>=1) and (../prefix-length - ../compress-block-length<=31)";
                description
                  "Block segment length. The block segment length is within the range of prefix length.";
              }
            }
            case compress-16 {
              description
                "The compression type is 16-bit compression.";
              leaf compress-16 {
                ext:operation-exclude update;
                type empty;
                must "((../prefix-length mod 4)=0) and (../prefix-length<=92) and ../../../compress-16-mode" ;
                description
                  "The compression type is 16-bit compression, the node segment length is 16.";
              }
            }
          }
          leaf compress-static-length {
            when "../compress-block-length or ../compress-16";
            type uint8 {
              range "1..32";
            }
            must "../compress-block-length and (../compress-static-length<=32 - (../prefix-length - ../compress-block-length)) or ../compress-16 and ../compress-static-length<=16";
            description
              "Compress static segment length. The compress static segment length is within the range of compress length.";
          }
          leaf flex-algo {
            ext:operation-exclude update|delete;
            type uint8 {
              range "0|128..255";
            }
            default "0";
            description
              "Flexible algorithm.";
          }
          container preference {
            presence "The preference for the locator.";
            description
              "Configure the locator preference.";
              leaf value {
                type uint8 {
                  range "1..255";
                }
                mandatory "true";
                description
                  "The locator preference value.";
              }
          }
          container srv6lbs {
            description
              "List of segment routing IPv6 local blocks reserved for BSIDs.";
            list srv6lb {
              key "index";
              max-elements  "1";
              description
                "Configure segment routing IPv6 local block reserved for BSIDs. Currently only one configuration is supported.";
              leaf index {
                type uint32;
                description
                  "The identifier of a segment routing IPv6 local block.";
              }
              leaf begin-value {
                type inet:ipv6-address-no-zone;
                description
                  "Begin value of the local block for SRv6 SIDs.";
              }
              leaf sid-reserve-number {
                type uint32 {
                  range "1..200000";
                }
                mandatory true;
                description
                  "The number of SIDs reserved for BSIDs in local block.";
              }
            }
          }
          container opcodes {
            description
              "Configure SRv6 opcodes configuration.";
            container ends {
              description
                "List of End type opcode configuration.";
              list end {
                must "../../../static-length>0 or ../../../compress-static-length>0";
                key "value";
                max-elements  "1";
                description
                  "Configure End type opcode configuration.";
                leaf value {
                  type inet:ipv6-address-no-zone;
                  description
                    "Opcode value. The opcode range is dynamically calculated based on the locator configuration.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
              }
            }
            container end-psps {
              description
                "List of End psp type opcode configuration.";
              list end-psp {
                must "../../../static-length>0 or ../../../compress-static-length>0";
                key "value";
                max-elements  "1";
                description
                  "Configure End psp type opcode configuration.";
                leaf value {
                  type inet:ipv6-address-no-zone;
                  description
                    "Opcode value. The opcode range is dynamically calculated based on the locator configuration.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
              }
            }
            container end-psp-usp-usds {
              description
                "List of End psp-usp-usd type opcode configuration.";
              list end-psp-usp-usd {
                must "../../../static-length>0 or ../../../compress-static-length>0";
                key "value";
                max-elements  "1";
                description
                  "Configure End psp-usp-usd type opcode configuration.";
                leaf value {
                  type inet:ipv6-address-no-zone;
                  description
                    "Opcode value. The opcode range is dynamically calculated based on the locator configuration.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
              }
            }
            container end-psp-usp-usd-cocs {
              description
                "List of End psp-usp-usd-coc type opcode configuration.";
              list end-psp-usp-usd-coc {
                must "../../../compress-static-length>0";
                key "value";
                max-elements  "1";
                description
                  "Configure End psp-usp-usd-coc type opcode configuration.";
                leaf value {
                  type inet:ipv6-address-no-zone;
                  description
                    "Opcode value. The opcode range is dynamically calculated based on the locator configuration.";
                }
              }
            }
            container end-cocs {
              description
                "List of End coc type opcode configuration.";
              list end-coc {
                must "../../../compress-static-length>0";
                key "value";
                max-elements  "1";
                description
                  "Configure End coc type opcode configuration.";
                leaf value {
                  type inet:ipv6-address-no-zone;
                  description
                    "Opcode value. The opcode range is dynamically calculated based on the locator configuration.";
                }
              }
            }
            container end-psp-cocs {
              description
                "List of End psp-coc type opcode configuration.";
              list end-psp-coc {
                must "../../../compress-static-length>0";
                key "value";
                max-elements  "1";
                description
                  "Configure End psp-coc type opcode configuration.";
                leaf value {
                  type inet:ipv6-address-no-zone;
                  description
                    "Opcode value. The opcode range is dynamically calculated based on the locator configuration.";
                }
              }
            }
            container end-ops {
              description
                "List of End.OP type opcode configuration.";
              list end-op {
                must "../../../static-length>0";
                key "value";
                max-elements  "1";
                description
                  "Configure End.OP type opcode configuration.";
                leaf value {
                  type inet:ipv6-address-no-zone;
                  description
                    "Opcode value. The opcode range is dynamically calculated based on the locator configuration.";
                }
              }
            }
            container end-xs {
              description
                "List of End.X type opcode configuration.";
              list end-x {
                must "../../../static-length>0 or ../../../compress-static-length>0";
                key "value if-name next-hop";
                unique "if-name next-hop s-flag";
                description
                  "Configure End.X type opcode configuration.";
                leaf value {
                  type inet:ipv6-address-no-zone;
                  must "(../s-flag = 'false' and count(../../end-x[value=current()]) = 1) or (../s-flag='true' and not(../../end-x[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "Nexthop address.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
                leaf s-flag {
                  type boolean;
                  default "false";
                  description
                    "Enable/disable the ability to associate an Opcode value with a set of adjacencies."; 
                }
                leaf protected {
                  type boolean;
                  must "../protected = 'false' or ../../../../flex-algo = 0";
                  default "false";
                  description
                    "Enable/disable protected End.X.";
                }
              }
            }
            container end-x-psps {
              description
                "List of End.X psp type opcode configuration.";
              list end-x-psp {
                must "../../../static-length>0 or ../../../compress-static-length>0";
                key "value if-name next-hop";
                unique "if-name next-hop s-flag";
                description
                  "Configure End.X psp type opcode configuration.";
                leaf value {
                  type inet:ipv6-address-no-zone;
                  must "(../s-flag = 'false' and count(../../end-x-psp[value=current()]) = 1) or (../s-flag='true' and not(../../end-x-psp[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "NextHop address.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-x-psp-usp-usds {
              description
                "List of End.X psp-usp-usd type opcode configuration.";
              list end-x-psp-usp-usd {
                must "../../../static-length>0 or ../../../compress-static-length>0";
                key "value if-name next-hop";
                unique "if-name next-hop s-flag";
                description
                  "Configure End.X psp-usp-usd type opcode configuration.";
                leaf value {
                  type inet:ipv6-address-no-zone;
                  must "(../s-flag = 'false' and count(../../end-x-psp-usp-usd[value=current()]) = 1) or (../s-flag='true' and not(../../end-x-psp-usp-usd[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "NextHop address.";
                }
                leaf compress {
                  ext:operation-exclude update|delete;
                  type boolean;
                  must "(../compress = 'true' and (../../../../compress-block-length>0 or ../../../../compress-16) and (../../../../compress-static-length>0)) or ../compress = 'false'";
                  default "false";
                  description
                    "Enable/disable compress function.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-x-psp-usp-usd-cocs {
              description
                "List of End.X psp-usp-usd-coc type opcode configuration.";
              list end-x-psp-usp-usd-coc {
                must "../../../compress-static-length>0";
                key "value if-name next-hop";
                unique "if-name next-hop s-flag";
                description
                  "Configure End.X psp-usp-usd-coc type opcode configuration.";
                leaf value {
                  type inet:ipv6-address-no-zone;
                  must "(../s-flag = 'false' and count(../../end-x-psp-usp-usd-coc[value=current()]) = 1) or (../s-flag='true' and not(../../end-x-psp-usp-usd-coc[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "NextHop address.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-x-cocs {
              description
                "List of End.X coc type opcode configuration.";
              list end-x-coc {
                must "../../../compress-static-length>0";
                key "value if-name next-hop";
                unique "value";
                unique "if-name next-hop s-flag";
                description
                  "Configure End.X coc type opcode configuration.";
                leaf value {
                  type inet:ipv6-address-no-zone;
                  must "(../s-flag = 'false' and count(../../end-x-coc[value=current()]) = 1) or (../s-flag='true' and not(../../end-x-coc[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "NextHop address.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-x-psp-cocs {
              description
                "List of End.X psp-coc type opcode configuration.";
              list end-x-psp-coc {
                must "../../../compress-static-length>0";
                key "value if-name next-hop";
                unique "value";
                unique "if-name next-hop s-flag";
                description
                  "Configure End.X psp-coc type opcode configuration.";
                leaf value {
                  type inet:ipv6-address-no-zone;
                  must "(../s-flag = 'false' and count(../../end-x-psp-coc[value=current()]) = 1) or (../s-flag='true' and not(../../end-x-psp-coc[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "NextHop address.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-dt2us {
              description
                "List of End.DT2U type opcode configuration.";
              list end-dt2u {
                must "../../../static-length>0 or ../../../compress-static-length>0";
                key "value";
                unique "bd-id";
                description
                  "Configure End.DT2U type opcode configuration.";
                leaf value {
                  type inet:ipv6-address-no-zone;
                  description
                    "Opcode value. The opcode range is dynamically calculated based on the locator configuration.";
                }
                leaf bd-id {
                  ext:operation-exclude update;
                  ext:support-filter "true";
                  type leafref {
                    path "/bd:bd/bd:instances/bd:instance/bd:id";
                  }
                  mandatory "true";
                  description
                    "Bridge domain ID.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-dt2uls {
              description
                "List of End.DT2UL type opcode configuration.";
              list end-dt2ul {
                must "../../../static-length>0";
                key "value";
                unique "bd-id";
                description
                  "Configure End.DT2UL type opcode configuration.";
                leaf value {
                  type inet:ipv6-address-no-zone;
                  description
                    "Opcode value. The opcode range is dynamically calculated based on the locator configuration.";
                }
                leaf bd-id {
                  ext:operation-exclude update;
                  ext:support-filter "true";
                  type leafref {
                    path "/bd:bd/bd:instances/bd:instance/bd:id";
                  }
                  mandatory "true";
                  description
                    "Bridge domain ID.";
                }
              }
            }
            container end-dt2ms {
              description
                "List of End.DT2M type opcode configuration.";
              list end-dt2m {
                must "../../../static-length>0 or ../../../compress-static-length>0";
                key "value";
                unique "bd-id";
                description
                  "Configure End.DT2M type opcode configuration.";
                leaf value {
                  type inet:ipv6-address-no-zone;
                  description
                    "Opcode value. The opcode range is dynamically calculated based on the locator configuration.";
                }
                leaf bd-id {
                  ext:operation-exclude update;
                  ext:support-filter "true";
                  type leafref {
                    path "/bd:bd/bd:instances/bd:instance/bd:id";
                  }
                  mandatory "true";
                  description
                    "Bridge domain ID.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0) and (../../../../args-length<=16))";
                  default "false";
                  description
                    "Enable/disable compress function.";
                }
              }
            }
            container end-dx2s {
              description
                "List of End.DX2 type opcode configuration.";
              list end-dx2 {
                must "../../../static-length>0 or ../../../compress-static-length>0";
                key "value";
                unique "evpl-id";
                description
                  "Configure End.DX2 type opcode configuration.";
                leaf value {
                  type inet:ipv6-address-no-zone;
                  description
                    "Opcode value. The opcode range is dynamically calculated based on the locator configuration.";
                }
                leaf evpl-id {
                  ext:operation-exclude update;
                  type leafref {
                    path "/evpl:evpl/evpl:instances/evpl:instance/evpl:id";
                  }
                  must "((/evpl:evpl/evpl:instances/evpl:instance[evpl:id=current()]/evpl:mode='mpls-mode') or (/evpl:evpl/evpl:instances/evpl:instance[evpl:id=current()]/evpl:mode='srv6-mode') or (/evpl:evpl/evpl:instances/evpl:instance[evpl:id=current()]/evpl:mode='none') or (/evpl:evpl/evpl:instances/evpl:instance[evpl:id=current()]/evpl:mode='static-mode'))";
                  mandatory "true";
                  description
                    "EVPL instance ID.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-dx2ls {
              description
                "List of End.DX2L type opcode configuration.";
              list end-dx2l {
                must "../../../static-length>0";
                key "value";
                unique "evpl-id";
                description
                  "Configure End.DX2L type opcode configuration.";
                leaf value {
                  type inet:ipv6-address-no-zone;
                  description
                    "Opcode value. The opcode range is dynamically calculated based on the locator configuration.";
                }
                leaf evpl-id {
                  ext:operation-exclude update;
                  type leafref {
                    path "/evpl:evpl/evpl:instances/evpl:instance/evpl:id";
                  }
                  must "((/evpl:evpl/evpl:instances/evpl:instance[evpl:id=current()]/evpl:mode='mpls-mode') or (/evpl:evpl/evpl:instances/evpl:instance[evpl:id=current()]/evpl:mode='srv6-mode') or (/evpl:evpl/evpl:instances/evpl:instance[evpl:id=current()]/evpl:mode='none') or (/evpl:evpl/evpl:instances/evpl:instance[evpl:id=current()]/evpl:mode='static-mode'))";
                  mandatory "true";
                  description
                    "EVPL instance ID.";
                }
              }
            }
            container end-dt4s {
              description
                "List of End.DT4 type opcode configuration.";
              list end-dt4 {
                must "../../../static-length>0 or ../../../compress-static-length>0";
                must "not(count(../end-dt4[protocol='evpn-l3vpn'][vpn-name=current()/vpn-name]) != 0 and count(../end-dt4[protocol!='evpn-l3vpn'][vpn-name=current()/vpn-name]) != 0)";
                key "value";
                unique "vpn-name protocol";
                description
                  "Configure End.DT4 type opcode configuration.";
                leaf value {
                  type inet:ipv6-address-no-zone;
                  description
                    "Opcode value. The opcode range is dynamically calculated based on the locator configuration.";
                }
                leaf vpn-name {
                  ext:operation-exclude update;
                  type leafref {
                    path "/ni:network-instance/ni:instances/ni:instance/ni:name";
                  }
                  default "_public_";
                  description
                    "VPN name.";
                }
                leaf protocol {
                  type protocol-type;
                  must "not(../vpn-name='_public_' and (../protocol='evpn' or ../protocol='evpn-l3vpn'))";
                  default "l3vpn";
                  description
                    "Protocol type.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-dt6s {
              description
                "List of End.DT6 type opcode configuration.";
              list end-dt6 {
                must "../../../static-length>0 or ../../../compress-static-length>0";
                must "not(count(../end-dt6[protocol='evpn-l3vpn'][vpn-name=current()/vpn-name]) != 0 and count(../end-dt6[protocol!='evpn-l3vpn'][vpn-name=current()/vpn-name]) != 0)";
                key "value";
                unique "vpn-name protocol";
                description
                  "Configure End.DT6 type opcode configuration.";
                leaf value {
                  type inet:ipv6-address-no-zone;
                  description
                    "Opcode value. The opcode range is dynamically calculated based on the locator configuration.";
                }
                leaf vpn-name {
                  ext:operation-exclude update;
                  type leafref {
                    path "/ni:network-instance/ni:instances/ni:instance/ni:name";
                  }
                  default "_public_";
                  description
                    "VPN name.";
                }
                leaf protocol {
                  type protocol-type;
                  must "not(../vpn-name='_public_' and (../protocol='evpn' or ../protocol='evpn-l3vpn'))";
                  default "l3vpn";
                  description
                    "Protocol type.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-dt46s {
              description
                "List of End.DT46 type opcode configuration.";
              list end-dt46 {
                must "../../../static-length>0 or ../../../compress-static-length>0";
                key "value";
                unique "vpn-name";
                description
                  "Configure End.DT46 type opcode configuration.";
                leaf value {
                  type inet:ipv6-address-no-zone;
                  description
                    "Opcode value. The opcode range is dynamically calculated based on the locator configuration.";
                }
                leaf vpn-name {
                  type leafref {
                    path "/ni:network-instance/ni:instances/ni:instance/ni:name";
                  }
                  default "_public_";
                  description
                    "VPN name.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-ms {
              description
                "List of End.M type opcode configuration.";
              list end-m {
                must "../../../static-length>0 and ../../../flex-algo=0";
                key "value mirror-prefix mirror-mask";
                description
                  "Configure End.M type opcode configuration.";
                leaf value {
                  type inet:ipv6-address-no-zone;
                  description
                    "Opcode value. The opcode range is dynamically calculated based on the locator configuration.";
                }
                leaf mirror-prefix {
                  type inet:ipv6-address-no-zone;
                  description
                    "Mirror locator prefix.";
                }
                leaf mirror-mask {
                  type uint8 {
                    range "32..120";
                  }
                  description
                  "Mirror locator mask.";
                }
              }
            }
            container end-dx4s {
              description
                "List of End.DX4 type opcode configuration.";
              list end-dx4 {
                must "../../../static-length>0 or ../../../compress-static-length>0";
                key "value vpn-name if-name next-hop";
                description
                  "Configure End.DX4 type opcode configuration.";
                leaf value {
                  type inet:ipv6-address-no-zone;
                  description
                    "Opcode value. The opcode range is dynamically calculated based on the locator configuration.";
                }
                leaf vpn-name {
                  type leafref {
                    path "/ni:network-instance/ni:instances/ni:instance/ni:name";
                  }
                  description
                    "VPN name.";
                }
                leaf if-name {
                  type leafref {
                    path "/ifm:ifm/ifm:interfaces/ifm:interface/ifm:name";
                  }
                  description
                    "Interface name. Only support physical port.";
                }
                leaf next-hop {
                  type inet:ipv4-address-no-zone;
                  description
                    "NextHop address.";
                }
                leaf protocol {
                  type protocol-type-dx4;
                  mandatory true;
                  description
                    "Protocol type.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-dx6s {
              description
                "List of End.DX6 type opcode configuration.";
              list end-dx6 {
                must "../../../static-length>0 or ../../../compress-static-length>0";
                key "value vpn-name if-name next-hop";
                description
                  "Configure End.DX6 type opcode configuration.";
                leaf value {
                  type inet:ipv6-address-no-zone;
                  description
                    "Opcode value. The opcode range is dynamically calculated based on the locator configuration.";
                }
                leaf vpn-name {
                  type leafref {
                    path "/ni:network-instance/ni:instances/ni:instance/ni:name";
                  }
                  must "../vpn-name!='_public_'";
                  description
                    "VPN name.";
                }
                leaf if-name {
                  type leafref {
                    path "/ifm:ifm/ifm:interfaces/ifm:interface/ifm:name";
                  }
                  description
                    "Interface name. Only support physical port.";
                }
                leaf next-hop {
                  type inet:ipv6-address-no-zone;
                  description
                    "Nexthop address.";
                }
                leaf protocol {
                  type protocol-type-dx6;
                  mandatory true;
                  description
                    "Protocol type.";
                }
                leaf behavior {
                  type behavior-type;
                  must "(../compress='false' and ../behavior='no-flavor') or (../compress='true' and (../behavior='next' or (../behavior='coc-next' and ../../../../../../compress-16-mode='default')))";
                  default "no-flavor";
                  description
                    "Behaviors.";
                }
                leaf compress {
                  ext:operation-exclude update;
                  type boolean;
                  must "../compress='false' or (../compress='true' and ../../../../compress-16 and (../../../../compress-static-length>0))";
                  default "false";
                  description
                    "Enable/disable compress function.";
                }
              }
            }
            container end-ass {
              description
                "List of End.AS type opcode.";
              list end-as {
                must "../../../static-length>0";
                must "(service-class and color) or (not(service-class) and not(color))";
                key "value";
                description
                  "Configure End.AS type opcode.";
                leaf value {
                  type inet:ipv6-address-no-zone;
                  description
                    "Opcode value. The opcode range is dynamically calculated based on the locator configuration.";
                }
                leaf backup-value {
                  type inet:ipv6-address-no-zone;
                  description
                    "Backup proxy SID function opcode value. The opcode range is dynamically calculated based on the locator configuration.";
                }
                leaf inner-type {
                  type inner-type;
                  default "null";
                  description
                    "Inner packet type.";
                }
                leaf bypass-enable {
                  type boolean;
                  default "false";
                  description
                    "Enable/disable bypass function of SFC.";
                }
                leaf bypass-sid {
                  when "../bypass-enable='true'";
                  type inet:ipv6-address-no-zone;
                  description
                    "Bypass SID, that must be a valid SID of other protection device in the SF group.";
                }
                choice service-mode {
                  default "uniform";
                  description
                    "Configure differenciated service mode.";
                  case pipe {
                    description
                     "Pipe mode.";
                    leaf service-class {
                      type service-class;
                      description
                       "Class of service.";
                    }
                    leaf color {
                      type color;
                      description
                        "Packet color.";
                    }
                  }
                  case uniform {
                    description
                      "Uniform mode.";
                    leaf diffserv-uniform {
                      type empty;
                      description
                        "Uniform mode.";
                    }
                  }
                }
                choice ttl-mode {
                  default "uniform";
                  description
                    "Configure TTL mode.";
                  case pipe {
                    description
                     "Pipe mode.";  
                    leaf ttl-value {
                      type uint8 {
                        range "1..255";
                      }
                      description
                       "TTL value.";
                    }
                  }
                  case uniform {
                    description
                      "Uniform mode.";
                    leaf ttl-uniform {
                      type empty;
                      description
                        "Uniform mode.";
                    }
                  }
                }
                leaf forward-no-bypass {
                  type boolean;
                  default "false";
                  description
                    "Enable/disable the function that traffic is not forwarded over the local protection path.";
                }
                container l2-fwds {
                  description
                    "List of encapsulation for layer 2 packet forwarding.";
                  list l2-fwd {
                    key "out-ifname in-ifname out-vlan in-vlan out-ce-vlan in-ce-vlan";
                    max-elements "1";
                    description
                      "Configure encapsulation for layer 2 packet forwarding.";
                    leaf out-ifname {
                      type leafref {
                        path "/ifm:ifm/ifm:interfaces/ifm:interface/ifm:name";
                      }
                      must "/ifm:ifm/ifm:interfaces/ifm:interface[ifm:name=current()]/ifm:l2-mode-enable='true'";
                      description
                        "Outbound interface from SFF to SF, this interface must be exclusively used by SFC.";
                    }
                    leaf in-ifname {
                      type leafref {
                        path "/ifm:ifm/ifm:interfaces/ifm:interface/ifm:name";
                      }
                      must "/ifm:ifm/ifm:interfaces/ifm:interface[ifm:name=current()]/ifm:l2-mode-enable='true'";
                      description
                        "Inbound interface from SF to SFF, this interface must be exclusively used by SFC.";
                    }
                    leaf out-vlan {
                      type uint32 {
                        range "0..4094";
                        ext:value-meaning {
                          ext:item 0 {
                            ext:meaning "no-set";
                            description "Value 0 means that the VLAN ID is not set.";
                          }
                        }
                      }
                      description
                        "Outer VLAN ID of the outbound interface from SFF to SF.";
                    }
                    leaf in-vlan {
                      type uint32 {
                        range "0..4094";
                        ext:value-meaning {
                          ext:item 0 {
                            ext:meaning "no-set";
                            description "Value 0 means that the VLAN ID is not set.";
                          }
                        }
                      }
                      description
                        "Outer VLAN ID of the inbound interface from SF to SFF.";
                    }
                    leaf out-ce-vlan {
                      type uint32 {
                        range "0..4094";
                        ext:value-meaning {
                          ext:item 0 {
                            ext:meaning "no-set";
                            description "Value 0 means that the VLAN ID is not set.";
                          }
                        }
                      }
                      must "../out-vlan!=0";
                      description
                        "Inner VLAN ID of the outbound interface from SFF to SF.";
                    }
                    leaf in-ce-vlan {
                      type uint32 {
                        range "0..4094";
                        ext:value-meaning {
                          ext:item 0 {
                            ext:meaning "no-set";
                            description "Value 0 means that the VLAN ID is not set.";
                          }
                        }
                      }
                      must "../in-vlan!=0";
                      description
                        "Inner VLAN ID of the inbound interface from SF to SFF.";
                    }
                    leaf dest-mac {
                      type pub-type:mac-address;
                      description
                        "MAC address of destination for the inbound interface, that is H-H-H.";
                    }
                  }
                }
                container l3-fwds {
                  description
                    "List of encapsulation for layer 3 packet forwarding.";
                  list l3-fwd {
                    key "next-hop in-ifname out-ifname";
                    description
                      "Configure encapsulation for layer 3 packet forwarding.";
                    leaf next-hop {
                      type inet:ipv4-address-no-zone;
                      description
                        "IPv4 next hop address.";
                    }
                    leaf in-ifname {
                      type leafref {
                        path "/ifm:ifm/ifm:interfaces/ifm:interface/ifm:name";
                      }
                      must "/ifm:ifm/ifm:interfaces/ifm:interface[ifm:name=current()]/ifm:type='Vbdif' or (/ifm:ifm/ifm:interfaces/ifm:interface[ifm:name=current()]/ifm:class='sub-interface' and not(/ifm:ifm/ifm:interfaces/ifm:interface[ifm:name=current()]/ifm:l2-mode-enable='true'))";
                      description
                        "Inbound interface from SF to SFF, this interface must be exclusively used by SFC.";
                    }
                    leaf out-ifname {
                      type leafref {
                        path "/ifm:ifm/ifm:interfaces/ifm:interface/ifm:name";
                      }
                      must "/ifm:ifm/ifm:interfaces/ifm:interface[ifm:name=current()]/ifm:type='Vbdif' or (/ifm:ifm/ifm:interfaces/ifm:interface[ifm:name=current()]/ifm:class='sub-interface' and not(/ifm:ifm/ifm:interfaces/ifm:interface[ifm:name=current()]/ifm:l2-mode-enable='true'))";
                      description
                        "Outbound interface from SFF to SF, this interface must be exclusively used by SFC.";
                    }
                    leaf symmetric-index {
                      type uint32 {
                        range "1..4294967295";
                      }
                      description
                        "Symmetric index for the forward and reverse traffic on the same VM.";
                    }
                  }
                }
                container cache {
                  description
                    "Configure SR information to be attached on the traffic coming back from SF.";
                  leaf source-address {
                    type inet:ipv6-address-no-zone;
                    description
                      "IPv6 source address that encapsulated on the traffic coming back from SF.";
                  }
                  leaf sl-num {
                    type uint32 {
                      range "0..10";
                    }
                    config false;
                    description
                      "Number of route segments remaining.";
                  }
                  container ipv6addrs {
                    description
                      "List of IPv6 address for encapsulating on the traffic coming back from SF. The local End.AS SID must be in the address list except the first address.";
                    list ipv6addr {
                      key "ipv6-address";
                      max-elements 11;
                      ordered-by user;
                      description
                        "Configure the IPv6 address for encapsulating on the traffic coming back from SF.";
                      leaf ipv6-address {
                        type inet:ipv6-address-no-zone;
                        description
                          "Configure the IPv6 address for encapsulating on the traffic coming back from SF.";
                      }
                    }
                  }
                }
              }
            }
            container end-extensions {
              description
                "List of End type opcode configuration.";
              list end-extension {
                must "../../../compress-static-length>0";
                key "value";
                unique "behavior";
                description
                  "Configure End type opcode configuration.";
                leaf value {
                  type inet:ipv6-address-no-zone;
                  description
                    "Opcode value. The opcode range is dynamically calculated based on the locator configuration.";
                }
                leaf behavior {
                  type behavior-type;
                  must "(../../../../compress-16 and (../../../../../../compress-16-mode='default' and (../behavior='psp-usd-next'))) or (../behavior='usp-usd')";
                  mandatory "true";
                  description
                    "Behaviors.";
                }
              }
            }
            container end-uncompressed-extensions {
              description
                "List of uncompressed End type opcode configuration.";
              list end-uncompressed-extension {
                must "../../../static-length>0";
                must "not(../../end-extensions/end-extension[behavior=current()/behavior])";
                key "value";
                unique "behavior";
                description
                  "Configure uncompressed End type opcode.";
                leaf value {
                  type inet:ipv6-address-no-zone;
                  description
                    "Opcode value. The opcode range is dynamically calculated based on the locator configuration.";
                }
                leaf behavior {
                  type behavior-type;
                  must "../behavior='usp-usd'";
                  mandatory "true";
                  description
                    "Behaviors.";
                }
              }
            }
            container end-x-extensions {
              description
                "List of End.X type opcode configuration.";
              list end-x-extension {
                must "../../../compress-static-length>0";
                key "value if-name next-hop";
                unique "behavior if-name next-hop s-flag";
                description
                  "Configure End.X type opcode configuration.";
                leaf value {
                  type inet:ipv6-address-no-zone;
                  must "(../s-flag = 'false' and count(../../end-x-extension[value=current()]) = 1) or (../s-flag = 'true' and not(../../end-x-extension[value = current()][behavior != current()/../behavior]) and not(../../end-x-extension[value = current()][protected != current()/../protected]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "Nexthop address.";
                }
                leaf behavior {
                  type behavior-type;
                  must "(../../../../compress-16 and (../behavior='psp-usd-next' or (../../../../../../compress-16-mode='default' and (../behavior='psp-usp-usd-coc-next')))) or (../behavior='usp-usd')";
                  mandatory "true";
                  description
                    "Behaviors.";
                }
                leaf s-flag {
                  type boolean;
                  default "false";
                  description
                    "Enable/disable the ability to associate an Opcode value with a set of adjacencies.";
                }
                leaf protected {
                  type boolean;
                  must "../protected = 'false' or ../../../../flex-algo = 0";
                  default "false";
                  description
                    "Enable/disable protected End.X.";
                }
              }
            }
            container end-x-uncompressed-extensions {
              description
                "List of uncompressed End.X type opcode configuration.";
              list end-x-uncompressed-extension {
                must "../../../static-length>0";
                must "not(../../end-x-extensions/end-x-extension[behavior=current()/behavior][if-name=current()/if-name][next-hop=current()/next-hop][s-flag=current()/s-flag])";
                key "value if-name next-hop";
                unique "behavior if-name next-hop s-flag";
                description
                  "Configure uncompressed End.X type opcode.";
                leaf value {
                  type inet:ipv6-address-no-zone;
                  must "(../s-flag = 'false' and count(../../end-x-uncompressed-extension[value=current()])=1) or (../s-flag = 'true' and not(../../end-x-uncompressed-extension[value = current()][behavior != current()/../behavior]))";
                  description
                    "Opcode value. The opcode range is dynamically calculated based on the locator configuration.";
                }
                leaf if-name {
                  type leafref {
                    path "/ifm:ifm/ifm:interfaces/ifm:interface/ifm:name";
                  }
                  description
                    "Interface name.";
                }
                leaf next-hop {
                  type inet:ipv6-address-no-zone;
                  description
                    "Nexthop address.";
                }
                leaf behavior {
                  type behavior-type;
                  must "../behavior='usp-usd'";
                  mandatory "true";
                  description
                    "Behaviors.";
                }
                leaf s-flag {
                  type boolean;
                  default "false";
                  description
                    "Enable/disable the ability to associate an Opcode value with a set of adjacencies.";
                }
              }
            }
          }
          container attribute {
            config false;
            description
              "Operational data of locator.";
            leaf block {
              type inet:ipv6-address-no-zone;
              description
                "Block segment.";
            }
            leaf node-id {
              type inet:ipv6-address-no-zone;
              description
                "NodeId segment.";
            }
            leaf node-id-length {
              type uint8 {
                range "0..255";
              }
              description
                "Length of the NodeId segment.";
            }
            leaf reference {
              type uint16 {
                range "0..65535";
              }
              description
                "Number of times the locator is referenced.";
            }
            leaf compress-dynamic-sid-pool-id {
              type uint32 {
                range "0..4294967295";
              }
              description
                "ID of a compressed dynamic SID pool.";
            }
            leaf compress-dynamic-length {
              type uint8 {
                range "0..255";
              }
              description
                "Length of the compression dynamic segment.";
            }
            leaf compress-dynamic-sid-begin {
              type inet:ipv6-address-no-zone;
              description
                "Start value in the range of compressed dynamic SIDs.";
            }
            leaf compress-dynamic-sid-end {
              type inet:ipv6-address-no-zone;
              description
                "End value in the range of compressed dynamic SIDs.";
            }
            leaf compress-static-sid-begin {
              type inet:ipv6-address-no-zone;
              description
                "Start value in the range of compressed static SIDs.";
            }
            leaf compress-static-sid-end {
              type inet:ipv6-address-no-zone;
              description
                "End value in the range of compressed static SIDs.";
            }
            leaf dynamic-sid-pool-id {
              type uint32 {
                range "0..4294967295";
              }
              description
                "ID of a dynamic SID pool.";
            }
            leaf dynamic-length {
              type uint8 {
                range "0..255";
              }
              description
                "Length of the dynamic segment.";
            }
            leaf dynamic-sid-begin {
              type inet:ipv6-address-no-zone;
              description
                "Start value in the range of dynamic SIDs.";
            }
            leaf dynamic-sid-end {
              type inet:ipv6-address-no-zone;
              description
                "End value in the range of dynamic SIDs.";
            }
            leaf static-sid-begin {
              type inet:ipv6-address-no-zone;
              description
                "Start value in the range of static SIDs.";
            }
            leaf static-sid-end {
              type inet:ipv6-address-no-zone;
              description
                "End value in the range of static SIDs.";
            }
            leaf global-id-block {
              type uint8;
              description
                "Ratio of GIBs in compressed SIDs.";
            }
            leaf local-id-block {
              type uint8;
              description
                "Ratio of LIBs in compressed SIDs.";
            }
            container srv6lb-attributes {
              description
                "List of operational data of srv6 local block reserved for BSIDs.";
              list srv6lb-attribute {
                key "index";
                max-elements  "1";
                description
                  "Statistics of segment routing IPv6 local block BSIDs. Currently only one configuration is supported.";
                leaf index {
                  type uint32;
                  description
                    "The index of a segment routing IPv6 local block BSIDs.";
                }
                leaf local-block-begin {
                  type inet:ipv6-address-no-zone;
                  description
                    "Begin value in the range of reserved local block BSIDs.";
                }
                leaf local-block-end {
                  type inet:ipv6-address-no-zone;
                  description
                    "End value in the range of reserved local block BSIDs.";
                }
                leaf number {
                  type uint32 {
                    range "1..200000";
                  }
                  description
                   "Segment routing IPv6 local block range.";
                }
              }
            }
          }
        }
      }
      container remote-end-ops {
        when "../enable='true'";
        description
          "List of remote End.OTP configuration.";
        list remote-end-op {
          key "sid";
          description
            "Configure remote End.OTP configuration.";
          leaf sid {
            type inet:ipv6-address-no-zone;
            description
              "Remote End.OTP SID.";
          }
          leaf prefix-length {
            type uint8 {
              range "1..128";
            }
            mandatory true;
            description
              "Remote End.OTP SID prefix length.";
          }
        }
      }
      container local-sids {
        config false;
        description
          "Statistics of segment routing IPv6 local SID list.";
        container ends {
          description
            "List of segment routing IPv6 End local SID list.";
          list end{
            key "value";
            description
              "Statistics of segment routing IPv6 End local SID list.";
            leaf value {
              type inet:ipv6-address-no-zone;
              description
                "End SID value.";
            }
            leaf locator-name {
              type string {
                length "1..31";
              }
              description
                "Locator name.";
            }
            leaf update-time {
              type yang:date-and-time;
              units s;
              description
                "Update time stamp of a SID.";
            }
          }
        }
        container end-psps {
          description
            "List of segment routing IPv6 End psp local SID list.";
          list end-psp{
            key "value";
            description
              "Statistics of segment routing IPv6 End psp local SID list.";
            leaf value {
              type inet:ipv6-address-no-zone;
              description
                "End SID value.";
            }
            leaf locator-name {
              type string {
                length "1..31";
              }
              description
                "Locator name.";
            }
            leaf update-time {
              type yang:date-and-time;
              units s;
              description
                "Update time stamp of a SID.";
            }
          }
        }
        container end-psp-usp-usds {
          description
            "List of segment routing IPv6 End psp-usp-usd local SID list.";
          list end-psp-usp-usd{
            key "value";
            description
              "Statistics of segment routing IPv6 End psp-usp-usd local SID list.";
            leaf value {
              type inet:ipv6-address-no-zone;
              description
                "End SID value.";
            }
            leaf locator-name {
              type string {
                length "1..31";
              }
              description
                "Locator name.";
            }
            leaf update-time {
              type yang:date-and-time;
              units s;
              description
                "Update time stamp of a SID.";
            }
          }
        }
        container end-psp-usp-usd-cocs {
          description
            "List of segment routing IPv6 End psp-usp-usd-coc local SID list.";
          list end-psp-usp-usd-coc{
            key "value";
            description
              "Statistics of segment routing IPv6 End psp-usp-usd-coc local SID list.";
            leaf value {
              type inet:ipv6-address-no-zone;
              description
                "End psp-usp-usd-coc SID value.";
            }
            leaf locator-name {
              type string {
                length "1..31";
              }
              description
                "Locator name.";
            }
            leaf update-time {
              type yang:date-and-time;
              units s;
              description
                "Update time stamp of a SID.";
            }
          }
        }
        container end-cocs {
          description
            "List of segment routing IPv6 End coc local SID list.";
          list end-coc{
            key "value";
            description
              "Statistics of segment routing IPv6 End coc local SID list.";
            leaf value {
              type inet:ipv6-address-no-zone;
              description
                "End coc SID value.";
            }
            leaf locator-name {
              type string {
                length "1..31";
              }
              description
                "Locator name.";
            }
            leaf update-time {
              type yang:date-and-time;
              units s;
              description
                "Update time stamp of a SID.";
            }
          }
        }
        container end-psp-cocs {
          description
            "List of segment routing IPv6 End psp-coc local SID list.";
          list end-psp-coc{
            key "value";
            description
              "Statistics of segment routing IPv6 End psp-coc local SID list.";
            leaf value {
              type inet:ipv6-address-no-zone;
              description
                "End psp-coc SID value.";
            }
            leaf locator-name {
              type string {
                length "1..31";
              }
              description
                "Locator name.";
            }
            leaf update-time {
              type yang:date-and-time;
              units s;
              description
                "Update time stamp of a SID.";
            }
          }
        }
        container end-ops {
          description
            "List of segment routing IPv6 End.OP local SID list.";
          list end-op {
            key "value";
            description
              "Statistics of segment routing IPv6 End.OP local SID list.";
            leaf value {
              type inet:ipv6-address-no-zone;
              description
                "End.OP SID value.";
            }
            leaf locator-name {
              type string {
                length "1..31";
              }
              description
                "Locator name.";
            }
            leaf update-time {
              type yang:date-and-time;
              units s;
              description
                "Update time stamp of a SID.";
            }
          }
        }
        container end-xs {
          description
            "List of segment routing IPv6 End.X local SID list.";
          list end-x {
            key "value";
            description
              "Statistics of segment routing IPv6 End.X local SID list.";
            leaf value {
              type inet:ipv6-address-no-zone;
              description
                "End.X SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-psps {
          description
            "List of segment routing IPv6 End.X psp local SID list.";
          list end-x-psp {
            key "value";
            description
              "Statistics of segment routing IPv6 End.X psp local SID list.";
            leaf value {
              type inet:ipv6-address-no-zone;
              description
                "End.X SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-psp-usp-usds {
          description
            "List of segment routing IPv6 End.X psp-usp-usd local SID list.";
          list end-x-psp-usp-usd {
            key "value";
            description
              "Statistics of segment routing IPv6 End.X psp-usp-usd local SID list.";
            leaf value {
              type inet:ipv6-address-no-zone;
              description
                "End.X SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-psp-usp-usd-cocs {
          description
            "List of segment routing IPv6 End.X psp-usp-usd-coc local SID list.";
          list end-x-psp-usp-usd-coc {
            key "value";
            description
              "Statistics of segment routing IPv6 End.X psp-usp-usd-coc local SID list.";
            leaf value {
              type inet:ipv6-address-no-zone;
              description
                "End.X psp-usp-usd-coc SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-cocs {
          description
            "List of segment routing IPv6 End.X coc local SID list.";
          list end-x-coc {
            key "value";
            description
              "Statistics of segment routing IPv6 End.X coc local SID list.";
            leaf value {
              type inet:ipv6-address-no-zone;
              description
                "End.X coc SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-psp-cocs {
          description
            "List of segment routing IPv6 End.X psp-coc local SID list.";
          list end-x-psp-coc {
            key "value";
            description
              "Statistics of segment routing IPv6 End.X psp-coc local SID list.";
            leaf value {
              type inet:ipv6-address-no-zone;
              description
                "End.X psp-coc SID value.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-dt2us {
          description
            "List of segment routing IPv6 End.DT2U local SID list.";
          list end-dt2u {
            key "value";
            description
              "Statistics of segment routing IPv6 End.DT2U local SID list.";
            leaf value {
              type inet:ipv6-address-no-zone;
              description
                "End.DT2U SID value.";
            }
            leaf bd-id {
              ext:support-filter "true";
              type uint32 {
                range "1..16777215";
              }
              description
                "The Bridge-domain ID corresponding to the SID.";
            }
            leaf locator-name {
              type string {
                length "1..32";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dt2uls {
          description
            "List of segment routing IPv6 End.DT2UL local SID list.";
          list end-dt2ul {
            key "value";
            description
              "Statistics of segment routing IPv6 End.DT2UL local SID list.";
            leaf value {
              type inet:ipv6-address-no-zone;
              description
                "End.DT2UL SID value.";
            }
            leaf bd-id {
              ext:support-filter "true";
              type uint32 {
                range "1..16777215";
              }
              description
                "The Bridge-domain ID corresponding to the SID.";
            }
            leaf locator-name {
              type string {
                length "1..32";
              }
              description
                "Locator name.";
            }
            leaf update-time {
              type yang:date-and-time;
              units s;
              description
                "Update time stamp of a SID.";
            }
          }
        }
        container end-dt2ms {
          description
            "List of segment routing IPv6 End.DT2M local SID list.";
          list end-dt2m {
            key "value";
            description
              "Statistics of segment routing IPv6 End.DT2M local SID list.";
            leaf value {
              type inet:ipv6-address-no-zone;
              description
                "End.DT2M SID value.";
            }
            leaf bd-id {
              ext:support-filter "true";
              type uint32 {
                range "1..16777215";
              }
              description
                "The Bridge-domain ID corresponding to the SID.";
            }
            leaf locator-name {
              type string {
                length "1..32";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dx2s {
          description
            "List of segment routing IPv6 End.DX2 local SID list.";
          list end-dx2 {
            key "value";
            description
              "Statistics of segment routing IPv6 End.DX2 local SID list.";
            leaf value {
              type inet:ipv6-address-no-zone;
              description
                "End.DX2 SID value.";
            }
            leaf evpl-id {
              ext:support-filter "true";
              type uint32 {
                range "0..4294967295";
              }
              description
                "EVPL ID mapped to the SID.";
            }
            leaf locator-name {
              type string {
                length "1..32";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dx2ls {
          description
            "List of segment routing IPv6 End.DX2L local SID list.";
          list end-dx2l {
            key "value";
            description
              "Statistics of segment routing IPv6 End.DX2L local SID list.";
            leaf value {
              type inet:ipv6-address-no-zone;
              description
                "End.DX2L SID value.";
            }
            leaf evpl-id {
              ext:support-filter "true";
              type uint32 {
                range "0..4294967295";
              }
              description
                "EVPL ID mapped to the SID.";
            }
            leaf locator-name {
              type string {
                length "1..32";
              }
              description
                "Locator name.";
            }
            leaf update-time {
              type yang:date-and-time;
              units s;
              description
                "Update time stamp of a SID.";
            }
          }
        }
        container end-dt4s {
          description
            "List of segment routing IPv6 End.DT4 local SID list.";
          list end-dt4 {
            key "value";
            description
              "Statistics of segment routing IPv6 End.DT4 local SID list.";
            leaf value {
              type inet:ipv6-address-no-zone;
              description
                "End.DT4 SID value.";
            }
            leaf vpn-name {
              type string {
                length "1..31";
              }
              description
                "VPN name.";
            }
            leaf locator-name {
              type string {
                length "1..31";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dt6s {
          description
            "List of segment routing IPv6 End.DT6 local SID list.";
          list end-dt6 {
            key "value";
            description
              "Statistics of segment routing IPv6 End.DT6 local SID list.";
            leaf value {
              type inet:ipv6-address-no-zone;
              description
                "End.DT6 SID value.";
            }
            leaf vpn-name {
              type string {
                length "1..31";
              }
              description
                "VPN name.";
            }
            leaf locator-name {
              type string {
                length "1..31";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dt46s {
          description
            "List of segment routing IPv6 End.DT46 local SID list.";
          list end-dt46 {
            key "value";
            description
              "Statistics of segment routing IPv6 End.DT46 local SID list.";
            leaf value {
              type inet:ipv6-address-no-zone;
              description
                "End.DT46 SID value.";
            }
            leaf vpn-name {
              type string {
                length "1..31";
              }
              description
                "VPN name.";
            }
            leaf locator-name {
              type string {
                length "1..31";
              }
              description
                "Locator name.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-ms {
          config false;
          description
            "List of segment routing IPv6 End.M local SID list.";
          list end-m{
            key "value";
            config false;
            description
              "Statistics of segment routing IPv6 End.M local SID list.";
            leaf value {
              type inet:ipv6-address-no-zone;
              config false;
              description
                "End.M SID value.";
            }
            leaf flavor {
              type string {
                length "1..64";
              }
              config false;
              description
                "End SID flavor value.";
            }
            leaf locator-name {
              type string {
                length "1..31";
              }
              config false;
              description
                "Locator name.";
            }
            leaf mirror-locator-number {
              type uint32;
              config false;
              description
                "Mirror locator number.";
            }
            leaf mirror-locator-set {
              type string {
                length "1..360";
              }
              config false;
              description
                "Mirror locator address set.";
            }
            leaf update-time {
              type yang:date-and-time;
              units s;
              description
                "Update time stamp of a SID.";
            }
          }
        }
        container end-dx4s {
          config false;
          description
            "List of segment routing IPv6 End.DX4 local SID list.";
          list end-dx4 {
            key "value";
            config false;
            description
              "Statistics of segment routing IPv6 End.DX4 local SID list.";
            leaf value {
              type inet:ipv6-address-no-zone;
              config false;
              description
                "End.DX4 SID value.";
            }
            leaf vpn-name {
              type string {
                length "1..31";
              }
              config false;
              description
                "VPN name.";
            }
            leaf locator-name {
              type string {
                length "1..31";
              }
              config false;
              description
                "Locator name.";
            }
            leaf if-name {
              type string {
                length "1..32";
              }
              description
                "Exit interface.";
            }
            leaf next-hop {
              type inet:ipv4-address-no-zone;
              description
                "Next hop IPv4 address.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-dx6s {
          config false;
          description
            "List of segment routing IPv6 End.DX6 local SID list.";
          list end-dx6 {
            key "value";
            config false;
            description
              "Statistics of segment routing IPv6 End.DX6 local SID list.";
            leaf value {
              type inet:ipv6-address-no-zone;
              config false;
              description
                "End.DX6 SID value.";
            }
            leaf vpn-name {
              type string {
                length "1..31";
              }
              config false;
              description
                "VPN name.";
            }
            leaf locator-name {
              type string {
                length "1..31";
              }
              config false;
              description
                "Locator name.";
            }
            leaf if-name {
              type string {
                length "1..32";
              }
              description
                "Exit interface.";
            }
            leaf next-hop {
              type inet:ipv6-address-no-zone;
              description
                "Next hop IPv6 address.";
            }
            leaf behavior {
              type behavior-type;
              description
                "Behaviors.";
            }
            leaf compress {
              type sid-compress-type;
              description
                "Compress type.";
            }
            leaf update-time {
              type yang:date-and-time;
              units s;
              description
                "Update time stamp of a SID.";
            }
          }
        }
        container end-b6s {
          description
            "List of segment routing IPv6 End.B6 local SID list.";
          list end-b6 {
            key "value";
            description
              "Statistics of segment routing IPv6 End.B6 local SID list.";
            leaf value {
              type inet:ipv6-address-no-zone;
              description
                "End.B6 SID value.";
            }
            leaf tunnel-id {
              type uint32 {
                range "0..4294967295";
              }
              description
                "Tunnel Id.";
            }
            leaf tunnel-type {
              type string {
                length "1..16";
              }
              description
                "Tunnel type.";
            }
            leaf tunnel-vrf-id {
              type uint32 {
                range "0..4294967295";
              }
              description
                "Tunnel VRF Id.";
            }
            leaf encapsulation-mode {
              type encapsulation-type;
              description
                "Encapsulation mode.";
            }
            leaf slice-enable {
              type boolean;
              description
                "Whether the slice is enabled.";
            }
            leaf locator-name {
              type string {
                length "1..31";
              }
              description
                "Locator name.";
            }
            leaf update-time {
              type yang:date-and-time;
              units s;
              description
                "Update time stamp of a SID.";
            }
            leaf reduce-enable {
              type boolean;
              description
                "Whether the reduce is enabled.";
            }
            leaf afr-enable {
              type boolean;
              description
                "Whether AFR is enabled.";
            }
            leaf inherit-slice-enable {
              type boolean;
              description
                "Whether inheriting slice is enabled.";
            }
          }
        }
        container end-extensions {
          description
            "List of segment routing IPv6 End extension local SID list.";
          list end-extension {
            key "value";
            description
              "Statistics of segment routing IPv6 End extension local SID list.";
            leaf value {
              type inet:ipv6-address-no-zone;
              description
                "End extension SID value.";
            }
            leaf behavior {
              type behavior-type;
              description
                "Behaviors.";
            }
            leaf locator-name {
              type string {
                length "1..31";
              }
              description
                "Locator name.";
            }
            leaf update-time {
              type yang:date-and-time;
              units s;
              description
                "Update time stamp of a SID.";
            }
          }
        }
        container end-uncompressed-extensions {
          description
            "List of Segment Routing IPv6 uncompressed End extension local SIDs.";
          list end-uncompressed-extension {
            key "value";
            description
              "Statistics of Segment Routing IPv6 uncompressed End extension local SIDs.";
            leaf value {
              type inet:ipv6-address-no-zone;
              description
                "Uncompressed End extension SID value.";
            }
            leaf behavior {
              type behavior-type;
              description
                "Behaviors.";
            }
            leaf locator-name {
              type string {
                length "1..31";
              }
              description
                "Locator name.";
            }
            leaf update-time {
              type yang:date-and-time;
              units s;
              description
                "Update time stamp of a SID.";
            }
          }
        }
        container end-x-extensions {
          description
            "List of segment routing IPv6 End.X extension local SID list.";
          list end-x-extension {
            key "value";
            description
              "Statistics of segment routing IPv6 End.X extension local SID list.";
            leaf value {
              type inet:ipv6-address-no-zone;
              description
                "End.X extension SID value.";
            }
            leaf behavior {
              type behavior-type;
              description
                "Behaviors.";
            }
            leaf locator-name {
              type string {
                length "1..31";
              }
              description
                "Locator name.";
            }
            leaf te-frr-flag {
              type string {
                length "1..31";
              }
              status obsolete;
              description
                "TE FRR flag.";
            }
            leaf te-frr-delay-time-remain {
              type uint32;
              units ms;
              status obsolete;
              description
                "Remaining time of the TE FRR delay timer.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container end-x-uncompressed-extensions {
          description
            "List of Segment Routing IPv6 uncompressed End.X extension local SIDs.";
          list end-x-uncompressed-extension {
            key "value";
            description
              "Statistics of Segment Routing IPv6 uncompressed End.X extension local SIDs.";
            leaf value {
              type inet:ipv6-address-no-zone;
              description
                "Uncompressed End.X extension SID value.";
            }
            leaf behavior {
              type behavior-type;
              description
                "Behaviors.";
            }
            leaf locator-name {
              type string {
                length "1..31";
              }
              description
                "Locator name.";
            }
            leaf update-time {
              type yang:date-and-time;
              units s;
              description
                "Update time stamp of a SID.";
            }
            leaf next-hop-count {
              type uint32;
              description
                "Count of next hops.";
            }
            container next-hops {
              description
                "List of next hop information.";
              list next-hop {
                key "if-name next-hop";
                description
                  "Statistics of next hop information.";
                leaf if-name {
                  type leafref {
                    path "/ifm:ifm/ifm:interfaces/ifm:interface/ifm:name";
                  }
                  description
                    "Exit interface.";
                }
                leaf next-hop {
                  type inet:ipv6-address-no-zone;
                  description
                    "Next hop IPv6 address.";
                }
                leaf te-frr-flag {
                  type string {
                  length "1..31";
                }
                description
                  "TE FRR flag.";
                }
                leaf te-frr-delay-time-remain {
                  type uint32;
                  units ms;
                  description
                    "Remaining time of the TE FRR delay timer.";
                }
                leaf bak-if-name {
                  type leafref {
                    path "/ifm:ifm/ifm:interfaces/ifm:interface/ifm:name";
                  }
                  description
                    "Backup exit interface.";
                }
                leaf bak-next-hop {
                  type inet:ipv6-address-no-zone;
                  description
                    "Backup next hop IPv6 address.";
                }
                leaf bak-update-time {
                  type yang:date-and-time;
                  units s;
                  description
                    "Backup update time stamp of a SID.";
                }
                leaf bak-compress-mode {
                  type sid-stack-compress-type;
                  description
                  "Compress type.";
                }
                leaf bak-label-stack {
                  type string {
                    length "1..1024";
                  }
                  description
                    "Label stack information of the END-X SID protection path.";
                }
              }
            }
          }
        }
        container xsids {
          description
            "List of segment routing IPv6 XSID local SID list.";
          list xsid {
            key "value";
            description
              "Statistics of segment routing IPv6 XSID local SID list.";
            leaf value {
              type inet:ipv6-address-no-zone;
              description
                "XSID SID value.";
            }
            leaf tunnel-id {
              type uint32 {
                range "0..4294967295";
              }
              description
                "Tunnel Id.";
            }
            leaf tunnel-type {
              type string {
                length "1..16";
              }
              description
                "Tunnel type.";
            }
            leaf tunnel-vrf-id {
              type uint32 {
                range "0..4294967295";
              }
              description
                "Tunnel VRF Id.";
            }
            leaf encapsulation-mode {
              type encapsulation-type;
              description
                "Encapsulation mode.";
            }
            leaf slice-enable {
              type boolean;
              description
                "Whether the slice is enabled.";
            }
            leaf locator-name {
              type string {
                length "1..31";
              }
              description
                "Locator name.";
            }
            leaf update-time {
              type yang:date-and-time;
              units s;
              description
                "Update time stamp of a SID.";
            }
          }
        }
      }
      container global-info {
        config false;
        description
          "Operational data of segment routing IPv6 global information.";
        leaf source-address {
          type inet:ipv6-address-no-zone;
          description
            "SRv6 encapsulation source address information.";
        }
        leaf te-frr-enable {
          type boolean;
          description
            "SR TE FRR mode information.";
        }
        leaf te-ipv6-router-id {
          type inet:ipv6-address-no-zone;
          description
            "Global TE IPv6 router ID.";
        }
        leaf active-path-mtu {
          type uint32;
          description
            "Active path MTU value.";
        }
      }
    }
  }
}
