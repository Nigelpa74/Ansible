/*
Copyright (C) 2019-2024 Huawei Technologies Co., Ltd. All rights reserved.
*/
module huawei-isis-srv6 {
  namespace "urn:huawei:yang:huawei-isis-srv6";
  prefix isis-srv6;
  import huawei-network-instance {
    prefix ni;
  }
  import huawei-isis {
    prefix isis;
  }
  import huawei-srv6 {
    prefix srv6;
  }
  import huawei-extension {
    prefix ext;
  }
  import huawei-net-slice {
    prefix net-slice;
  }
  import huawei-pub-type {
    prefix pub-type;
  }
  import huawei-ifm {
    prefix ifm;
  }
  organization
    "Huawei Technologies Co., Ltd.";
  contact
    "Huawei Industrial Base
     Bantian, Longgang
     Shenzhen 518129
     People's Republic of China
     Website: http://www.huawei.com
     Email: support@huawei.com";
  description
    "ISIS segment routing IPv6 management.";
  revision 2024-12-15 {
    description
      "Add auto-end-x-protected. Add compress-flex-algo-excludes. Add parallel-sid-advertise.
       Add leaf usp-usd under container auto-sid-advertise. Add srv6 container. Modify auto-endx-disable description.";
    reference
      "Huawei private.";
  }
  revision 2023-11-01 {
    description
      "Add compress-type for 16bit compresssion. Add strict-msd-check. Add slice-source-prefixs.";
    reference
      "Huawei private.";
  }
  revision 2023-03-09 {
    description
      "Add must condition for checking if intelligent-convergence conflicts with frr or avoid-microloop.";
    reference "Huawei private.";
  }
  revision 2022-10-11 {
    description
      "Add leafs for container auto-sid-advertise.";
    reference
      "Huawei private.";
  }
  revision 2022-07-20 {
    description
      "Add container auto-sid-advertise etc.";
    reference
      "Huawei private.";
  }
  revision 2021-03-11 {
    description
      "Add container inter level protect etc.";
    reference
      "Huawei private.";
  }
  revision 2019-04-04 {
    description
      "Initial revision.";
    reference
      "Huawei private.";
  }
  ext:task-name  "isis";
  typedef encap-mode {
    type enumeration {
      enum "no-set" {
        value 0;
        description
          "No-set mode.";
      }
      enum "insert" {
        value 1;
        description
          "Insert mode.";
      }
      enum "encaps" {
        value 2;
        description
          "Encaps mode.";
      }
    }
    description
      "Encapsulation mode for IS-IS SRv6 SID stack.";
  }
  typedef stack-compress-type {
    type enumeration {
      enum "compress-32" {
        value 0;
        description
          "32-bit compression.";
      }
      enum "compress-16" {
        value 1;
        description
          "16-bit compression.";
      }
    }
    description
      "Compress type for IS-IS SRv6 SID stack.";
  }
  augment /ni:network-instance/ni:instances/ni:instance/isis:isis/isis:sites/isis:site/isis:afs/isis:af {
    description
      "ISIS segment routing IPv6 augment to ISIS.";
    container srv6 {
      when "../../../../../../ni:name='_public_' and ../isis:type='afipv6'";
      description
        "Configure ISIS segment routing IPv6.";
      container locators {
        when "../../../../isis:cost-style='wide' or ../../../../isis:cost-style='transition'  or ../../../../isis:cost-style='wtransition'";
        description
          "List of segment routing IPv6 locator.";
          list locator {
          key "locator-name";
          description
          "Configure segment routing IPv6 locator.";
          leaf locator-name {
            type leafref {
              path "/ni:network-instance/ni:instances/ni:instance/srv6:srv6/srv6:locators/srv6:locator/srv6:name";
            }
            description
              "Enable ISIS segment routing IPv6 with specified Locator.";
          }
          leaf auto-sid {
            type boolean;
            default "true";
            description
              "Enable/disable automatic application for SID.";
          }
          leaf auto-end-x-protected {
            when "../auto-sid='true'";
            type boolean;
            must "../auto-end-x-protected='false' or /ni:network-instance/ni:instances/ni:instance[ni:name='_public_']/srv6:srv6/srv6:locators/srv6:locator[srv6:name = current()/../isis-srv6:locator-name]/srv6:flex-algo=0";
            default "false";
            description
              "Enable/disable automatic protected End.X.";
          }
          leaf auto-end-x-parallel-protected {
            when "../auto-end-x-protected='true'";
            type boolean;
            default "false";
            description
              "Enable/disable automatic parallel protected END.X.";
          }
        }
      }
      container locator-tag {
        description
          "Configure IPv6 segment routing default tag.";
        leaf tag-value {
          type uint32 {
            range "1..4294967295";
          }
          description
            "Set a default tag value for locator.";
        }
      }
      container avoid-microloop {
        when "../locators/locator";
        description
          "Configure IPv6 segment routing avoid microloop.";
        leaf enable {
          type boolean;
          must "../isis-srv6:enable='false' or ../../../isis:intelligent-convergence/isis:enable='false'";
          default "false";
          description
            "Enable/disable IPv6 segment routing avoid microloop.";
        }
        leaf delay-value {
          type uint16 {
            range "1000..60000";
          }
          default "5000";
          description
            "Set the route delivery delay for IPv6 segment routing avoid microloop.";
        }
      }
      container inter-level-protect {
        when "../../isis:frr/isis:enable='true' and ../locators/locator";
        description
        "Configure Inter-Level-Protect.";
        leaf enable-level1 {
          type boolean;
          default "false";
          description
          "Enable/disable Level 1 Inter-Level-Protect.";
        }
        leaf preferred {
          type boolean;
          must "../enable-level1='true' or ../preferred='false'";
          default "false";
          description
          "Enable/disable Inter-Level-Protect Preferred.";
        }
      }
      container compress {
        when "../locators/locator";
        description
            "Configure compress mode for IS-IS Srv6 SID stack.";
        leaf enable {
          type boolean;
          default "false";
          description
            "Enable/disable SRv6 compress mode."; 
        }
        leaf compress-type {
          when "../enable = 'true'";
          type stack-compress-type;
          must ". = 'compress-32' or /ni:network-instance/ni:instances/ni:instance/srv6:srv6/srv6:locators/srv6:locator[srv6:name = current()/../../isis-srv6:locators/isis-srv6:locator/isis-srv6:locator-name]/srv6:compress-16";
          default "compress-32";
          description
            "Configure compress type for IS-IS SRv6 SID stack."; 
        }
        leaf destination-address {
          when "../compress-type = 'compress-16'";
          type boolean;
          default "false";
          description
            "Enable/disable the ability of destination address compression.";
        }
      }
      container encapsulation-mode {
        when "../locators/locator";
        description
          "Configure encapsulation mode for IS-IS SRv6 SID stack.";
        leaf mode {
          type encap-mode;
          default "no-set";
          description
            "Specify insert or encaps mode for IS-IS SRv6 SID stack."; 
        }
      }
      container auto-sid-advertise {
        description
          "Configure SRv6 auto-sid advertised flavor for End and EndX.";
        leaf no-flavor {
          type boolean;
          default "false";
          description
            "Enable/disable SRv6 auto-sid no-flavor advertise."; 
        }
        leaf psp {
          type boolean;
          default "false";
          description
            "Enable/disable SRv6 auto-sid psp flavor advertise."; 
        }
        leaf psp-usp-usd {
          type boolean;
          default "false";
          description
            "Enable/disable SRv6 auto-sid psp-usp-usd flavor advertise."; 
        }
        leaf usp-usd {
          type boolean;
          default "false";
          description
            "Enable/disable SRv6 auto-sid usp-usd flavor advertise."; 
        }
        leaf psp-usp-usd-coc {
          type boolean;
          default "false";
          description
            "Enable/disable SRv6 auto-sid psp-usp-usd-coc flavor advertise."; 
        }
        leaf coc {
          type boolean;
          default "false";
          description
            "Enable/disable SRv6 auto-sid coc flavor advertise."; 
        }
        leaf psp-coc {
          type boolean;
          default "false";
          description
            "Enable/disable SRv6 auto-sid psp-coc flavor advertise."; 
        }
        leaf psp-usp-usd-coc-next {
          type boolean;
          default "false";
          description
            "Enable/disable SRv6 auto-sid psp-usp-usd-coc-next flavor advertise."; 
        }
        leaf psp-usd-next {
          type boolean;
          default "false";
          description
            "Enable/disable SRv6 auto-sid psp-usd-next flavor advertise."; 
        }
      }
      container parallel-sid-advertise {
        description
          "Configure SRv6 parallel-sid advertised flavor for EndX.";
        leaf no-flavor {
          type boolean;
          default "false";
          description
            "Enable/disable SRv6 parallel-sid no-flavor advertise."; 
        }
        leaf psp {
          type boolean;
          default "false";
          description
            "Enable/disable SRv6 parallel-sid psp flavor advertise."; 
        }
        leaf psp-usp-usd {
          type boolean;
          default "false";
          description
            "Enable/disable SRv6 parallel-sid psp-usp-usd flavor advertise."; 
        }
        leaf psp-usp-usd-coc {
          type boolean;
          default "false";
          description
            "Enable/disable SRv6 parallel-sid psp-usp-usd-coc flavor advertise."; 
        }
        leaf psp-usp-usd-coc-next {
          type boolean;
          default "false";
          description
            "Enable/disable SRv6 parallel-sid psp-usp-usd-coc-next flavor advertise."; 
        }
        leaf psp-usd-next {
          type boolean;
          default "false";
          description
            "Enable/disable SRv6 parallel-sid psp-usd-next flavor advertise."; 
        }
      }
      container strict-msd-check {
        when "../locators/locator";
        description
          "Configure strict MSD check for IS-IS SRv6 SID stack.";
        leaf enable {
          type boolean;
          default "false";
          description
            "Enable/disable SRv6 strictly check msd function."; 
        }
      }
      container slice-source-prefixs {
        description
        "List of network-slice source-prefixs.";
        list slice-source-prefix {
          key "prefix-name";
          description
          "Configure network-slice source-prefix.";
          leaf prefix-name {
           type leafref {
             path "/net-slice:net-slice/net-slice:network-slice-source-prefix/net-slice:prefixs/net-slice:prefix/net-slice:name";
           }
          must "/net-slice:net-slice/net-slice:network-slice-source-prefix/net-slice:prefixs/net-slice:prefix[net-slice:name=current()]/net-slice:ipv6-prefix";
          description
            "Prefix name of network-slice source-prefix.";
          }
          leaf tag-value {
            type uint32 {
              range "1..4294967295";
            }
            description
              "Set a tag value for network-slice source-prefix.";
          }
        }
      }
      container compress-flex-algo-excludes {
          description
              "List of flexible algorithm excluded compression capabilities in an IS-IS process.";
          list compress-flex-algo-exclude {
            key "compress-type";
            description
              "Configure flexible algorithm compression.";
          leaf compress-type {
               type stack-compress-type;
               must ". = 'compress-16'";
               description
                 "Configure compress type for IS-IS flexible algorithm SRv6 SID stack.";
          } 
          leaf flex-algo-id {
               type pub-type:id-range {
               ext:value-range '128..255';
               pattern '((12[8-9]|1[3-9][0-9]|2[0-4][0-9]|25[0-5])?(-(12[8-9]|1[3-9][0-9]|2[0-4][0-9]|25[0-5]))?(,((12[8-9]|1[3-9][0-9]|2[0-4][0-9]|25[0-5])(-(12[8-9]|1[3-9][0-9]|2[0-4][0-9]|25[0-5]))?))*)|((([\+|\-](12[8-9]|1[3-9][0-9]|2[0-4][0-9]|25[0-5]))|([\+|\-]\((12[8-9]|1[3-9][0-9]|2[0-4][0-9]|25[0-5])-(12[8-9]|1[3-9][0-9]|2[0-4][0-9]|25[0-5])\)))?(,(([\+|\-](12[8-9]|1[3-9][0-9]|2[0-4][0-9]|25[0-5]))|([\+|\-]\((12[8-9]|1[3-9][0-9]|2[0-4][0-9]|25[0-5])-(12[8-9]|1[3-9][0-9]|2[0-4][0-9]|25[0-5])\))))*)';
               }
               mandatory "true";
               description
                 "Flexible algorithm identifier.";
          } 
        }
      }
    }
  }
  augment /ni:network-instance/ni:instances/ni:instance/isis:isis/isis:sites/isis:site/isis:circuits/isis:circuit/isis:afs/isis:af {
    description
      "Augment IS-IS Segment Routing IPv6 to IS-IS interface.";
    container srv6 {
      when "../isis:type='afipv6' and ../../../../../../../../ni:name='_public_'";
      description
        "Configure IS-IS circuit Segment Routing IPv6.";
      leaf auto-endx-disable {
        when "/ifm:ifm/ifm:interfaces/ifm:interface[ifm:name=current()/../../../../isis:name]/ifm:type!='LoopBack'";
        type empty;
        description
          "Enable/Disable automatic End.X SID advertisement. If there is no SRv6 license authorization for this interface, configure the auto-endx-disable parameter.";
      }
    }
  }
}
