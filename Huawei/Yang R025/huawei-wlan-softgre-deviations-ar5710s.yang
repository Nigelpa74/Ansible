/*
Copyright (C) 2019 Huawei Technologies Co., Ltd. All rights reserved.
*/
module huawei-wlan-softgre-deviations-ar5710s {
  yang-version 1;
  namespace "urn:huawei:yang:huawei-wlan-softgre-deviations-ar5710s";
  prefix wlan-softgre-devs-ar5710s;

  import huawei-wlan-softgre {
    prefix wlan-softgre;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-softgre module.";

  revision 2019-11-06 {
    description
      "Initial revision.";
    reference "Huawei private.";
  }

  deviation "/wlan-softgre:wlan-softgre" {
    deviate not-supported;
  }
}
