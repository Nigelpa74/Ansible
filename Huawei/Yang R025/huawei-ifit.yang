/*
Copyright (C) 2019-2020 Huawei Technologies Co., Ltd. All rights reserved.
*/
module huawei-ifit {
  namespace "urn:huawei:yang:huawei-ifit";
  prefix ifit;

  import huawei-extension {
    prefix ext;
  } 


  organization
    "Huawei Technologies Co., Ltd.";
  contact
    "Huawei Industrial Base
     Bantian, Longgang
     Shenzhen 518129
     People's Republic of China
     Website: http://www.huawei.com
     Email: support@huawei.com";
  description
    "This module contains a collection of YANG definitions IFIT feature.";
  revision 2020-04-08 {
    description
      "Move nodes to huawei-ifit-common.yang.";
    reference
      "Huawei private.";
  }
  revision 2020-03-25 {
    description
      "Delete enum null.";
    reference
      "Huawei private.";
  }
  revision 2020-03-16 {
    description
      "Add new xpath.";
    reference
      "Huawei private.";
  }
    revision 2020-03-09 {
    description
      "Modify description.";
    reference
      "Huawei private.";
  }
    revision 2019-05-21 {
    description
      "Initial revision.";
    reference
      "Huawei private.";
  }
  ext:task-name  "ifit";
  container ifit {
    presence "IFIT Enable.";
    description
      "Inband flow information telemetry.";
  }
}
