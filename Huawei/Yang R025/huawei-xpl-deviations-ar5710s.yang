/*
Copyright (C) 2025 Huawei Technologies Co., Ltd. All rights reserved.
*/
module huawei-xpl-deviations-ar5710s {
  yang-version 1;
  namespace "urn:huawei:yang:huawei-xpl-deviations-ar5710s";
  prefix xpl-devs-ar5710s;

  import huawei-xpl {
    prefix xpl;
  }

  organization
    "Huawei Technologies Co., Ltd.";
  contact
    "Huawei Industrial Base
     Bantian, Longgang
     Shenzhen 518129
     People's Republic of China
     Website: http://www.huawei.com
     Email: support@huawei.com";
  description
    "This module defines deviation statements for huawei-xpl module.";

  revision 2025-02-24 {
    description
      "Initial revision.";
    reference "Huawei private.";
  }

  deviation "/xpl:xpl" {
    deviate not-supported;
  }
}
