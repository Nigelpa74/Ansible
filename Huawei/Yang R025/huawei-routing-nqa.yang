/*
Copyright (C) 2020-2025 Huawei Technologies Co., Ltd. All rights reserved.
*/
module huawei-routing-nqa {
  yang-version 1;
  namespace "urn:huawei:yang:huawei-routing-nqa";
  prefix rt-nqa;
  
  import huawei-extension {
    prefix ext;
  }
  import huawei-network-instance {
    prefix ni;
  }
  import huawei-l3vpn {
    prefix l3vpn;
  }
  import huawei-routing
  {
    prefix rt;
  }
  import huawei-nqa {
    prefix nqa;
  }
  organization
    "Huawei Technologies Co., Ltd.";
  contact
    "Huawei Industrial Base
    Bantian, Longgang
    Shenzhen 518129
    People's Republic of China
    Website: http://www.huawei.com
    Email: support@huawei.com";
  description
    "The file defines the static route track NQA.";
  revision 2025-04-14 {
    description
      "Add the deprecated status for the nodes in the unicast-route list.";
    reference
      "Huawei private.";
  }
  revision 2024-10-14 {
    description
      "The must condition of the NQA node is modified, and the inherit-cost restriction is deleted.";
    reference
      "Huawei private.";
  }
  revision 2022-10-17 {
    description
      "Add NQA node for nexthop-vrf-vxlans.";
    reference
      "Huawei private.";
  }
  revision 2022-09-30 {
    description
      "Add NQA node for nexthop-vrf-onlys. Add Static route track NQA test group.";
    reference
      "Huawei private.";
  }
  revision 2022-03-17 {
    description
      "Add NQA node for v4 via v6 static route.";
    reference
      "Huawei private.";
  }
  revision 2020-04-20 {
    description
      "Add NQA query node.";
    reference
      "Huawei private.";
  }
  revision 2020-02-25 {
    description
      "Initial revision.";
    reference
      "Huawei private.";
  }
  ext:task-name "route-base";

  augment /ni:network-instance/ni:instances/ni:instance/l3vpn:afs/l3vpn:af/rt:routing/rt:static-routing/rt:unicast-routes/rt:unicast-route/rt:track-setting {
    status deprecated;
    description
      "Static route track NQA.";
    case nqa {
      status deprecated;
      description
        "Track NQA.";
      leaf admin-name {
        type leafref {
          path "/nqa:nqa/nqa:instances/nqa:instance/nqa:admin-name";
        }
        must "../rt:bfd-enable='false' and ../rt:permanent='false' and ../rt:topology-name='base' and ../test-name";
        status deprecated;
        description
          "Name of an NQA administer instance.";
      }
      leaf test-name {
        type leafref {
          path "/nqa:nqa/nqa:instances/nqa:instance/nqa:test-name";
        }
        must "../rt:bfd-enable='false' and ../rt:permanent='false' and ../rt:topology-name='base' and ../admin-name";
        status deprecated;
        description
          "Name of an NQA test instance.";
      }
    }
  }
  augment /ni:network-instance/ni:instances/ni:instance/l3vpn:afs/l3vpn:af/rt:routing/rt:static-routing/rt:unicast-route2s/rt:unicast-route2/rt:nexthop-interfaces/rt:nexthop-interface/rt:track-setting {
    description
      "Static route track NQA.";
    case nqa {
      description
        "Track NQA.";
      leaf nqa-admin-name {
        type leafref {
          path "/nqa:nqa/nqa:instances/nqa:instance/nqa:admin-name";
        }
        must "../rt:permanent='false' and ../../../rt:topology-name='base' and ../nqa-test-name";
        description
          "Name of an NQA administer instance.";
      }
      leaf nqa-test-name {
        type leafref {
          path "/nqa:nqa/nqa:instances/nqa:instance/nqa:test-name";
        }
        must "../rt:permanent='false' and ../../../rt:topology-name='base' and ../nqa-admin-name";
        description
          "Name of an NQA test instance.";
      }
    }
    case nqa-group {
      description
        "Track NQA group.";
      leaf nqa-group-name {
        type leafref {
          path "/nqa:nqa/nqa:groups/nqa:group/nqa:group-name";
        }
        must "../rt:permanent='false' and ../../../rt:topology-name='base'";
        description
          "Name of an NQA test group.";
      }
    }
  }
  augment /ni:network-instance/ni:instances/ni:instance/l3vpn:afs/l3vpn:af/rt:routing/rt:static-routing/rt:unicast-route2s/rt:unicast-route2/rt:nexthop-interface-addresses/rt:nexthop-interface-address/rt:track-setting {
    description
      "Static route track NQA.";
    case nqa {
      description
        "Track NQA.";
      leaf nqa-admin-name {
        type leafref {
          path "/nqa:nqa/nqa:instances/nqa:instance/nqa:admin-name";
        }
        must "../rt:permanent='false' and ../../../rt:topology-name='base' and ../nqa-test-name";
        description
          "Name of an NQA administer instance.";
      }
      leaf nqa-test-name {
        type leafref {
          path "/nqa:nqa/nqa:instances/nqa:instance/nqa:test-name";
        }
        must "../rt:permanent='false' and ../../../rt:topology-name='base' and ../nqa-admin-name";
        description
          "Name of an NQA test instance.";
      }
    }
    case nqa-group {
      description
        "Track NQA group.";
      leaf nqa-group-name {
        type leafref {
          path "/nqa:nqa/nqa:groups/nqa:group/nqa:group-name";
        }
        must "../rt:permanent='false' and ../../../rt:topology-name='base'";
        description
          "Name of an NQA test group.";
      }
    }
  }
  augment /ni:network-instance/ni:instances/ni:instance/l3vpn:afs/l3vpn:af/rt:routing/rt:static-routing/rt:unicast-route2s/rt:unicast-route2/rt:nexthop-addresses/rt:nexthop-address/rt:track-setting {
    description
      "Static route track NQA.";
    case nqa {
      description
        "Track NQA.";
      leaf nqa-admin-name {
        type leafref {
          path "/nqa:nqa/nqa:instances/nqa:instance/nqa:admin-name";
        }
        must "../rt:permanent='false' and ../../../rt:topology-name='base' and ../nqa-test-name";
        description
          "Name of an NQA administer instance.";
      }
      leaf nqa-test-name {
        type leafref {
          path "/nqa:nqa/nqa:instances/nqa:instance/nqa:test-name";
        }
        must "../rt:permanent='false' and ../../../rt:topology-name='base' and ../nqa-admin-name";
        description
          "Name of an NQA test instance.";
      }
    }
    case nqa-group {
      description
        "Track NQA group.";
      leaf nqa-group-name {
        type leafref {
          path "/nqa:nqa/nqa:groups/nqa:group/nqa:group-name";
        }
        must "../rt:permanent='false' and ../../../rt:topology-name='base'";
        description
          "Name of an NQA test group.";
      }
    }
  }
  augment /ni:network-instance/ni:instances/ni:instance/l3vpn:afs/l3vpn:af/rt:routing/rt:static-routing/rt:unicast-route2s/rt:unicast-route2/rt:nexthop-vrf-addresses/rt:nexthop-vrf-address/rt:track-setting {
    description
      "Static route track NQA.";
    case nqa {
      description
        "Track NQA.";
      leaf nqa-admin-name {
        type leafref {
          path "/nqa:nqa/nqa:instances/nqa:instance/nqa:admin-name";
        }
        must "../rt:permanent='false' and ../../../rt:topology-name='base' and ../nqa-test-name";
        description
          "Name of an NQA administer instance.";
      }
      leaf nqa-test-name {
        type leafref {
          path "/nqa:nqa/nqa:instances/nqa:instance/nqa:test-name";
        }
        must "../rt:permanent='false' and ../../../rt:topology-name='base' and ../nqa-admin-name";
        description
          "Name of an NQA test instance.";
      }
    }
    case nqa-group {
      description
        "Track NQA group.";
      leaf nqa-group-name {
        type leafref {
          path "/nqa:nqa/nqa:groups/nqa:group/nqa:group-name";
        }
        must "../rt:permanent='false' and ../../../rt:topology-name='base'";
        description
          "Name of an NQA test group.";
      }
    }
  }
  augment /ni:network-instance/ni:instances/ni:instance/l3vpn:afs/l3vpn:af/rt:routing/rt:static-routing/rt:unicast-route2s/rt:unicast-route2/rt:nexthop-vrf-onlys/rt:nexthop-vrf-only/rt:track-setting {
    description
      "Static route track NQA.";
    case nqa {
      description
        "Track NQA.";
      leaf nqa-admin-name {
        type leafref {
          path "/nqa:nqa/nqa:instances/nqa:instance/nqa:admin-name";
        }
        must "../nqa-test-name";
        description
          "Name of an NQA administer instance.";
      }
      leaf nqa-test-name {
        type leafref {
          path "/nqa:nqa/nqa:instances/nqa:instance/nqa:test-name";
        }
        must "../nqa-admin-name";
        description
          "Name of an NQA test instance.";
      }
    }
    case nqa-group {
      description
        "Track NQA group.";
      leaf nqa-group-name {
        type leafref {
          path "/nqa:nqa/nqa:groups/nqa:group/nqa:group-name";
        }
        description
          "Name of an NQA test group.";
      }
    }
  }
  augment /ni:network-instance/ni:instances/ni:instance/l3vpn:afs/l3vpn:af/rt:routing/rt:static-routing/rt:ipv4-routes/rt:ipv4-route {
    description
      "Static route track NQA.";
    leaf nqa-admin-name {
      type leafref {
        path "/nqa:nqa/nqa:instances/nqa:instance/nqa:admin-name";
      }
      must "../nqa-test-name";
      description
        "Name of an NQA administer instance.";
    }
    leaf nqa-test-name {
      type leafref {
        path "/nqa:nqa/nqa:instances/nqa:instance/nqa:test-name";
      }
      must "../nqa-admin-name";
      description
        "Name of an NQA test instance.";
    }
    leaf nqa-group-name {
      type leafref {
        path "/nqa:nqa/nqa:groups/nqa:group/nqa:group-name";
      }
      description
        "Name of an NQA test group.";
    }
  }
  augment /ni:network-instance/ni:instances/ni:instance/l3vpn:afs/l3vpn:af/rt:routing/rt:static-routing/rt:ipv6-routes/rt:ipv6-route {
    description
      "Static route track NQA.";
    leaf nqa-admin-name {
      type leafref {
        path "/nqa:nqa/nqa:instances/nqa:instance/nqa:admin-name";
      }
      must "../nqa-test-name";
      description
        "Name of an NQA administer instance.";
    }
    leaf nqa-test-name {
      type leafref {
        path "/nqa:nqa/nqa:instances/nqa:instance/nqa:test-name";
      }
      must "../nqa-admin-name";
      description
        "Name of an NQA test instance.";
    }
    leaf nqa-group-name {
      type leafref {
        path "/nqa:nqa/nqa:groups/nqa:group/nqa:group-name";
      }
      description
        "Name of an NQA test group.";
    }
  }
  augment /ni:network-instance/ni:instances/ni:instance/l3vpn:afs/l3vpn:af/rt:routing/rt:static-routing/rt:unicast-route2s/rt:unicast-route2/rt:v4-via-v6-interface-addresses/rt:v4-via-v6-interface-address/rt:track-setting {
    description
      "Static route track NQA.";
    case nqa {
      description
        "Track NQA.";
      leaf nqa-admin-name {
        type leafref {
          path "/nqa:nqa/nqa:instances/nqa:instance/nqa:admin-name";
        }
        must "../nqa-test-name";
        description
          "Name of an NQA administer instance.";
      }
      leaf nqa-test-name {
        type leafref {
          path "/nqa:nqa/nqa:instances/nqa:instance/nqa:test-name";
        }
        must "../nqa-admin-name";
        description
          "Name of an NQA test instance.";
      }
    }
    case nqa-group {
      description
        "Track NQA group.";
      leaf nqa-group-name {
        type leafref {
          path "/nqa:nqa/nqa:groups/nqa:group/nqa:group-name";
        }
        description
          "Name of an NQA test group.";
      }
    }
  }
  augment /ni:network-instance/ni:instances/ni:instance/l3vpn:afs/l3vpn:af/rt:routing/rt:static-routing/rt:unicast-route2s/rt:unicast-route2/rt:v4-via-v6-addresses/rt:v4-via-v6-address/rt:track-setting {
    description
      "Static route track NQA.";
    case nqa {
      description
        "Track NQA.";
      leaf nqa-admin-name {
        type leafref {
          path "/nqa:nqa/nqa:instances/nqa:instance/nqa:admin-name";
        }
        must "../nqa-test-name";
        description
          "Name of an NQA administer instance.";
      }
      leaf nqa-test-name {
        type leafref {
          path "/nqa:nqa/nqa:instances/nqa:instance/nqa:test-name";
        }
        must "../nqa-admin-name";
        description
          "Name of an NQA test instance.";
      }
    }
    case nqa-group {
      description
        "Track NQA group.";
      leaf nqa-group-name {
        type leafref {
          path "/nqa:nqa/nqa:groups/nqa:group/nqa:group-name";
        }
        description
          "Name of an NQA test group.";
      }
    }
  }
  augment /ni:network-instance/ni:instances/ni:instance/l3vpn:afs/l3vpn:af/rt:routing/rt:static-routing/rt:unicast-route2s/rt:unicast-route2/rt:v4-via-v6-vrf-addresses/rt:v4-via-v6-vrf-address/rt:track-setting {
    description
      "Static route track NQA.";
    case nqa {
      description
        "Track NQA.";
      leaf nqa-admin-name {
        type leafref {
          path "/nqa:nqa/nqa:instances/nqa:instance/nqa:admin-name";
        }
        must "../nqa-test-name";
        description
          "Name of an NQA administer instance.";
      }
      leaf nqa-test-name {
        type leafref {
          path "/nqa:nqa/nqa:instances/nqa:instance/nqa:test-name";
        }
        must "../nqa-admin-name";
        description
          "Name of an NQA test instance.";
      }
    }
    case nqa-group {
      description
        "Track NQA group.";
      leaf nqa-group-name {
        type leafref {
          path "/nqa:nqa/nqa:groups/nqa:group/nqa:group-name";
        }
        description
          "Name of an NQA test group.";
      }
    }
  }
  augment /ni:network-instance/ni:instances/ni:instance/l3vpn:afs/l3vpn:af/rt:routing/rt:static-routing/rt:unicast-route2s/rt:unicast-route2/rt:nexthop-vrf-vxlans/rt:nexthop-vrf-vxlan/rt:track-setting {
    description
      "Static route track NQA.";
    case nqa {
      description
        "Track NQA.";
      leaf nqa-admin-name {
        type leafref {
          path "/nqa:nqa/nqa:instances/nqa:instance/nqa:admin-name";
        }
        must "../nqa-test-name";
        description
          "Name of an NQA administer instance.";
      }
      leaf nqa-test-name {
        type leafref {
          path "/nqa:nqa/nqa:instances/nqa:instance/nqa:test-name";
        }
        must "../nqa-admin-name";
        description
          "Name of an NQA test instance.";
      }
    }
  }
}
