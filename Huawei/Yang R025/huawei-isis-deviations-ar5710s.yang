/*
Copyright (C) 2025 Huawei Technologies Co., Ltd. All rights reserved.
*/
module huawei-isis-deviations-ar5710s {
  namespace "urn:huawei:yang:huawei-isis-deviations-ar5710s";
  prefix isis-devs-ar5710s;

  import huawei-isis {
    prefix isis;
  }
  import huawei-evpl {
    prefix evpl;
  }
  import huawei-l3vpn {
    prefix l3vpn;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-isis module.";

  revision 2025-02-24 {
    description
      "Initial revision.";
    reference "Huawei private.";
  }

  typedef import-protocol-deviations {
    type enumeration {
      enum direct {
        value 1;
        description
          "Import direct routes.";
      }
      enum ospf {
        value 2;
        description
          "Import OSPF routes.";
      }
      enum isis {
        value 3;
        description
          "Import ISIS routes.";
      }
      enum static {
        value 4;
        description
          "Import static routes.";
      }
      enum rip {
        value 5;
        description
          "Import RIP routes.";
      }
      enum bgp {
        value 6;
        description
          "Import BGP routes.";
      }
      enum ospfv3 {
        value 7;
        description
          "Import OSPFv3 routes.";
      }
      enum ripng {
        value 8;
        description
          "Import RIPng routes.";
      }
    }
    description
      "ISIS import protocol type.";
  }

  deviation "/isis:isis/isis:global/isis:purge-source-trace-enable" {
    deviate not-supported;
  }
  deviation "/isis:isis/isis:global/isis:purge-source-trace-port" {
    deviate not-supported;
  }
  deviation "/isis:isis/isis:global/isis:peer-control-disable" {
    deviate not-supported;
  }
  deviation "/isis:isis/isis:global/isis:session-car" {
    deviate not-supported;
  }
  deviation "/isis:isis/isis:global/isis:micro-isolation-car" {
    deviate not-supported;
  }
  deviation "/isis:isis/isis:network-reliability/isis:adaptive-routing-historys" {
    deviate not-supported;
  }
  deviation "/isis:reset-isis-all" {
    deviate not-supported;
  }
  deviation "/isis:reset-isis-peer" {
    deviate not-supported;
  }
  deviation "/isis:reset-suppress-flapping-peer" {
    deviate not-supported;
  }
  deviation "/ni:network-instance/ni:instances/ni:instance/l3vpn:afs/l3vpn:af/isis:isis-import-rts" {
    deviate not-supported;
  }
  deviation "/ni:network-instance/ni:instances/ni:instance/isis:isis/isis:sites/isis:site/isis:description" {
    deviate not-supported;
  }
  deviation "/ni:network-instance/ni:instances/ni:instance/isis:isis/isis:sites/isis:site/isis:multi-iid" {
    deviate not-supported;
  }
  deviation "/ni:network-instance/ni:instances/ni:instance/isis:isis/isis:sites/isis:site/isis:shutdown" {
    deviate not-supported;
  }
  deviation "/ni:network-instance/ni:instances/ni:instance/isis:isis/isis:sites/isis:site/isis:relax-spf-limit" {
    deviate not-supported;
  }
  deviation "/ni:network-instance/ni:instances/ni:instance/isis:isis/isis:sites/isis:site/isis:direct-inherit" {
    deviate not-supported;
  }
  deviation "/ni:network-instance/ni:instances/ni:instance/isis:isis/isis:sites/isis:site/isis:adv-one-intf-addr" {
    deviate not-supported;
  }
  deviation "/ni:network-instance/ni:instances/ni:instance/isis:isis/isis:sites/isis:site/isis:bfd-session-check" {
    deviate not-supported;
  }
  deviation "/ni:network-instance/ni:instances/ni:instance/isis:isis/isis:sites/isis:site/isis:ipv4-prefix-ipv6-nexthop" {
    deviate not-supported;
  }
  deviation "/ni:network-instance/ni:instances/ni:instance/isis:isis/isis:sites/isis:site/isis:id-consistency-detect" {
    deviate not-supported;
  }
  deviation "/ni:network-instance/ni:instances/ni:instance/isis:isis/isis:sites/isis:site/isis:reverse-cost" {
    deviate not-supported;
  }
  deviation "/ni:network-instance/ni:instances/ni:instance/isis:isis/isis:sites/isis:site/isis:lsp-fragments-extend" {
    deviate not-supported;
  }
  deviation "/ni:network-instance/ni:instances/ni:instance/isis:isis/isis:sites/isis:site/isis:poi-tlv" {
    deviate not-supported;
  }
  deviation "/ni:network-instance/ni:instances/ni:instance/isis:isis/isis:sites/isis:site/isis:lsdb-limit" {
    deviate not-supported;
  }
  deviation "/ni:network-instance/ni:instances/ni:instance/isis:isis/isis:sites/isis:site/isis:suppress-flapping" {
    deviate not-supported;
  }
  deviation "/ni:network-instance/ni:instances/ni:instance/isis:isis/isis:sites/isis:site/isis:timer/isis:lsp-max" {
    deviate not-supported;
  }
  deviation "/ni:network-instance/ni:instances/ni:instance/isis:isis/isis:sites/isis:site/isis:timer/isis:lsp-refresh" {
    deviate not-supported;
  }
  deviation "/ni:network-instance/ni:instances/ni:instance/isis:isis/isis:sites/isis:site/isis:timer/isis:purge-lsp-delay" {
    deviate not-supported;
  }
  deviation "/ni:network-instance/ni:instances/ni:instance/isis:isis/isis:sites/isis:site/isis:lsp-length" {
    deviate not-supported;
  }
  deviation "/ni:network-instance/ni:instances/ni:instance/isis:isis/isis:sites/isis:site/isis:te-set-subtlv" {
    deviate not-supported;
  }
  deviation "/ni:network-instance/ni:instances/ni:instance/isis:isis/isis:sites/isis:site/isis:lsp-lifetime" {
    deviate not-supported;
  }
  deviation "/ni:network-instance/ni:instances/ni:instance/isis:isis/isis:sites/isis:site/isis:bgp-ls/isis:enable-level1" {
    deviate not-supported;
  }
  deviation "/ni:network-instance/ni:instances/ni:instance/isis:isis/isis:sites/isis:site/isis:bgp-ls/isis:enable-level2" {
    deviate not-supported;
  }
  deviation "/ni:network-instance/ni:instances/ni:instance/isis:isis/isis:sites/isis:site/isis:bgp-ls/isis:ignore-level2-leak-level1" {
    deviate not-supported;
  }
  deviation "/ni:network-instance/ni:instances/ni:instance/isis:isis/isis:sites/isis:site/isis:bgp-ls/isis:exclude-ipv4-prefix" {
    deviate not-supported;
  }
  deviation "/ni:network-instance/ni:instances/ni:instance/isis:isis/isis:sites/isis:site/isis:bgp-ls/isis:report-exclude" {
    deviate not-supported;
  }
  deviation "/ni:network-instance/ni:instances/ni:instance/isis:isis/isis:sites/isis:site/isis:bier" {
    deviate not-supported;
  }
  deviation "/ni:network-instance/ni:instances/ni:instance/isis:isis/isis:sites/isis:site/isis:extern-ability" {
    deviate not-supported;
  }
  deviation "/ni:network-instance/ni:instances/ni:instance/isis:isis/isis:sites/isis:site/isis:local-mt" {
    deviate not-supported;
  }
  deviation "/ni:network-instance/ni:instances/ni:instance/isis:isis/isis:sites/isis:site/isis:virtual-systems" {
    deviate not-supported;
  }
  deviation "/ni:network-instance/ni:instances/ni:instance/isis:isis/isis:sites/isis:site/isis:host-names" {
    deviate not-supported;
  }
  deviation "/ni:network-instance/ni:instances/ni:instance/isis:isis/isis:sites/isis:site/isis:circuits/isis:circuit/isis:level" {
    deviate not-supported;
  }
  deviation "/ni:network-instance/ni:instances/ni:instance/isis:isis/isis:sites/isis:site/isis:circuits/isis:circuit/isis:hello-mode" {
    deviate not-supported;
  }
  deviation "/ni:network-instance/ni:instances/ni:instance/isis:isis/isis:sites/isis:site/isis:circuits/isis:circuit/isis:silent-enable" {
    deviate not-supported;
  }
  deviation "/ni:network-instance/ni:instances/ni:instance/isis:isis/isis:sites/isis:site/isis:circuits/isis:circuit/isis:purge-source-trace-block" {
    deviate not-supported;
  }
  deviation "/ni:network-instance/ni:instances/ni:instance/isis:isis/isis:sites/isis:site/isis:circuits/isis:circuit/isis:silent-cost" {
    deviate not-supported;
  }
  deviation "/ni:network-instance/ni:instances/ni:instance/isis:isis/isis:sites/isis:site/isis:circuits/isis:circuit/isis:dis-name" {
    deviate not-supported;
  }
  deviation "/ni:network-instance/ni:instances/ni:instance/isis:isis/isis:sites/isis:site/isis:circuits/isis:circuit/isis:reverse-cost" {
    deviate not-supported;
  }
  deviation "/ni:network-instance/ni:instances/ni:instance/isis:isis/isis:sites/isis:site/isis:circuits/isis:circuit/isis:mesh-group" {
    deviate not-supported;
  }
  deviation "/ni:network-instance/ni:instances/ni:instance/isis:isis/isis:sites/isis:site/isis:circuits/isis:circuit/isis:suppress-flapping" {
    deviate not-supported;
  }
  deviation "/ni:network-instance/ni:instances/ni:instance/isis:isis/isis:sites/isis:site/isis:circuits/isis:circuit/isis:timer" {
    deviate not-supported;
  }
  deviation "/ni:network-instance/ni:instances/ni:instance/isis:isis/isis:sites/isis:site/isis:circuits/isis:circuit/isis:broadcast" {
    deviate not-supported;
  }
  deviation "/ni:network-instance/ni:instances/ni:instance/isis:isis/isis:sites/isis:site/isis:circuits/isis:circuit/isis:p2p/isis:peer-ip-ignore" {
    deviate not-supported;
  }
  deviation "/ni:network-instance/ni:instances/ni:instance/isis:isis/isis:sites/isis:site/isis:circuits/isis:circuit/isis:hello-auths" {
    deviate not-supported;
  }
  deviation "/ni:network-instance/ni:instances/ni:instance/isis:isis/isis:sites/isis:site/isis:circuits/isis:circuit/isis:afs/isis:af/isis:tag-level1" {
    deviate not-supported;
  }
  deviation "/ni:network-instance/ni:instances/ni:instance/isis:isis/isis:sites/isis:site/isis:circuits/isis:circuit/isis:afs/isis:af/isis:tag-level2" {
    deviate not-supported;
  }
  deviation "/ni:network-instance/ni:instances/ni:instance/isis:isis/isis:sites/isis:site/isis:circuits/isis:circuit/isis:afs/isis:af/isis:suppress-reach" {
    deviate not-supported;
  }
  deviation "/ni:network-instance/ni:instances/ni:instance/isis:isis/isis:sites/isis:site/isis:circuits/isis:circuit/isis:afs/isis:af/isis:incr-cost" {
    deviate not-supported;
  }
  deviation "/ni:network-instance/ni:instances/ni:instance/isis:isis/isis:sites/isis:site/isis:circuits/isis:circuit/isis:afs/isis:af/isis:bfd-bit-error" {
    deviate not-supported;
  }
  deviation "/ni:network-instance/ni:instances/ni:instance/isis:isis/isis:sites/isis:site/isis:circuits/isis:circuit/isis:afs/isis:af/isis:mpls-ldp" {
    deviate not-supported;
  }
  deviation "/ni:network-instance/ni:instances/ni:instance/isis:isis/isis:sites/isis:site/isis:circuits/isis:circuit/isis:afs/isis:af/isis:frr/isis:rlfa-disable-level1" {
    deviate not-supported;
  }
  deviation "/ni:network-instance/ni:instances/ni:instance/isis:isis/isis:sites/isis:site/isis:circuits/isis:circuit/isis:afs/isis:af/isis:frr/isis:rlfa-disable-level2" {
    deviate not-supported;
  }
  deviation "/ni:network-instance/ni:instances/ni:instance/isis:isis/isis:sites/isis:site/isis:circuits/isis:circuit/isis:afs/isis:af/isis:bfd/isis:type/isis:track" {
    deviate not-supported;
  }
  deviation "/ni:network-instance/ni:instances/ni:instance/isis:isis/isis:sites/isis:site/isis:circuits/isis:circuit/isis:afs/isis:af/isis:bfd/isis:tos-exp" {
    deviate not-supported;
  }
  deviation "/ni:network-instance/ni:instances/ni:instance/isis:isis/isis:sites/isis:site/isis:circuits/isis:circuit/isis:afs/isis:af/isis:bfd/isis:bfd-incr-cost" {
    deviate not-supported;
  }
  deviation "/ni:network-instance/ni:instances/ni:instance/isis:isis/isis:sites/isis:site/isis:circuits/isis:circuit/isis:afs/isis:af/isis:ldp-sync" {
    deviate not-supported;
  }
  deviation "/ni:network-instance/ni:instances/ni:instance/isis:isis/isis:sites/isis:site/isis:circuits/isis:circuit/isis:afs/isis:af/isis:link-group-ports" {
    deviate not-supported;
  }
  deviation "/ni:network-instance/ni:instances/ni:instance/isis:isis/isis:sites/isis:site/isis:circuits/isis:circuit/isis:afs/isis:af/isis:topologys" {
    deviate not-supported;
  }
  deviation "/ni:network-instance/ni:instances/ni:instance/isis:isis/isis:sites/isis:site/isis:circuits/isis:circuit/isis:afs/isis:af/isis:delay-normalize" {
    deviate not-supported;
  }
  deviation "/ni:network-instance/ni:instances/ni:instance/isis:isis/isis:sites/isis:site/isis:circuits/isis:circuit/isis:afs/isis:af/isis:bandwidth-cost-level1" {
    deviate not-supported;
  }
  deviation "/ni:network-instance/ni:instances/ni:instance/isis:isis/isis:sites/isis:site/isis:circuits/isis:circuit/isis:afs/isis:af/isis:bandwidth-cost-level2" {
    deviate not-supported;
  }
  deviation "/ni:network-instance/ni:instances/ni:instance/isis:isis/isis:sites/isis:site/isis:circuits/isis:circuit/isis:disp-data" {
    deviate not-supported;
  }
  deviation "/ni:network-instance/ni:instances/ni:instance/isis:isis/isis:sites/isis:site/isis:tlv-fragments" {
    deviate not-supported;
  }
  deviation "/ni:network-instance/ni:instances/ni:instance/isis:isis/isis:sites/isis:site/isis:apply-link-cost" {
    deviate not-supported;
  }
  deviation "/ni:network-instance/ni:instances/ni:instance/isis:isis/isis:sites/isis:site/isis:adv-app-link-attr" {
    deviate not-supported;
  }
  deviation "/ni:network-instance/ni:instances/ni:instance/isis:isis/isis:sites/isis:site/isis:peer-hold-max-cost-normalize-on-startup" {
    deviate not-supported;
  }
  deviation "/ni:network-instance/ni:instances/ni:instance/isis:isis/isis:sites/isis:site/isis:afs/isis:af/isis:apply-qppb" {
    deviate not-supported;
  }
  deviation "/ni:network-instance/ni:instances/ni:instance/isis:isis/isis:sites/isis:site/isis:afs/isis:af/isis:max-load-balancing" {
    deviate not-supported;
  }
  deviation "/ni:network-instance/ni:instances/ni:instance/isis:isis/isis:sites/isis:site/isis:afs/isis:af/isis:auto-cost" {
    deviate not-supported;
  }
  deviation "/ni:network-instance/ni:instances/ni:instance/isis:isis/isis:sites/isis:site/isis:afs/isis:af/isis:auto-cost-compatible" {
    deviate not-supported;
  }
  deviation "/ni:network-instance/ni:instances/ni:instance/isis:isis/isis:sites/isis:site/isis:afs/isis:af/isis:bandwidth" {
    deviate not-supported;
  }
  deviation "/ni:network-instance/ni:instances/ni:instance/isis:isis/isis:sites/isis:site/isis:afs/isis:af/isis:cost-level1" {
    deviate not-supported;
  }
  deviation "/ni:network-instance/ni:instances/ni:instance/isis:isis/isis:sites/isis:site/isis:afs/isis:af/isis:cost-level2" {
    deviate not-supported;
  }
  deviation "/ni:network-instance/ni:instances/ni:instance/isis:isis/isis:sites/isis:site/isis:afs/isis:af/isis:bfd-bit-error" {
    deviate not-supported;
  }
  deviation "/ni:network-instance/ni:instances/ni:instance/isis:isis/isis:sites/isis:site/isis:afs/isis:af/isis:default-tag-level1" {
    deviate not-supported;
  }
  deviation "/ni:network-instance/ni:instances/ni:instance/isis:isis/isis:sites/isis:site/isis:afs/isis:af/isis:default-tag-level2" {
    deviate not-supported;
  }
  deviation "/ni:network-instance/ni:instances/ni:instance/isis:isis/isis:sites/isis:site/isis:afs/isis:af/isis:arp-keep-disable" {
    deviate not-supported;
  }
  deviation "/ni:network-instance/ni:instances/ni:instance/isis:isis/isis:sites/isis:site/isis:afs/isis:af/isis:attach-bit" {
    deviate not-supported;
  }
  deviation "/ni:network-instance/ni:instances/ni:instance/isis:isis/isis:sites/isis:site/isis:afs/isis:af/isis:preference/isis:policy-type/isis:route-filter" {
    deviate not-supported;
  }
  deviation "/ni:network-instance/ni:instances/ni:instance/isis:isis/isis:sites/isis:site/isis:afs/isis:af/isis:default-route" {
    deviate not-supported;
  }
  deviation "/ni:network-instance/ni:instances/ni:instance/isis:isis/isis:sites/isis:site/isis:afs/isis:af/isis:import-routes/isis:import-route/isis:policy-type/isis:route-filter-name" {
    deviate not-supported;
  }
  deviation "/ni:network-instance/ni:instances/ni:instance/isis:isis/isis:sites/isis:site/isis:afs/isis:af/isis:import-routes/isis:import-route/isis:nosidflag" {
    deviate not-supported;
  }
  deviation "/ni:network-instance/ni:instances/ni:instance/isis:isis/isis:sites/isis:site/isis:afs/isis:af/isis:import-routes/isis:import-route/isis:no-bier" {
    deviate not-supported;
  }
  deviation "/ni:network-instance/ni:instances/ni:instance/isis:isis/isis:sites/isis:site/isis:afs/isis:af/isis:nexthop-weights" {
    deviate not-supported;
  }
  deviation "/ni:network-instance/ni:instances/ni:instance/isis:isis/isis:sites/isis:site/isis:afs/isis:af/isis:leak-route-level2-to-level1" {
    deviate not-supported;
  }
  deviation "/ni:network-instance/ni:instances/ni:instance/isis:isis/isis:sites/isis:site/isis:afs/isis:af/isis:leak-route-level1-to-level2" {
    deviate not-supported;
  }
  deviation "/ni:network-instance/ni:instances/ni:instance/isis:isis/isis:sites/isis:site/isis:afs/isis:af/isis:summary-prefixs" {
    deviate not-supported;
  }
  deviation "/ni:network-instance/ni:instances/ni:instance/isis:isis/isis:sites/isis:site/isis:afs/isis:af/isis:unreachable-prefix-announcement" {
    deviate not-supported;
  }
  deviation "/ni:network-instance/ni:instances/ni:instance/isis:isis/isis:sites/isis:site/isis:afs/isis:af/isis:traffic-eng/isis:metric-delay" {
    deviate not-supported;
  }
  deviation "/ni:network-instance/ni:instances/ni:instance/isis:isis/isis:sites/isis:site/isis:afs/isis:af/isis:traffic-eng/isis:metric-link-losses" {
    deviate not-supported;
  }
  deviation "/ni:network-instance/ni:instances/ni:instance/isis:isis/isis:sites/isis:site/isis:afs/isis:af/isis:traffic-eng/isis:bandwidth-utilized" {
    deviate not-supported;
  }
  deviation "/ni:network-instance/ni:instances/ni:instance/isis:isis/isis:sites/isis:site/isis:afs/isis:af/isis:traffic-eng/isis:bandwidth" {
    deviate not-supported;
  }
  deviation "/ni:network-instance/ni:instances/ni:instance/isis:isis/isis:sites/isis:site/isis:afs/isis:af/isis:bfd/isis:tos-exp" {
    deviate not-supported;
  }
  deviation "/ni:network-instance/ni:instances/ni:instance/isis:isis/isis:sites/isis:site/isis:afs/isis:af/isis:bfd/isis:bfd-incr-cost" {
    deviate not-supported;
  }
  deviation "/ni:network-instance/ni:instances/ni:instance/isis:isis/isis:sites/isis:site/isis:afs/isis:af/isis:bfd/isis:bfd-incr-cost-wtr" {
    deviate not-supported;
  }
  deviation "/ni:network-instance/ni:instances/ni:instance/isis:isis/isis:sites/isis:site/isis:afs/isis:af/isis:ldp-sync" {
    deviate not-supported;
  }
  deviation "/ni:network-instance/ni:instances/ni:instance/isis:isis/isis:sites/isis:site/isis:afs/isis:af/isis:mpls-ldp-global" {
    deviate not-supported;
  }
  deviation "/ni:network-instance/ni:instances/ni:instance/isis:isis/isis:sites/isis:site/isis:afs/isis:af/isis:prefix-prioritys" {
    deviate not-supported;
  }
  deviation "/ni:network-instance/ni:instances/ni:instance/isis:isis/isis:sites/isis:site/isis:afs/isis:af/isis:frr/isis:policy-type/isis:route-filter" {
    deviate not-supported;
  }
  deviation "/ni:network-instance/ni:instances/ni:instance/isis:isis/isis:sites/isis:site/isis:afs/isis:af/isis:frr/isis:ecmp-level1" {
    deviate not-supported;
  }
  deviation "/ni:network-instance/ni:instances/ni:instance/isis:isis/isis:sites/isis:site/isis:afs/isis:af/isis:frr/isis:ecmp-level2" {
    deviate not-supported;
  }
  deviation "/ni:network-instance/ni:instances/ni:instance/isis:isis/isis:sites/isis:site/isis:afs/isis:af/isis:frr/isis:remote-lfa" {
    deviate not-supported;
  }
  deviation "/ni:network-instance/ni:instances/ni:instance/isis:isis/isis:sites/isis:site/isis:afs/isis:af/isis:frr/isis:tilfa/isis:remote-srlg-level1" {
    deviate not-supported;
  }
  deviation "/ni:network-instance/ni:instances/ni:instance/isis:isis/isis:sites/isis:site/isis:afs/isis:af/isis:frr/isis:tilfa/isis:remote-srlg-level2" {
    deviate not-supported;
  }
  deviation "/ni:network-instance/ni:instances/ni:instance/isis:isis/isis:sites/isis:site/isis:afs/isis:af/isis:filter-import" {
    deviate not-supported;
  }
  deviation "/ni:network-instance/ni:instances/ni:instance/isis:isis/isis:sites/isis:site/isis:afs/isis:af/isis:filter-exports" {
    deviate not-supported;
  }
  deviation "/ni:network-instance/ni:instances/ni:instance/isis:isis/isis:sites/isis:site/isis:afs/isis:af/isis:topologys" {
    deviate not-supported;
  }
  deviation "/ni:network-instance/ni:instances/ni:instance/isis:isis/isis:sites/isis:site/isis:afs/isis:af/isis:delay-normalize" {
    deviate not-supported;
  }
  deviation "/ni:network-instance/ni:instances/ni:instance/isis:isis/isis:sites/isis:site/isis:afs/isis:af/isis:adaptive-routing" {
    deviate not-supported;
  }
  deviation "/ni:network-instance/ni:instances/ni:instance/isis:isis/isis:sites/isis:site/isis:afs/isis:af/isis:route-statisticss" {
    deviate not-supported;
  }
  deviation "/ni:network-instance/ni:instances/ni:instance/isis:isis/isis:sites/isis:site/isis:afs/isis:af/isis:route-counts" {
    deviate not-supported;
  }
  deviation "/ni:network-instance/ni:instances/ni:instance/isis:isis/isis:sites/isis:site/isis:afs/isis:af/isis:ipv4-routes" {
    deviate not-supported;
  }
  deviation "/ni:network-instance/ni:instances/ni:instance/isis:isis/isis:sites/isis:site/isis:afs/isis:af/isis:ipv6-routes" {
    deviate not-supported;
  }
  deviation "/ni:network-instance/ni:instances/ni:instance/isis:isis/isis:sites/isis:site/isis:afs/isis:af/isis:ipv4-import-routes" {
    deviate not-supported;
  }
  deviation "/ni:network-instance/ni:instances/ni:instance/isis:isis/isis:sites/isis:site/isis:afs/isis:af/isis:ipv6-import-routes" {
    deviate not-supported;
  }
  deviation "/ni:network-instance/ni:instances/ni:instance/isis:isis/isis:sites/isis:site/isis:afs/isis:af/isis:ipv6-upa-advertise-routes" {
    deviate not-supported;
  }
  deviation "/ni:network-instance/ni:instances/ni:instance/isis:isis/isis:sites/isis:site/isis:afs/isis:af/isis:ipv6-upa-receive-routes" {
    deviate not-supported;
  }
  deviation "/ni:network-instance/ni:instances/ni:instance/isis:isis/isis:sites/isis:site/isis:afs/isis:af/isis:migp-routes" {
    deviate not-supported;
  }
  deviation "/ni:network-instance/ni:instances/ni:instance/isis:isis/isis:sites/isis:site/isis:afs/isis:af/isis:adaptive-routing-infos" {
    deviate not-supported;
  }
  deviation "/ni:network-instance/ni:instances/ni:instance/isis:isis/isis:sites/isis:site/isis:afs/isis:af/isis:adaptive-routing-historys" {
    deviate not-supported;
  }
  deviation "/ni:network-instance/ni:instances/ni:instance/isis:isis/isis:sites/isis:site/isis:afs/isis:af/isis:l2-bundle" {
    deviate not-supported;
  }
  deviation "/ni:network-instance/ni:instances/ni:instance/isis:isis/isis:sites/isis:site/isis:avoid-micro-loop/isis:sr-enable" {
    deviate not-supported;
  }
  deviation "/ni:network-instance/ni:instances/ni:instance/isis:isis/isis:sites/isis:site/isis:avoid-micro-loop/isis:sr-rib-update-delay" {
    deviate not-supported;
  }
  deviation "/ni:network-instance/ni:instances/ni:instance/isis:isis/isis:sites/isis:site/isis:avoid-micro-loop/isis:te-tunnel-enable" {
    deviate not-supported;
  }
  deviation "/ni:network-instance/ni:instances/ni:instance/isis:isis/isis:sites/isis:site/isis:avoid-micro-loop/isis:te-tunnel-delay" {
    deviate not-supported;
  }
  deviation "/ni:network-instance/ni:instances/ni:instance/isis:isis/isis:sites/isis:site/isis:link-groups" {
    deviate not-supported;
  }
  deviation "/ni:network-instance/ni:instances/ni:instance/isis:isis/isis:sites/isis:site/isis:fad-bindings" {
    deviate not-supported;
  }
  deviation "/ni:network-instance/ni:instances/ni:instance/isis:isis/isis:sites/isis:site/isis:flex-algo" {
    deviate not-supported;
  }
  deviation "/ni:network-instance/ni:instances/ni:instance/isis:isis/isis:sites/isis:site/isis:circ-datas" {
    deviate not-supported;
  }
  deviation "/ni:network-instance/ni:instances/ni:instance/isis:isis/isis:sites/isis:site/isis:bfd-sessions/isis:bfd-session/isis:detect-interval" {
    deviate not-supported;
  }
  deviation "/ni:network-instance/ni:instances/ni:instance/isis:isis/isis:sites/isis:site/isis:bfd-sessions/isis:bfd-session/isis:threshold" {
    deviate not-supported;
  }
  deviation "/ni:network-instance/ni:instances/ni:instance/isis:isis/isis:sites/isis:site/isis:bfd-sessions/isis:bfd-session/isis:incr-cost" {
    deviate not-supported;
  }
  deviation "/ni:network-instance/ni:instances/ni:instance/isis:isis/isis:sites/isis:site/isis:bfd-sessions/isis:bfd-session/isis:wtr-value" {
    deviate not-supported;
  }
  deviation "/ni:network-instance/ni:instances/ni:instance/isis:isis/isis:sites/isis:site/isis:bfd-bit-error-sessions" {
    deviate not-supported;
  }
  deviation "/ni:network-instance/ni:instances/ni:instance/isis:isis/isis:sites/isis:site/isis:peers" {
    deviate not-supported;
  }
  deviation "/ni:network-instance/ni:instances/ni:instance/isis:isis/isis:sites/isis:site/isis:lsdbs" {
    deviate not-supported;
  }
  deviation "/ni:network-instance/ni:instances/ni:instance/isis:isis/isis:sites/isis:site/isis:flex-algo-states" {
    deviate not-supported;
  }
  deviation "/ni:network-instance/ni:instances/ni:instance/isis:isis/isis:sites/isis:site/isis:lsp-statisticss" {
    deviate not-supported;
  }
  deviation "/ni:network-instance/ni:instances/ni:instance/isis:isis/isis:sites/isis:site/isis:name-mappings" {
    deviate not-supported;
  }
  deviation "/ni:network-instance/ni:instances/ni:instance/isis:isis/isis:sites/isis:site/isis:virtual-accesss" {
    deviate not-supported;
  }
  deviation "/ni:network-instance/ni:instances/ni:instance/isis:isis/isis:sites/isis:site/isis:authentication-length-compatible" {
    deviate not-supported;
  }
  deviation "/ni:network-instance/ni:instances/ni:instance/isis:isis/isis:sites/isis:site/isis:circuits/isis:circuit/isis:name" {
    deviate delete {
      must '/ni:network-instance/ni:instances/ni:instance/isis:isis/isis:sites/isis:site/isis:multi-iid or not(/ni:network-instance/ni:instances/ni:instance/isis:isis/isis:sites/isis:site[isis:id != current()/../../../isis:id]/isis:circuits/isis:circuit[isis:name = current()])';
    }
    deviate delete {
      must 'not(/evpl:evpl/evpl:instances/evpl:instance/evpl:interfaces/evpl:interface[evpl:name=current()])';
    }
    deviate add {
      must 'not(/ni:network-instance/ni:instances/ni:instance/isis:isis/isis:sites/isis:site[isis:id != current()/../../../isis:id]/isis:circuits/isis:circuit[isis:name = current()])';
    }
  }
  deviation "/ni:network-instance/ni:instances/ni:instance/isis:isis/isis:sites/isis:site/isis:circuits/isis:circuit/isis:afs/isis:af/isis:bfd/isis:min-rx" {
    deviate replace {
      default "1000";
    }
  }
  deviation "/ni:network-instance/ni:instances/ni:instance/isis:isis/isis:sites/isis:site/isis:circuits/isis:circuit/isis:afs/isis:af/isis:bfd/isis:min-tx" {
    deviate replace {
      default "1000";
    }
  }
  deviation "/ni:network-instance/ni:instances/ni:instance/isis:isis/isis:sites/isis:site/isis:afs/isis:af/isis:ipv6-base-topo" {
    deviate delete {
      must "not(../ipv6-base-topo='ipv6' and ../../../ipv4-prefix-ipv6-nexthop='true')";
    }
  }
  deviation "/ni:network-instance/ni:instances/ni:instance/isis:isis/isis:sites/isis:site/isis:afs/isis:af/isis:import-routes/isis:import-route/isis:protocol" {
    deviate replace {
      type isis-devs-ar5710s:import-protocol-deviations;
    }
  }
  deviation "/ni:network-instance/ni:instances/ni:instance/isis:isis/isis:sites/isis:site/isis:afs/isis:af/isis:advertise-link-attributes/isis:enable" {
    deviate add {
      must "../../type='afipv6' or ../enable='false'";
    }
  }
}
