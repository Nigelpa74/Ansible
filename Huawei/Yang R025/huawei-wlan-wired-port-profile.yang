/*
Copyright (C) 2021-2025 Huawei Technologies Co., Ltd. All rights reserved.
*/
module huawei-wlan-wired-port-profile {
  yang-version 1;
  namespace "urn:huawei:yang:huawei-wlan-wired-port-profile";
  prefix wired-port-prof;
  import huawei-extension {
    prefix ext;
  }
  import huawei-pub-type {
    prefix pub-type;
  }
  import huawei-vlan {
    prefix vlan;
  }
  import huawei-wlan-ap {
    prefix wlan-ap;
  }
  import huawei-wlan-ap-group-profile {
    prefix wlan-apg;
  }

  organization
    "Huawei Technologies Co., Ltd.";
  contact
    "Huawei Industrial Base
     Bantian, Longgang
     Shenzhen 518129
     People's Republic of China
     Website: http://www.huawei.com
     Email: support@huawei.com";
  description
    "Wired port profile configuration service package.";
  revision 2025-09-19 {
    description
      "Modify error words.";
    reference
      "Huawei private.";
  }
  revision 2025-08-06 {
    description
      "Expand the index range of multige ports and XGe ports.";
    reference
      "Huawei private.";
  }
  revision 2025-03-06 {
    description
      "Delete dot1x-client-profile.";
    reference
      "Huawei private.";
  }
  revision 2025-02-27 {
    description
      "Modify profile-name.";
    reference
      "Huawei private.";
  }
  revision 2025-01-23 {
    description
      "Add binding-dot1x-client-profile.";
    reference
      "Huawei private.";
  }
  revision 2025-01-10 {
    description
      "Add traffic-remarks, multicast-suppression, unicast-suppression, broadcast-suppression, forward-mode and traffic-filter-statistics-switch.";
    reference
      "Huawei private.";
  }
  revision 2024-12-18 {
    description
      "Add voice-VLAN.";
    reference
      "Huawei private.";
  }
  revision 2024-09-14 {
    description
      "Add default cfg generated by system.";
    reference
      "Huawei private.";
  }
  revision 2024-06-13 {
    description
      "Add MACsec.";
    reference
      "Huawei private.";
  }
  revision 2024-05-16 {
    description
      "The default profile cannot be deleted.";
    reference
      "Huawei private.";
  }
  revision 2023-12-29 {
    description
      "Add poe legacy-enable, power-off-time-range, and power-enable.";
    reference
      "Huawei private.";
  }
  revision 2023-12-14 {
    description
      "Add mode and user-isolate.";
    reference
      "Huawei private.";
  }
  revision 2023-09-21 {
    description
      "Modify the data type of tagged-vlan/untagged-vlan.";
    reference
      "Huawei private.";
  }
  revision 2023-07-10 {
    description
      "Add port-description.";
    reference
      "Huawei private.";
  }
  revision 2023-02-02 {
    description
      "Modify stp auto-shutdown-recovery-time.";
    reference
      "Huawei private.";
  }
  revision 2022-12-26 {
    description
      "Add eth-trunk/learn-client-address for IPv6/stp auto-shutdown-recovery-time.";
    reference
      "Huawei private.";
  }
  revision 2021-12-25 {
    description
      "Initial revision.";
    reference
      "Huawei private.";
  }
  grouping wiredport-containers {
    description
      "Wired port configurations.";
    leaf description {
      type string {
        length "1..242";
      }
      description
        "Configure the description of the port.";
    }
    leaf mode {
      type enumeration {
        enum "auto" {
          value 0;
          description
            "Default auto mode.";
        }
        enum "root" {
          value 1;
          description
            "Root mode.";
        }
        enum "endpoint" {
          value 2;
          description
            "Endpoint mode.";
        }
        enum "middle" {
          value 3;
          description
            "Middle mode.";
        }
      }
      default "auto";
      description
        "Configure the mode of the port.";
    }
    leaf user-isolate {
      type enumeration {
        enum "disable" {
          value 0;
          description
            "User-isolate disable.";
        }
        enum "all" {
          value 1;
          description
            "User-isolate all.";
        }
        enum "l2" {
          value 2;
          description
            "User-isolate l2.";
        }
      }
      default "disable";
      description
        "The isolation function prevents users from communicating with each other.";
    }
    leaf pvid {
      type vlan:vlan-id;
      description
        "The pvid of the port.";
    }
    leaf tagged-vlan {
      type pub-type:vlan-range;
      description
        "Configure tagged-VLAN list.";
    }
    leaf untagged-vlan {
      type union {
        type pub-type:vlan-range;
        type string {
          pattern "-";
        }
      }
      default "1";
      description
        "Configure untagged-VLAN list.";
    }
    leaf eth-trunk {
      type uint8 {
        range "0..1";
      }
      description
        "Specifies the ID of the Eth-Trunk.";
    }
    leaf learn-client-address-ipv4 {
      type boolean;
      default "false";
      description
        "Enable/disable the function of client address learning.";
    }
    leaf learn-client-address-ipv6 {
      type boolean;
      default "false";
      description
        "Enable/disable the function of client IPv6 address learning.";
    }
    leaf dai {
      type boolean;
      default "false";
      description
        "Enable/disable the function of Dynamic ARP detection.";
    }
    leaf ipsg {
      type boolean;
      default "false";
      description
        "Enable/disable the function of IP packet binding check.";
    }
    leaf igmp-snooping {
      type boolean;
      default "false";
      description
        "Enable/disable the function of IGMP Snooping.";
    }
    leaf dhcp-trust-port {
      type boolean;
      default "true";
      description
        "Enable/disable the function of DHCP Trust.";
    }
    container stp {
      description
        "Configure the function of stp.";
      leaf switch {
        type enumeration {
          enum "disable" {
            value 0;
            description
              "Stp disable.";
          }
          enum "enable" {
            value 1;
            description
              "Stp enable.";
          }
          enum "auto" {
            value 2;
            description
              "Stp auto.";
          }
        }
        default "auto";
        description
          "Configure stp switch.";
      }
      leaf auto-shutdown-enable {
        type boolean;
        default "false";
        description
          "Enable/disable stp auto shutdown.";
      }
      leaf auto-shutdown-recovery-time {
        when "../auto-shutdown-enable = 'true'";
        type uint16 {
          range "600..3600";
        }
        units "s";
        default "600";
        description
          "The auto-recovery interval for an AP's wired interface on which the STP-triggered port shutdown function is enabled.";
      }
    }
    container port-security {
      description
        "Configure the function of port security.";
      leaf enable {
        type boolean;
        default "false";
        description
          "Enable/disable port security.";
      }
      leaf max-mac-num {
        when "../enable='true'";
        type uint8 {
          range "1..64";
        }
        description
          "Configure the maximum number of secure MAC addresses.";
      }
      leaf protect-action {
        when "../enable='true'";
        type enumeration {
          enum "protect" {
            value 0;
            description
              "Configure protect.";
          }
          enum "restrict" {
            value 1;
            description
              "Configure restrict.";
          }
        }
        default "restrict";
        description
          "Configure the protection action.";
      }
      leaf mac-address-sticky {
        when "../enable='true'";
        type boolean;
        default "false";
        description
          "Enable/disable the function of Sticky MAC.";
      }
    }
    container traffic-optimize {
      description
        "Configure the function of traffic optimize.";
      leaf tcp-adjust-mss {
        type uint16 {
          range "128..2048";
        }
        description
          "Configure the Maximum TCP packet.";
      }
      leaf broadcast-suppression {
        type uint32 {
          range "0..14881000";
        }
        units "pps";
        description
          "Configure broadcast-suppression.";
      }
      leaf multicast-suppression {
        type uint32 {
          range "0..14881000";
        }
        units "pps";
        description
          "Configure multicast-suppression.";
      }
      leaf unicast-suppression {
        type uint32 {
          range "0..14881000";
        }
        units "pps";
        description
          "Configure unicast-suppression.";
      }
    }
    container traffic-filters {
      description
        "List of traffic filter.";
      list traffic-filter {
        must "((./ipv4-acl-number != 0 or ./l2-acl-number != 0) and ./ipv6-acl-number = 0) or (./ipv4-acl-number = 0 and ./l2-acl-number = 0 and ipv6-acl-number != 0)";
        key "direction ipv4-acl-number l2-acl-number ipv6-acl-number";
        max-elements 16;
        description
          "Configure traffic filter.";
        leaf direction {
          type enumeration {
            enum "inbound" {
              value 0;
              description
                "Filtering package in incoming.";
            }
            enum "outbound" {
              value 1;
              description
                "Filtering package in outgoing.";
            }
          }
          description
            "Direction of traffic filter configure.";
        }
        leaf ipv4-acl-number {
          type uint32 {
            range "0|3000..3031";
          }
          description
            "IPv4 ACL.";
        }
        leaf l2-acl-number {
          type uint32 {
            range "0|4000..4031";
          }
          description
            "L2 ACL.";
        }
        leaf ipv6-acl-number {
          type uint32 {
            range "0|3000..3031";
          }
          description
            "IPv6 ACL.";
        }
      }
    }
    leaf traffic-filter-statistics-switch {
      type boolean;
      default false;
      description
        "Enable/disable traffic-filter statistics.";
    }
    container traffic-remarks {
      presence "Create traffic remark policy";
      description
        "List of traffic remark.";
      list traffic-remark {
        must "((./ipv4-acl-number != 0 or ./l2-acl-number != 0) and ./ipv6-acl-number = 0) or (./ipv4-acl-number = 0 and ./l2-acl-number = 0 and ipv6-acl-number != 0)";
        key "direction ipv4-acl-number l2-acl-number ipv6-acl-number";
        description
          "Configure traffic remark.";
        leaf direction {
          type enumeration {
            enum "inbound" {
              value 0;
              description
                "Filtering package in incoming.";
            }
            enum "outbound" {
              value 1;
              description
                "Filtering package in outgoing.";
            }
          }
          description
            "Direction of traffic remark Configure.";
        }
        leaf ipv4-acl-number {
          type uint32 {
            range "0|3000..3031";
          }
          description
            "IPv4 ACL.";
        }
        leaf l2-acl-number {
          type uint32 {
            range "0|4000..4031";
          }
          description
            "L2 ACL.";
        }
        leaf ipv6-acl-number {
          type uint32 {
            range "0|3000..3031";
          }
          description
            "IPv6 ACL.";
        }
        choice dscp-or-dot1p {
          mandatory true;
          description
            "Configure dscp-or-dot1p.";
          case dscp {
            leaf dscp {
              type uint8 {
                range "0..63";
              }
              description
                "Configure dscp value.";
            }
            description
              "Remark dscp.";
          }
          case dot1p {
            leaf dot1p {
              type uint8 {
                range "0..7";
              }
              description
                "Configure dot1p value.";
            }
            description
              "Remark dot1p.";
          }
        }
      }
    }
    container poe {
      description
        "Configure the list of Ethernet power supply.";
		leaf legacy-enable {
          type boolean;
          default "false";
          description
            "Enable/disable PoE legacy.";
        }
	    leaf power-off-time-range {
          type string {
            length "1..32";
          }
          description
          "Specifies PoE power-off time range on the interface. If the current time is within the specified time range, the remote PD connected to the interface cannot be powered on.";
        }
        leaf power-enable {
          type boolean;
          default "true";
          description
            "Enable/disable PoE power supply on the interface.";
        }
    }
    container macsec {
      presence "Configure MACsec CKN and CAK";
      description
        "Configure MACsec secure connectivity association name and key.";
      leaf ckn {
        ext:case-sensitivity "upper2lower";
        type string {
          length "2..64";
        }
        mandatory true;
        description
          "The value of CKN. CKN is an even number in hexadecimal notation, containing at least one digit and one letter. The letters are case-insensitive.";
      }
      leaf cak {
        type pub-type:password-extend;
        mandatory true;
        description
          "The value of CAK. CAK is a hexadecimal notation. If cak is a cleartext character string, it is case-insensitive. If cak is a ciphertext character string, it is case-sensitive. It must be different from CKN. The length of CAK can only be 32 or 64 bits, but in the case of encryption mode, the length can be more than 100 bits, so the length range is defined as 1 to 432. Before configuring a 64-bit CAK, you must configure a 256-bit cipher suite.";
      }
    }
    container voice-vlan {
      description "Configure voice VLAN function.";
      leaf vlan-id {
        type vlan:vlan-id {
          range "2..4094";
        }
        description
          "Voice VLAN ID.";
      }
    }
    leaf forward-mode {
      type enumeration {
        enum "direct" {
          value 1;
          description
            "The forward-mode is direct.";
        }
        enum "tunnel" {
          value 2;
          description
            "The forward-mode is tunnel.";
        }
      }
      default "direct";
      description
        "The service forwarding mode.";
    }
    container binding-dot1x-client-profile {
      description
        "Configure the dot1x client function.";
      leaf profile-name {
        type string {
          length "1..31";
        }
        description
          "The name of dot1x client profile.";
      }
      leaf pki-realm {
        when "../profile-name";
        type enumeration {
          enum "user-define" {
            value 0;
            description
              "PKI realm user-define.";
          }
          enum "default" {
            value 1;
            description
              "PKI realm default.";
          }
        }
        default "user-define";
        description
          "PKI realm for dot1x client.";
      }
    }
  }
  grouping ap-binding-wiredport-profiles {
    description
      "Binding wired-port profiles.";
    container eth-trunk-instances {
      description
        "List of Eth-Trunk instances.";
      list eth-trunk-instance {
        key "index";
        description
          "Configure Eth-Trunk instance.";
        leaf index {
          type uint8 {
            range "0..1";
          }
          description
            "The index of eth-trunk.";
        }
        leaf bind-wiredport-profile {
          type leafref {
            path "/wired-port-prof:wlan-wired-port-profile/wired-port-prof:wiredport-profiles/wired-port-prof:wiredport-profile/wired-port-prof:profile-name";
          }
          description
            "Binding a wired port profile to a Eth-Trunk interface.";
        }
      }
    }
    container ethernet-instances {
      description
        "List of ethernet instances.";
      list ethernet-instance {
        key "index";
        description
          "Configure ethernet instance.";
        leaf index {
          type uint8 {
            range "0..3";
          }
          description
            "The index of ethernet.";
        }
        leaf bind-wiredport-profile {
          type leafref {
            path "/wired-port-prof:wlan-wired-port-profile/wired-port-prof:wiredport-profiles/wired-port-prof:wiredport-profile/wired-port-prof:profile-name";
          }
          description
            "Binding a wired port profile to a ethernet interface.";
        }
      }
    }
    container ge-instances {
      description
        "List of ge instances.";
      list ge-instance {
        key "index";
        description
          "Configure ge instance.";
        leaf index {
          type uint8 {
            range "0..27";
          }
          description
            "The index of ge.";
        }
        leaf bind-wiredport-profile {
          type leafref {
            path "/wired-port-prof:wlan-wired-port-profile/wired-port-prof:wiredport-profiles/wired-port-prof:wiredport-profile/wired-port-prof:profile-name";
          }
          description
            "Binding a wired port profile to a ge interface.";
        }
      }
    }
    container multige-instances {
      description
        "List of multige instances.";
      list multige-instance {
        key "index";
        description
          "Configure multige instance.";
        leaf index {
          type uint8 {
            range "0..7";
          }
          description
            "The index of multige.";
        }
        leaf bind-wiredport-profile {
          type leafref {
            path "/wired-port-prof:wlan-wired-port-profile/wired-port-prof:wiredport-profiles/wired-port-prof:wiredport-profile/wired-port-prof:profile-name";
          }
          description
            "Binding a wired port profile to a multige interface.";
        }
      }
    }
    container xge-instances {
      description
        "List of xgigabitethernet instances.";
      list xge-instance {
        key "index";
        description
          "Configure xgigabitethernet instance.";
        leaf index {
          type uint8 {
            range "0..7";
          }
          description
            "The index of xgigabitethernet.";
        }
        leaf bind-wiredport-profile {
          type leafref {
            path "/wired-port-prof:wlan-wired-port-profile/wired-port-prof:wiredport-profiles/wired-port-prof:wiredport-profile/wired-port-prof:profile-name";
          }
          description
            "Binding a wired port profile to a xgigabitethernet interface.";
        }
      }
    }
  }
  grouping group-binding-wiredport-profiles {
    description
      "Binding wired-port profiles.";
    container eth-trunk-instances {
      description
        "List of Eth-Trunk instances.";
      list eth-trunk-instance {
        ext:generated-by system {
          ext:filter "index='0' or index='1'";
          description
            "The Eth-Trunk instance is generated by system.";
        }
        ext:operation-exclude "delete" {
          ext:filter "index='0' or index='1'";
          description
            "The Eth-Trunk instance cannot be deleted.";
        }
        key "index";
        description
          "Configure Eth-Trunk instance.";
        leaf index {
          type uint8 {
            range "0..1";
          }
          description
            "The index of eth-trunk.";
        }
        leaf bind-wiredport-profile {
          type leafref {
            path "/wired-port-prof:wlan-wired-port-profile/wired-port-prof:wiredport-profiles/wired-port-prof:wiredport-profile/wired-port-prof:profile-name";
          }
          default "default";
          description
            "Binding a wired port profile to a Eth-Trunk interface.";
        }
      }
    }
    container ethernet-instances {
      description
        "List of ethernet instances.";
      list ethernet-instance {
        ext:generated-by system {
          ext:filter "index='0' or index='1' or index='2' or index='3'";
          description
            "The FE instance is generated by system.";
        }
        ext:operation-exclude "delete" {
          ext:filter "index='0' or index='1' or index='2' or index='3'";
          description
            "The FE instance cannot be deleted.";
        }
        key "index";
        description
          "Configure ethernet instance.";
        leaf index {
          type uint8 {
            range "0..3";
          }
          description
            "The index of ethernet.";
        }
        leaf bind-wiredport-profile {
          type leafref {
            path "/wired-port-prof:wlan-wired-port-profile/wired-port-prof:wiredport-profiles/wired-port-prof:wiredport-profile/wired-port-prof:profile-name";
          }
          default "default";
          description
            "Binding a wired port profile to a ethernet interface.";
        }
      }
    }
    container ge-instances {
      description
        "List of ge instances.";
      list ge-instance {
        ext:generated-by system {
          ext:filter "index='0' or index='1' or index='2' or index='3' or index='4' or index='5' or index='6' or index='7' or index='8' or index='9' or index='10' or index='11' or index='12' or index='13' or index='14' or index='15' or index='16' or index='17' or index='18' or index='19' or index='20' or index='21' or index='22' or index='23' or index='24' or index='25' or index='26' or index='27'";
          description
            "The GE instance is generated by system.";
        }
        ext:operation-exclude "delete" {
          ext:filter "index='0' or index='1' or index='2' or index='3' or index='4' or index='5' or index='6' or index='7' or index='8' or index='9' or index='10' or index='11' or index='12' or index='13' or index='14' or index='15' or index='16' or index='17' or index='18' or index='19' or index='20' or index='21' or index='22' or index='23' or index='24' or index='25' or index='26' or index='27'";
          description
            "The GE instance cannot be deleted.";
        }
        key "index";
        description
          "Configure ge instance.";
        leaf index {
          type uint8 {
            range "0..27";
          }
          description
            "The index of ge.";
        }
        leaf bind-wiredport-profile {
          type leafref {
            path "/wired-port-prof:wlan-wired-port-profile/wired-port-prof:wiredport-profiles/wired-port-prof:wiredport-profile/wired-port-prof:profile-name";
          }
          default "default";
          description
            "Binding a wired port profile to a ge interface.";
        }
      }
    }
    container multige-instances {
      description
        "List of multige instances.";
      list multige-instance {
        ext:generated-by system {
          ext:filter "index='0' or index='1' or index='2' or index='3' or index='4' or index='5' or index='6' or index='7'";
          description
            "The MultiGE instance is generated by system.";
        }
        ext:operation-exclude "delete" {
          ext:filter "index='0' or index='1' or index='2' or index='3' or index='4' or index='5' or index='6' or index='7'";
          description
            "The MultiGE instance cannot be deleted.";
        }
        key "index";
        description
          "Configure multige instance.";
        leaf index {
          type uint8 {
            range "0..7";
          }
          description
            "The index of multige.";
        }
        leaf bind-wiredport-profile {
          type leafref {
            path "/wired-port-prof:wlan-wired-port-profile/wired-port-prof:wiredport-profiles/wired-port-prof:wiredport-profile/wired-port-prof:profile-name";
          }
          default "default";
          description
            "Binding a wired port profile to a multige interface.";
        }
      }
    }
    container xge-instances {
      description
        "List of xgigabitethernet instances.";
      list xge-instance {
        ext:generated-by system {
          ext:filter "index='0' or index='1' or index='2' or index='3' or index='4' or index='5' or index='6' or index='7'";
          description
            "The XGE instance is generated by system.";
        }
        ext:operation-exclude "delete" {
          ext:filter "index='0' or index='1' or index='2' or index='3' or index='4' or index='5' or index='6' or index='7'";
          description
            "The XGE instance cannot be deleted.";
        }
        key "index";
        description
          "Configure xgigabitethernet instance.";
        leaf index {
          type uint8 {
            range "0..7";
          }
          description
            "The index of xgigabitethernet.";
        }
        leaf bind-wiredport-profile {
          type leafref {
            path "/wired-port-prof:wlan-wired-port-profile/wired-port-prof:wiredport-profiles/wired-port-prof:wiredport-profile/wired-port-prof:profile-name";
          }
          default "default";
          description
            "Binding a wired port profile to a xgigabitethernet interface.";
        }
      }
    }
  }
  container wlan-wired-port-profile {
    description
      "Configure wired port profile.";
    container wiredport-profiles {
      description
        "List of wired port profiles.";
      list wiredport-profile {
        ext:generated-by "system" {
          description
            "The default profile is generated by system.";
          ext:filter "profile-name='default'";
        }
        ext:operation-exclude "delete" {
          ext:filter "profile-name='default'";
          description
            "The default profile cannot be deleted.";
        }
        key "profile-name";
        description
          "Configure a wired port profile.";
        leaf profile-name {
          type string {
            length "1..35";
            pattern '[^\s?]+';
            pattern '[!-~]+';
          }
          description
            "The wired port profile name.";
        }
        uses wired-port-prof:wiredport-containers;
      }
    }
  }
  augment /wlan-ap:wlan-ap/wlan-ap:ap-instances/wlan-ap:ap-instance {
    description
      "Applying the wired port profile configuration to an AP instance.";
    uses wired-port-prof:ap-binding-wiredport-profiles;
  }
  augment "/wlan-apg:wlan-ap-group-profile/wlan-apg:ap-group-profiles/wlan-apg:ap-group-profile" {
    description
      "Applying the wired port profile configuration to an AP group.";
    uses wired-port-prof:group-binding-wiredport-profiles;
  }
  ext:task-name "pcm";
}
