/*
Copyright (C) 2025 Huawei Technologies Co., Ltd. All rights reserved.
*/
module huawei-ftps-deviations-ar5710s {
  namespace "urn:huawei:yang:huawei-ftps-deviations-ar5710s";
  prefix ftps-devs-ar5710s;

  import huawei-ftps {
    prefix ftps;
  }
  import huawei-acl {
    prefix acl;
  }

  organization
    "Huawei Technologies Co., Ltd.";
  contact
    "Huawei Industrial Base
     Bantian, Longgang
     Shenzhen 518129
     People's Republic of China
     Website: http://www.huawei.com
     Email: support@huawei.com";
  description
    "This module defines deviation statements for huawei-ftps module.";

  revision 2025-02-24 {
    description
      "Initial revision.";
    reference "Huawei private.";
  }

  deviation "/ftps:ftps/ftps:ipv4-isolate-server-sources" {
    deviate not-supported;
  }
  deviation "/ftps:ftps/ftps:ipv6-isolate-server-sources" {
    deviate not-supported;
  }
  deviation "/ftps:ftps/ftps:session-car" {
    deviate not-supported;
  }
  deviation "/ftps:ftps/ftps:server/ftps:acl4-name-or-number" {
    deviate delete {
      must "/acl:acl/acl:groups/acl:group[acl:identity=current()]/acl:type='basic' or /acl:acl/acl:groups/acl:group[acl:identity=current()]/acl:type='advance' or /acl:acl/acl:groups/acl:group[acl:number=number(current())]/acl:type='basic' or /acl:acl/acl:groups/acl:group[acl:number=number(current())]/acl:type='advance'";
    }
    deviate add {
      must "/acl:acl/acl:groups/acl:group[acl:identity=current()]/acl:type='basic' or /acl:acl/acl:groups/acl:group[acl:identity=current()]/acl:type='advance'";
    }
  }
}
