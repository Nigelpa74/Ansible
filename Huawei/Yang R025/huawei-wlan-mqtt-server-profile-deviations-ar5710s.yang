/*
Copyright (C) 2019 Huawei Technologies Co., Ltd. All rights reserved.
*/
module huawei-wlan-mqtt-server-profile-deviations-ar5710s {
  yang-version 1;
  namespace "urn:huawei:yang:huawei-wlan-mqtt-server-profile-deviations-ar5710s";
  prefix mqtt-server-prof-devs-ar5710s;

  import huawei-wlan-mqtt-server-profile {
    prefix mqtt-server-prof;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-mqtt-server-profile module.";

  revision 2019-11-06 {
    description
      "Initial revision.";
    reference "Huawei private.";
  }

  deviation "/mqtt-server-prof:wlan-mqtt-server-profile" {
    deviate not-supported;
  }
}
