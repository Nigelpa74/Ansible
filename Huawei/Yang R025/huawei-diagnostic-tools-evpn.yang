/*
Copyright (C) 2019-2024 Huawei Technologies Co., Ltd. All rights reserved.
*/
submodule huawei-diagnostic-tools-evpn {
  yang-version 1;
  belongs-to huawei-diagnostic-tools {
    prefix diagnostic-tools;
  }

  import ietf-inet-types {
    prefix inet;
  }
  import huawei-pub-type {
    prefix pub-type;
  }
  import huawei-extension {
    prefix ext;
  }
  import huawei-ifm {
    prefix ifm;
  }
  include huawei-diagnostic-tools-common;
  include huawei-diagnostic-tools-type;

  organization
    "Huawei Technologies Co., Ltd.";
  contact
    "Huawei Industrial Base
     Bantian, Longgang
     Shenzhen 518129
     People's Republic of China
     Website: http://www.huawei.com
     Email: support@huawei.com";
  description
    "Evpn diagnosis tool.";
  revision 2024-01-12 {
    description
      "EVPN vpws ping add source-if-name.";
    reference
      "Huawei private.";
  }
  revision 2022-06-27 {
    description
      "Delete the default value of packet-size in evpn vpws trace.";
    reference
      "Huawei private.";
  }
  revision 2022-03-19 {
    description
      "Deleted path-index due to incompatible changes.";
    reference
      "Huawei private.";
  }
  revision 2022-02-08 {
    description
      "Modify leaf type of ce-id.";
    reference
      "Huawei private.";
  }
  revision 2020-01-14 {
    description
      "Add space.";
    reference
      "Huawei private.";
  }
  revision 2020-01-07 {
    description
      "Modify description of end-op.";
    reference
      "Huawei private.";
  }
  revision 2019-12-19 {
    description
      "Modify container ds-label-lists.";
    reference
      "Huawei private.";
  }
  revision 2019-12-14 {
    description
      "Container added for list.";
    reference
      "Huawei private.";
  }
  revision 2019-04-12 {
    description
      "Init revision.";
    reference
      "Huawei private.";
  }

  grouping evpn-ping-trace-result-type {
    description
      "Description of evpn-ping-trace-result-type.";
    container mac-ping-results {
      config false;
      description
        "List of test result.";
      list mac-ping-result {
        key "test-name";
        description
          "Statistics of test result of a certain hop in the test path. For a ping-type test, there is only one test result.";
        leaf test-name {
          type string {
            length "1..32";
          }
          description
            "Test name.";
        }
        leaf evpn-name {
          type string {
            length "1..31";
          }
          description
            "EVPN instance name.";
        }
        leaf bd-id {
          type uint32 {
            range "1..16777215";
          }
          description
            "The ID of bridge-domain.";
        }
        leaf mac {
          type pub-type:mac-address;
          description
            "Mac address.";
        }
        leaf packet-send {
          type uint32;
          description
            "Total number of sent packets.";
        }
        leaf packet-receive {
          type uint32;
          description
            "Total number of received packets.";
        }
        leaf loss-ratio {
          type pub-type:percent {
            range "0..100";
          }
          units "%";
          description
            "Packet loss ratio of a test.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        leaf status {
          type dgntl-test-status-type;
          description
            "Test status.";
        }
        container probes {
          description
            "List of EVPN MAC ping results of all packets in a test.";
          list probe {
            key "sequence";
            description
              "Statistics of get the response result of a single packet in a EVPN MAC ping test.";
            leaf sequence {
              type uint32 {
                range "1..4294967295";
              }              
              description
                "Serial number of a test packet received.";
            }
            leaf replier {
              type inet:ip-address-no-zone;
              description
                "Reply address in a received response packet.";
            }
            leaf data-bytes {
              type uint32;
              description
                "Number of bytes in a received response packet.";
            }
            leaf rtt {
              type uint32;
              units "ms";
              description
                "RTT of test packets.";
            }
            leaf result-type {
              type probe-result-type;
              description
                "Result of packet sending, which is either success or timeout.";
            }
            leaf is-delete {
              ext:support-filter "true";
              type boolean;
              description
                "Enable/disable the function of deleting test results.";
            }
          }
        }
      }
    }
    container multi-mac-ping-results {
      config false;
      description
        "List of EVPN MAC ping test result.";
      list multi-mac-ping-result {
        key "test-name path-index";
        description
          "Statistics of EVPN MAC ping test result.";
        leaf test-name {
          type string {
            length "1..32";
          }
          description
            "Test name.";
        }
        leaf path-index {
          type uint32 {
            range "1..4294967295";
          }
          description
            "Index of path.";
        }
        leaf evpn-name {
          type string {
            length "1..31";
          }
          description
            "EVPN instance name.";
        }
        leaf bd-id {
          type uint32 {
            range "1..16777215";
          }
          description
            "The ID of bridge-domain.";
        }
        leaf mac {
          type pub-type:mac-address;
          description
            "Mac address.";
        }
        leaf packet-send {
          type uint32;
          description
            "Total number of sent packets.";
        }
        leaf packet-receive {
          type uint32;
          description
            "Total number of received packets.";
        }
        leaf loss-ratio {
          type pub-type:percent {
            range "0..100";
          }
          units "%";
          description
            "Packet loss ratio of a test.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        leaf status {
          type dgntl-test-status-type;
          description
            "Test status.";
        }
        leaf path-status {
          type dgntl-test-status-type;
          description
            "Path test status.";
        }
        leaf tunnel-type {
          type dgntl-evpn-tunnel-type;
          description
            "Tunnel type.";
        }
        leaf peer-address {
          type inet:ip-address-no-zone;
          description
            "Peer address of the tunnel.";
        }
        container probes {
          description
            "List of EVPN MAC ping results of all packets in a test.";
          list probe {
            key "sequence";
            description
              "Statistics of get the response result of a single packet in a EVPN MAC ping test.";
            leaf sequence {
              type uint32 {
                range "1..4294967295";
              }
              description
                "Serial number of a test packet received.";
            }
            leaf replier {
              type inet:ip-address-no-zone;
              description
                "Reply address in a received response packet.";
            }
            leaf data-bytes {
              type uint32;
              description
                "Number of bytes in a received response packet.";
            }
            leaf rtt {
              type uint32;
              units "ms";
              description
                "RTT of test packets.";
            }
            leaf result-type {
              type probe-result-type;
              description
                "Result of packet sending, which is either success or timeout.";
            }
            leaf is-delete {
              ext:support-filter "true";
              type boolean;
              description
                "Enable/disable the function of deleting test results.";
            }
          }
        }
      }
    }
    container mac-trace-results {
      config false;
      description
        "List of EVPN MAC trace test result.";
      list mac-trace-result {
        key "test-name path-index";
        description
          "Statistics of EVPN MAC trace test result.";
        leaf test-name {
          type string {
            length "1..32";
          }
          description
            "Test name.";
        }
        leaf path-index {
          type uint32 {
            range "1..4294967295";
          }
          description
            "Index of path.";
        }
        leaf evpn-name {
          type string {
            length "1..31";
          }
          description
            "EVPN instance name.";
        }
        leaf bd-id {
          type uint32 {
            range "1..16777215";
          }
          description
            "The ID of bridge-domain.";
        }
        leaf mac {
          type pub-type:mac-address;
          description
            "Mac address.";
        }
        leaf status {
          type dgntl-test-status-type;
          description
            "Test status.";
        }
        leaf path-status {
          type dgntl-test-status-type;
          description
            "Path test status.";
        }
        leaf tunnel-type {
          type dgntl-evpn-tunnel-type;
          description
            "Tunnel type.";
        }
        leaf peer-address {
          type inet:ip-address-no-zone;
          description
            "Peer address of the tunnel.";
        }
        container hops {
          description
            "List of hop results.";
          list hop {
            key "hop-index packet-index";
            description
              "Statistics of hop results.";
            leaf hop-index {
              type uint32 {
                range "1..4294967295";
              }
              description
                "The index of the hop.";
            }
            leaf packet-index {
              type uint32 {
                range "1..4294967295";
              }
              description
                "The index of the receive packet.";
            }
            leaf replier {
              type inet:ip-address-no-zone;
              description
                "Reply address of the related hop in a test.";
            }
            leaf rtt {
              type uint32;
              units "ms";
              description
                "RTT of test packets.";
            }
            leaf type {
              type transmit-type;
              description
                "Node type.";
            }
            leaf ret-code {
              type lspv-return-code;
              description
                "Return code.";
            }
            leaf ds-address {
              type inet:ip-address-no-zone;
              description
                "Downstream address of the related hop in a test.";
            }
            container ds-label-lists {
              description
                "List of downstream information tables.";
              list ds-label-list {
                key "label-index";
                description
                  "Statistics of downstream information table.";
                leaf label-index {
                  type uint32 {
                    range "1..4294967295";
                  }
                  description
                    "The index of the ds label.";
                }
                leaf ds-label {
                  type uint32;
                  description
                    "Downstream labels.";
                }
              }
            }
            leaf result-type {
              type probe-result-type;
              description
                "Result of packet sending, which is either success or timeout.";
            }
            leaf is-hit {
              type boolean;
              description
                "Is hit the destination MAC address.";
            }
            leaf is-delete {
              ext:support-filter "true";
              type boolean;
              description
                "Enable/disable the function of deleting test results.";
            }
          }
        }
      }
    }
    container vpws-ping-results {
      config false;
      description
        "List of test result.";
      list vpws-ping-result {
        key "test-name";
        description
        "Statistics of ping test results.";
        leaf test-name {
          type string {
            length "1..32";
          }
          description
            "Test name.";
        }
        leaf local-ce-id {
          type uint32;
          description
            "Local EVPN VPWS ID.";
        }
        leaf remote-ce-id {
          type uint32;
          description
            "Remote EVPN VPWS ID.";
        }
        leaf packet-send {
          type uint32;
          description
            "Total number of sent packets.";
        }
        leaf packet-receive {
          type uint32;
          description
            "Total number of received packets.";
        }
        leaf loss-ratio {
          type pub-type:percent {
            range "0..100";
          }
          units "%";
          description
            "Packet loss ratio of a test.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        leaf status {
          type dgntl-test-status-type;
          description
            "Test status.";
        }
        leaf tunnel-type {
          type dgntl-evpn-tunnel-type;
          description
            "Tunnel type.";
        }
        leaf path-type {
          type dgntl-evpn-vpws-path-type;
          description
            "Tunnel primary/backup flag.";
        }
        leaf next-hop {
          type inet:ip-address-no-zone;
          description
            "Next-hop address of the tunnel.";
        }
        leaf vpn-sid {
          type inet:ipv6-address-no-zone;
          description
            "VPN sid ID.";
        }
        leaf is-new-version {
          type boolean;
          description
            "Is new version or not.";
        }
        container probes {
          description
            "List of ping results of all packets in a test.";
          list probe {
            key "sequence";
            description
              "Statistics of get the response result of a single packet in an EVPN VPWS ping test.";
            leaf sequence {
              type uint32 {
                range "1..4294967295";
              }              
              description
                "Serial number of a test packet received by a certain hop.";
            }
            leaf replier {
              type inet:ip-address-no-zone;
              description
                "Reply address in a received response packet.";
            }
            leaf data-bytes {
              type uint32;
              description
                "Number of bytes in a received response packet.";
            }
            leaf rtt {
              type uint32;
              units "ms";
              description
                "RTT of test packets.";
            }
            leaf result-type {
              type probe-result-type;
              description
                "Result of packet sending, which is either success or timeout.";
            }
            leaf is-delete {
              ext:support-filter "true";
              type boolean;
              description
                "Enable/disable the function of deleting test results.";
            }
          }
        }
      }
    }
    container multi-vpws-ping-results {
      config false;
      description
        "List of EVPN VPWS ping test result.";
      list multi-vpws-ping-result {
        key "test-name path-index";
        description
          "Statistics of EVPN VPWS ping test result.";
        leaf test-name {
          type string {
            length "1..32";
          }
          description
            "Test name.";
        }
        leaf path-index {
          type uint32 {
            range "1..4294967295";
          }
          description
            "Index of path.";
        }        
        leaf local-ce-id {
          type uint32;
          description
            "Local EVPN VPWS ID.";
        }
        leaf remote-ce-id {
          type uint32;
          description
            "Remote EVPN VPWS ID.";
        }
        leaf packet-send {
          type uint32;
          description
            "Total number of sent packets.";
        }
        leaf packet-receive {
          type uint32;
          description
            "Total number of received packets.";
        }
        leaf loss-ratio {
          type pub-type:percent {
            range "0..100";
          }
          units "%";
          description
            "Packet loss ratio of a test.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        leaf status {
          type dgntl-test-status-type;
          description
            "Test status.";
        }
        leaf tunnel-type {
          type dgntl-evpn-tunnel-type;
          description
            "Tunnel type.";
        }
        leaf path-type {
          type dgntl-evpn-vpws-path-type;
          description
            "Tunnel primary/backup flag.";
        }
        leaf next-hop {
          type inet:ip-address-no-zone;
          description
            "Next-hop address of the tunnel.";
        }
        leaf vpn-sid {
          type inet:ipv6-address-no-zone;
          description
            "VPN sid ID.";
        }
        container probes {
          description
            "List of ping results of all packets in a test.";
          list probe {
            key "sequence";
            description
              "Statistics of get the response result of a single packet in an EVPN VPWS ping test.";
            leaf sequence {
              type uint32 {
                range "1..4294967295";
              }              
              description
                "Serial number of a test packet received by a certain hop.";
            }
            leaf replier {
              type inet:ip-address-no-zone;
              description
                "Reply address in a received response packet.";
            }
            leaf data-bytes {
              type uint32;
              description
                "Number of bytes in a received response packet.";
            }
            leaf rtt {
              type uint32;
              units "ms";
              description
                "RTT of test packets.";
            }
            leaf result-type {
              type probe-result-type;
              description
                "Result of packet sending, which is either success or timeout.";
            }
            leaf is-delete {
              ext:support-filter "true";
              type boolean;
              description
                "Enable/disable the function of deleting test results.";
            }
          }
        }
      }
    }
    container vpws-trace-results {
      config false;
      description
        "List of test result.";
      list vpws-trace-result {
        key "test-name";
        description
          "Statistics of test result of a certain hop in the test path.";
        leaf test-name {
          type string {
            length "1..32";
          }
          description
            "Test name.";
        }
        leaf local-ce-id {
          type uint32;
          description
            "Local EVPN VPWS ID.";
        }
        leaf remote-ce-id {
          type uint32;
          description
            "Remote EVPN VPWS ID.";
        }
        leaf status {
          type dgntl-test-status-type;
          description
            "Test status.";
        }
        leaf tunnel-type {
          type dgntl-evpn-tunnel-type;
          description
            "Tunnel type.";
        }
        leaf path-type {
          type dgntl-evpn-vpws-path-type;
          description
            "Tunnel primary/backup flag.";
        }
        leaf next-hop {
          type inet:ip-address-no-zone;
          description
            "Next-hop address of the tunnel.";
        }
        leaf vpn-sid {
          type inet:ipv6-address-no-zone;
          description
            "VPN sid ID.";
        }
        leaf is-new-version {
          type boolean;
          description
            "Is new version or not.";
        }
        container hops {
          description
            "List of ping results of all packets in a test.";
          list hop {
            key "hop-index";
            description
              "Statistics of hop results.";
            leaf hop-index {
              type uint32 {
                range "1..4294967295";
              }              
              description
                "The index of the hop.";
            }
            leaf replier {
              type inet:ip-address-no-zone;
              description
                "Reply address of the related hop in a test.";
            }
            leaf rtt {
              type uint32;
              units "ms";
              description
                "RTT of test packets.";
            }
            leaf type {
              type transmit-type;
              description
                "Node type.";
            }
            leaf return-code {
              type uint32;
              description
                "Return code.";
            }
            leaf ds-address {
              type inet:ip-address-no-zone;
              description
                "Downstream address of the related hop in a test.";
            }
            container ds-label-lists {
              description
                "List of downstream information tables.";
              list ds-label-list {
                key "ds-label";
                description
                  "Statistics of downstream information table.";
                leaf ds-label {
                  type uint32;               
                  description
                    "Downstream labels.";
                }
              }
            }
            leaf result-type {
              type probe-result-type;
              description
                "Result of packet sending, which is either success or timeout.";
            }
            leaf is-delete {
              ext:support-filter "true";
              type boolean;
              description
                "Enable/disable the function of deleting test results.";
            }
          }
        }
      }
    }
    container multi-vpws-trace-results {
      config false;
      description
        "List of EVPN VPWS trace test result.";
      list multi-vpws-trace-result {
        key "test-name path-index";
        description
          "Statistics of EVPN VPWS trace test result.";
        leaf test-name {
          type string {
            length "1..32";
          }
          description
            "Test name.";
        }
        leaf path-index {
          type uint32 {
            range "1..4294967295";
          }
          description
            "Index of path.";
        }        
        leaf local-ce-id {
          type uint32;
          description
            "Local EVPN VPWS ID.";
        }
        leaf remote-ce-id {
          type uint32;
          description
            "Remote EVPN VPWS ID.";
        }
        leaf status {
          type dgntl-test-status-type;
          description
            "Test status.";
        }
        leaf tunnel-type {
          type dgntl-evpn-tunnel-type;
          description
            "Tunnel type.";
        }
        leaf path-type {
          type dgntl-evpn-vpws-path-type;
          description
            "Tunnel primary/backup flag.";
        }
        leaf next-hop {
          type inet:ip-address-no-zone;
          description
            "Next-hop address of the tunnel.";
        }
        leaf vpn-sid {
          type inet:ipv6-address-no-zone;
          description
            "VPN sid ID.";
        }
        container hops {
          description
            "List of ping results of all packets in a test.";
          list hop {
            key "hop-index";
            description
              "Statistics of hop results.";
            leaf hop-index {
              type uint32 {
                range "1..4294967295";
              }              
              description
                "The index of the hop.";
            }
            leaf replier {
              type inet:ip-address-no-zone;
              description
                "Reply address of the related hop in a test.";
            }
            leaf rtt {
              type uint32;
              units "ms";
              description
                "RTT of test packets.";
            }
            leaf type {
              type transmit-type;
              description
                "Node type.";
            }
            leaf return-code {
              type uint32;
              description
                "Return code.";
            }
            leaf ds-address {
              type inet:ip-address-no-zone;
              description
                "Downstream address of the related hop in a test.";
            }
            container ds-label-lists {
              description
                "List of downstream information tables.";
              list ds-label-list {
                key "ds-label";
                description
                  "Statistics of downstream information table.";
                leaf ds-label {
                  type uint32;               
                  description
                    "Downstream labels.";
                }
              }
            }
            leaf result-type {
              type probe-result-type;
              description
                "Result of packet sending, which is either success or timeout.";
            }
            leaf is-delete {
              ext:support-filter "true";
              type boolean;
              description
                "Enable/disable the function of deleting test results.";
            }
          }
        }
      }
    }
  }
  rpc evpn-start-mac-ping {
    description
      "Start evpn mac ping.";
    ext:node-ref "/diagnostic-tools:diagnostic-tools/diagnostic-tools:evpn/diagnostic-tools:mac-ping-results";
    input {
      leaf test-name {
        type string {
          length "1..32";
        }
        mandatory true;
        description
          "Test name.";
      }
      choice access-type {
        mandatory true;
        description
          "Access type.";
        case normal {
          description
            "Normal access.";
          leaf evpn-name {
            type string {
              length "1..31";
            }
            description
              "EVPN instance name.";
          }
        }
        case bd {
          description
            "Bridge-domain access.";
          leaf bd-id  {
            type uint32 {
              range "1..16777215";
            }
            mandatory true;
            description
              "The ID of bridge-domain.";
          }
          leaf vlan-id  {
            type uint16 {
              range "1..4094";
            }
            description
              "VLAN ID.";
          }
        }
      }
      leaf mac {
        type pub-type:mac-address;
        mandatory true;
        description
          "Mac address.";
      }
      leaf source-address {
        type inet:ip-address-no-zone;
        description
          "Source address of the string type. You can click this node to set different types of addresses and deploy the configurations together with the configuration of the source address type node. If the source address type is set to IPv4, this parameter is set to IPv4. If the source address type is set to IPv6, this parameter is set to IPv6.";
      }
      leaf count {
        type uint32 {
          range "1..4294967295";
        }
        default "5";
        description
          "Number of sent test packets.";
      }
      leaf interval {
        type uint32 {
          range "1..10000";
        }
        units "ms";
        default "2000";
        description
          "Interval for sending test packets.";
      }
      leaf packet-size {
        type uint32 {
          range "100..9568";
        }
        units "Byte";
        default "110";
        description
          "Number of bytes in a sent test packet.";
      }
      leaf timeout {
        type uint32 {
          range "0..65535";
        }
        units "ms";
        default "2000";
        description
          "Time taken to wait for the response packets after detection packets are sent. If no response packet is received within the timeout period, the system considers that the test packet times out.";
      }
      leaf reply-mode {
        type reply-mode-evpn;
        default "udp";
        description
          "Mode for responding to test packets in a test.";
      }
      leaf next-hop {
        type inet:ip-address-no-zone;
        description
          "Next Hop Address.";
      }
      choice match-type {
        description
          "Match type.";
        case te-class-match {
          description
            "Match type te class.";
          leaf te-class {
            when "../bd-id";
            type uint32 {
              range "1..65535";
            }
            description
              "Te class.";
          }
        }
        case service-class-match {
          description
            "Match type service class.";
          leaf service-class {
            when "../bd-id";
            type service-class-value;
            description
              "Service class.";
          }
        }
      }
      leaf source-if-name {
        type leafref {
          path "/ifm:ifm/ifm:interfaces/ifm:interface/ifm:name";
        }
        must "not(../source-if-name and (../te-class or ../service-class))";
        description
          "The source interface for echo requests.";
      }
      choice vlan-type {
		    when "source-if-name";
        description
          "VLAN type.";
        case qinq-vlan {
          description
            "QinQ VLAN.";
          leaf pe-vid {
            type uint16 {
              range "1..4094";
            }
            must "../pe-vid and ../ce-vid";
            description
              "PE VLAN ID.";
          }
          leaf ce-vid {
            type uint16 {
              range "1..4094";
            }
            must "../pe-vid and ../ce-vid";
            description
            "CE VLAN ID.";
          }
        }
        case dot1q-vlan {
          description
            "Dot1q VLAN.";
          leaf dot1q-vlan {
            type uint16 {
              range "1..4094";
            }
            description
              "Dot1q VLAN ID.";
          }
        }
 	  }
    }
  }

  rpc evpn-stop-mac-ping {
    description
      "Stop evpn mac ping.";
    ext:node-ref "/diagnostic-tools:diagnostic-tools/diagnostic-tools:evpn/diagnostic-tools:mac-ping-results";
    input {
      leaf test-name {
        type leafref {
          path "/diagnostic-tools:diagnostic-tools/diagnostic-tools:evpn/diagnostic-tools:mac-ping-results/diagnostic-tools:mac-ping-result/diagnostic-tools:test-name";
        }
        mandatory true;
        description
          "Test name.";
      }
    }
  }

  rpc evpn-delete-mac-ping {
    description
      "Delete evpn mac ping.";
    ext:node-ref "/diagnostic-tools:diagnostic-tools/diagnostic-tools:evpn/diagnostic-tools:mac-ping-results";
    input {
      leaf test-name {
        type leafref {
          path "/diagnostic-tools:diagnostic-tools/diagnostic-tools:evpn/diagnostic-tools:mac-ping-results/diagnostic-tools:mac-ping-result/diagnostic-tools:test-name";
        }
        mandatory true;
        description
          "Test name.";
      }
    }
  }
  rpc evpn-start-mac-trace {
    description
      "Start evpn mac trace.";
    ext:node-ref "/diagnostic-tools:diagnostic-tools/diagnostic-tools:evpn/diagnostic-tools:mac-trace-results";
    input {
      leaf test-name {
        type string {
          length "1..32";
        }
        mandatory true;
        description
          "Test name.";
      }
      choice access-type {
        mandatory true;
        description
          "Access type.";
        case normal {
          description
            "Normal access.";
          leaf evpn-name {
            type string {
              length "1..31";
            }
            description
              "EVPN instance name.";
          }
        }
        case bd {
          description
            "Bridge-domain access.";
          leaf bd-id  {
            type uint32 {
              range "1..16777215";
            }
            mandatory true;
            description
              "The ID of bridge-domain.";
          }
          leaf vlan-id  {
            type uint16 {
              range "1..4094";
            }
            description
              "VLAN ID.";
          }
        }
      }
      leaf mac {
        type pub-type:mac-address;
        mandatory true;
        description
          "Mac address.";
      }
      leaf source-address {
        type inet:ip-address-no-zone;
        description
          "Source address.";
      }
      leaf packet-size {
        type uint32 {
          range "100..9568";
        }
        units "Byte";
        description
          "Number of bytes in a sent test packet.";
      }
      leaf timeout {
        type uint32 {
          range "0..65535";
        }
        units "ms";
        default "2000";
        description
          "Time taken to wait for the response packets after detection packets are sent.";
      }
      leaf ttl {
        type uint8 {
          range "1..255";
        }
        default "30";
        description
          "Time to live.";
      }
      leaf reply-mode {
        type reply-mode-evpn;
        default "udp";
        description
          "Mode for responding to test packets in a test.";
      }
      leaf next-hop {
        type inet:ip-address-no-zone;
        description
          "Next Hop Address.";
      }
      leaf ttl-mode {
        type ttl-mode;
        description
          "TTL mode.";
      }
      choice match-type {
        description
          "Match type.";
        case te-class-match {
          description
            "Match type te class.";
          leaf te-class {
            when "../bd-id";
            type uint32 {
              range "1..65535";
            }
            description
              "Te class.";
          }
        }
        case service-class-match {
          description
            "Match type service class.";
          leaf service-class {
            when "../bd-id";
            type service-class-value;
            description
              "Service class.";
          }
        }
      }
    }
  }

  rpc evpn-stop-mac-trace {
    description
      "Stop evpn mac trace.";
    ext:node-ref "/diagnostic-tools:diagnostic-tools/diagnostic-tools:evpn/diagnostic-tools:mac-trace-results";
    input {
      leaf test-name {
        type leafref {
          path "/diagnostic-tools:diagnostic-tools/diagnostic-tools:evpn/diagnostic-tools:mac-trace-results/diagnostic-tools:mac-trace-result/diagnostic-tools:test-name";
        }
        mandatory true;
        description
          "Test name.";
      }
    }
  }

  rpc evpn-delete-mac-trace {
    description
      "Delete evpn mac trace.";
    ext:node-ref "/diagnostic-tools:diagnostic-tools/diagnostic-tools:evpn/diagnostic-tools:mac-trace-results";
    input {
      leaf test-name {
        type leafref {
          path "/diagnostic-tools:diagnostic-tools/diagnostic-tools:evpn/diagnostic-tools:mac-trace-results/diagnostic-tools:mac-trace-result/diagnostic-tools:test-name";
        }
        mandatory true;
        description
          "Test name.";
      }
    }
  }

  rpc evpn-start-vpws-ping {
    description
      "Start evpn vpws ping.";
    ext:node-ref "/diagnostic-tools:diagnostic-tools/diagnostic-tools:evpn/diagnostic-tools:vpws-ping-results";
    input {
      leaf test-name {
        type string {
          length "1..32";
        }
        mandatory true;
        description
          "Test name.";
      }
      leaf local-ce-id {
        type uint32 {
          range "1..4294967294";
        }
        mandatory true;
        description
          "Local EVPN VPWS ID.";
      }
      leaf remote-ce-id {
        type uint32 {
          range "1..4294967294";
        }
        mandatory true;
        description
          "Remote EVPN VPWS ID.";
      }
      leaf source-address {
        type inet:ip-address-no-zone;
        description
          "Source address of the string type. You can click this node to set different types of addresses and deploy the configurations together with the configuration of the source address type node. If the source address type is set to IPv4, this parameter is set to IPv4. If the source address type is set to IPv6, this parameter is set to IPv6.";
      }
      leaf count {
        type uint32 {
          range "1..4294967295";
        }
        default "5";
        description
          "Number of sent test packets.";
      }
      leaf interval {
        type uint32 {
          range "1..10000";
        }
        units "ms";
        default "2000";
        description
          "Interval for sending test packets.";
      }
      leaf packet-size {
        type uint32 {
          range "80..9600";
        }
        units "Byte";
        default "100";
        description
          "Number of bytes in a sent test packet.";
      }
      leaf exp {
        type uint32 {
          range "0..7";
        }
        description
          "EXP value in the label field of MPLS packets. The EXP value is used to distinguish the service types of MPLS packets.";
      }
      leaf tc {
        type uint8 {
          range "0..255";
        }
        description
          "Traffic class value of IPv6 packets. The traffic class value is used to distinguish the service types of IPv6 packets.";
      }
      leaf timeout {
        type uint32 {
          range "0..65535";
        }
        units "ms";
        default "2000";
        description
          "Time taken to wait for the response packets after detection packets are sent. If no response packet is received within the timeout period, the system considers that the test packet times out.";
      }
      leaf reply-mode {
        type reply-mode-evpn;
        default "udp";
        description
          "Mode for responding to test packets in a test.";
      }
      leaf end-op {
        type inet:ipv6-address-no-zone;
        must "not(../exp)";
        description
          "End-OP segment ID.";
      }
      leaf prefix-length {
        when "../end-op";
        type uint8 {
          range "1..128";
        }
        description
          "Length of the prefix.";
      }
      leaf backup {
        type boolean;
        description
          "Specify the backup tunnel.";
      }
      leaf control-word {
        type boolean;
        description
          "Enable/disable the control word function.";
      }
      leaf evpn-name {
        type string {
          length "1..31";
        }
        description
          "EVPN instance name.";
      }
      choice match-type {
        description
          "Match type.";
        case te-class-match {
          description
            "Match type te class.";
          leaf te-class {
            type uint32 {
              range "1..65535";
            }
            description
              "Te class.";
          }
        }
        case service-class-match {
          description
            "Match type service class.";
          leaf service-class {
            type service-class-value;
            description
              "Service class.";
          }
        }
      }
      leaf source-if-name {
        type leafref {
          path "/ifm:ifm/ifm:interfaces/ifm:interface/ifm:name";
        }
        must "not(../source-if-name and (../exp or ../end-op or ../backup or ../control-word or ../te-class or ../service-class))";
        description
          "The source interface for echo requests.";
      }
      choice vlan-type {
        when "source-if-name";
        description
          "VLAN type.";
        case qinq-vlan {
          description
            "QinQ VLAN.";
          leaf pe-vid {
            type uint16 {
              range "1..4094";
            }
            must "../pe-vid and ../ce-vid";
            description
              "PE VLAN ID.";
          }
          leaf ce-vid {
            type uint16 {
              range "1..4094";
            }
            must "../pe-vid and ../ce-vid";
            description
            "CE VLAN ID.";
          }
        }
        case dot1q-vlan {
          description
            "Dot1q VLAN.";
          leaf dot1q-vlan {
            type uint16 {
              range "1..4094";
            }
            description
              "Dot1q VLAN ID.";
          }
        }
      }
    }
  }

  rpc evpn-stop-vpws-ping {
    description
      "Stop evpn vpws ping.";
    ext:node-ref "/diagnostic-tools:diagnostic-tools/diagnostic-tools:evpn/diagnostic-tools:vpws-ping-results";
    input {
      leaf test-name {
        type leafref {
          path "/diagnostic-tools:diagnostic-tools/diagnostic-tools:evpn/diagnostic-tools:vpws-ping-results/diagnostic-tools:vpws-ping-result/diagnostic-tools:test-name";
        }
        mandatory true;
        description
          "Test name.";
      }
    }
  }

  rpc evpn-delete-vpws-ping {
    description
      "Delete evpn vpws ping.";
    ext:node-ref "/diagnostic-tools:diagnostic-tools/diagnostic-tools:evpn/diagnostic-tools:vpws-ping-results";
    input {
      leaf test-name {
        type leafref {
          path "/diagnostic-tools:diagnostic-tools/diagnostic-tools:evpn/diagnostic-tools:vpws-ping-results/diagnostic-tools:vpws-ping-result/diagnostic-tools:test-name";
        }
        mandatory true;
        description
          "Test name.";
      }
    }
  }

  rpc evpn-start-vpws-trace {
    description
      "Start evpn vpws trace.";
    ext:node-ref "/diagnostic-tools:diagnostic-tools/diagnostic-tools:evpn/diagnostic-tools:vpws-trace-results";
    input {
      leaf test-name {
        type string {
          length "1..32";
        }
        mandatory true;
        description
          "Test name.";
      }
      leaf local-ce-id {
        type uint32 {
          range "1..4294967294";
        }
        mandatory true;
        description
          "Local EVPN VPWS ID.";
      }
      leaf remote-ce-id {
        type uint32 {
          range "1..4294967294";
        }
        mandatory true;
        description
          "Remote EVPN VPWS ID.";
      }
      leaf source-address {
        type inet:ip-address-no-zone;
        description
          "Source address of the string type. You can click this node to set different types of addresses and deploy the configurations together with the configuration of the source address type node. If the source address type is set to IPv4, this parameter is set to IPv4. If the source address type is set to IPv6, this parameter is set to IPv6.";
      }
      leaf packet-size {
        type uint32 {
          range "96..9600";
        }
        units "Byte";
        description
          "Number of bytes in a sent test packet.";
      }
      leaf exp {
        type uint32 {
          range "0..7";
        }
        description
          "EXP value in the label field of MPLS packets. The EXP value is used to distinguish the service types of MPLS packets.";
      }
      leaf tc {
        type uint8 {
          range "0..255";
        }
        description
          "Traffic class value of IPv6 packets. The traffic class value is used to distinguish the service types of IPv6 packets.";
      }
      leaf timeout {
        type uint32 {
          range "0..65535";
        }
        units "ms";
        default "2000";
        description
          "Time taken to wait for the response packets after detection packets are sent. If no response packet is received within the timeout period, the system considers that the test packet times out.";
      }
      leaf ttl {
        type uint8 {
          range "1..255";
        }
        default "30";
        description
          "Time to live.";
      }
      leaf reply-mode {
        type reply-mode-evpn;
        default "udp";
        description
          "Mode for responding to test packets in a test.";
      }
      leaf ttl-mode {
        type ttl-mode;
        description
          "TTL mode.";
      }
      leaf end-op {
        type inet:ipv6-address-no-zone;
        must "not(../exp)";
        description
          "End-OP segment ID.";
      }
      leaf prefix-length {
        when "../end-op";
        type uint8 {
          range "1..128";
        }
        description
          "Length of the prefix.";
      }
      leaf backup {
        type boolean;
        description
          "Specify the backup tunnel.";
      }
      leaf control-word {
        type boolean;
        description
          "Enable/disable the control word function.";
      }
      leaf evpn-name {
        type string {
          length "1..31";
        }
        description
          "EVPN instance name.";
      }
      choice match-type {
        description
          "Match type.";
        case te-class-match {
          description
            "Match type te class.";
          leaf te-class {
            type uint32 {
              range "1..65535";
            }
            description
              "Te class.";
          }
        }
        case service-class-match {
          description
            "Match type service class.";
          leaf service-class {
            type service-class-value;
            description
              "Service class.";
          }
        }
      }
    }
  }

  rpc evpn-stop-vpws-trace {
    description
      "Stop evpn vpws trace.";
    ext:node-ref "/diagnostic-tools:diagnostic-tools/diagnostic-tools:evpn/diagnostic-tools:vpws-trace-results";
    input {
      leaf test-name {
        type leafref {
          path "/diagnostic-tools:diagnostic-tools/diagnostic-tools:evpn/diagnostic-tools:vpws-trace-results/diagnostic-tools:vpws-trace-result/diagnostic-tools:test-name";
        }
        mandatory true;
        description
          "Test name.";
      }
    }
  }

  rpc evpn-delete-vpws-trace {
    description
      "Delete evpn vpws trace.";
    ext:node-ref "/diagnostic-tools:diagnostic-tools/diagnostic-tools:evpn/diagnostic-tools:vpws-trace-results";
    input {
      leaf test-name {
        type leafref {
          path "/diagnostic-tools:diagnostic-tools/diagnostic-tools:evpn/diagnostic-tools:vpws-trace-results/diagnostic-tools:vpws-trace-result/diagnostic-tools:test-name";
        }
        mandatory true;
        description
          "Test name.";
      }
    }
  }

  augment "/diagnostic-tools:diagnostic-tools" {
    description
      "List of EVPN ping and trace tests.";
    container evpn {
      config false;
      description
        "Statistics of EVPN ping and trace tests.";
      uses diagnostic-tools:evpn-ping-trace-result-type;
    }
  }
}
