/*
Copyright (C) 2025 Huawei Technologies Co., Ltd. All rights reserved.
*/
module huawei-network-instance-deviations-ar5710s {
  namespace "urn:huawei:yang:huawei-network-instance-deviations-ar5710s";
  prefix ni-devs-ar5710s;

  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-network-instance module.";

  revision 2025-02-24 {
    description
      "Initial revision.";
    reference "Huawei private.";
  }

  deviation "/ni:network-instance/ni:global/ni:vpn-instance-limit" {
    deviate not-supported;
  }
  deviation "/ni:network-instance/ni:global/ni:route-distinguisher-auto-ip" {
    deviate add {
      must 'not (../route-distinguisher-auto-ip)';
    }
  }
}
