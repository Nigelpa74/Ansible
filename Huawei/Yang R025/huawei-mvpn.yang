/*
Copyright (C) 2019-2025 Huawei Technologies Co., Ltd. All rights reserved.
*/
module huawei-mvpn {
  namespace "urn:huawei:yang:huawei-mvpn";
  prefix mvpn;
  import huawei-ifm {
    prefix ifm;
  }
  import huawei-network-instance {
    prefix ni;
  }
  import huawei-l3vpn {
    prefix l3vpn;
  }
  import huawei-pub-type {
    prefix pub-type;
  }
  import huawei-routing-policy {
    prefix rtp;
  }
  import huawei-l3-multicast {
    prefix l3mc;
  }
  import ietf-inet-types {
    prefix inet;
  }
  import huawei-extension {
    prefix ext;
  }
  import huawei-acl {
    prefix acl;
  }
  import huawei-bier {
    prefix bier;
  }
  import huawei-net-slice {
    prefix net-slice;
  }
  import ietf-yang-types {
    prefix yang;
  }
  organization
    "Huawei Technologies Co., Ltd.";
  contact
    "Huawei Industrial Base
     Bantian, Longgang
     Shenzhen 518129
     People's Republic of China
     Website: http://www.huawei.com
     Email: support@huawei.com";
  description
    "A model for Multicast Virtual Private Network (MVPN).";
  revision 2025-03-19 {
    description
      "Add get-mvpn-tunnel-switch-info, sdwan-enable, sdwan-infos, send-c-multicast-ext-routes, and receive-c-multicast-ext-routes.";
    reference
      "Huawei private.";
  }
  revision 2025-03-13 {
    description
      "Add the tunnel-state node. Modify the value range of mvpnglb. Add the when condition and Modify the must condition of local-admin-id.";
    reference
      "Huawei private.";
  }
  revision 2024-12-10 {
    description
      "Add get-mvpnglb-by-range, global-static-label and mvpnglb. Delete the when conditon and modify the must conditon of local-admin-id. Add a container extranet-rpfs in mldp-mvpn. Modify the must condition in container extranet-rpfs in ng-mvpn. Modify must condition for frr-flow-based-acl-name node.";
    reference
      "Huawei private.";
  }
  revision 2024-06-19 {
    description
      "Modify container srv6-locator. Modify the when conditon of mvpn.";
    reference
      "Huawei private.";
  }
  revision 2024-01-22 {
    description
      "Add frr-flow-based-rate-acl-name and frr-flow-based-threshold.";
    reference
      "Huawei private.";
  }
  revision 2023-10-23 {
    description
      "Add the container mldp-in-band-signaling.";
    reference
      "Huawei private.";
  }
  revision 2023-10-17 {
    description
      "Modify the value range of per-item-tunnel-limit. The must condition of ng is modified. The must condition of slice-id is modified.";
    reference
      "Huawei private.";
  }
  revision 2022-11-30 {
    description
      "Add send-c-multicast-routes and receive-c-multicast-routes.";
    reference
      "Huawei private.";
  }
  revision 2022-10-12 {
    description
      "Add the node network-slice. Modify some nodes for Rosen MVPN. Add control message for Rosen MVPN.";
    reference
      "Huawei private.";
  }
  revision 2022-06-30 {
    description
      "Add the compatible style of IPv6 extended communities attributes. The must condition of star-grp is modified.";
    reference
      "Huawei private.";
  }
  revision 2022-03-03 {
    description
      "Modify some restriction for frr-acl-name. The must condition of frr-acl-name is modified. Modify type of locator and rsvp-te-p2mp-template. Add local-admin-id node. Modify extranet-rpfs when condition.";
    reference
      "Huawei private.";
  }
  revision 2021-08-05 {
    description
      "Add signal-format leaf fot Src-dt. Add multicast-sid case for src-dt-sid. Add node rosen-global. Delete some nodes that not supported. Modify the design for switch-group.";
    reference
      "Huawei private.";
  }
  revision 2021-07-25 {
    description
      "Modify some restriction for bier-entropy-mode. The when condition of bier-entropy-mode is deleted.";
    reference
      "Huawei private.";
  }
  revision 2021-03-30 {
    description
      "Nodes related to NG MVPN over BIER6 are added. Modify the xpath of leafref for ad-import-policy-name. Modify the design of ipmsi-infos.";
    reference
      "Huawei private.";
  }
  revision 2021-01-16 {
    description
      "Added configurable nodes related to IPv6 NG MVPN FRR. A must clause was deleted for is-c-multicast-frr. Modify the type of frr-acl-name.";
    reference
      "Huawei private.";
  }
  revision 2020-12-17 {
    description
      "Modify some restriction for NG MVPN S-PMSI tunnel. The value range of spmsi-tnl-detect-delay is modified.";
    reference
      "Huawei private.";
  }
  revision 2020-02-21 {
    description
      "Modify bier leaf node type to leafref. Add units for some nodes. Modify some restriction for bier node. Modify description. Add dynamic default value for per-item-tunnel-limit.";
    reference
      "Huawei private.";
  }
  revision 2020-02-04 {
    description
      "Change rsvp-te-p2mp-template leaf node type to leafref.";
    reference
      "Huawei private.";
  }
  revision 2019-12-18 {
    description
      "Change relative node for bier tunnel.";
    reference
      "Huawei private.";
  }
  revision 2019-11-20 {
    description
      "Change container information to ipmsi-infos.";
    reference
      "Huawei private.";
  }
  revision 2019-05-06 {
    description
      "Initial revision.";
    reference
      "Huawei private.";
  }
  ext:task-name "mvpn";

  typedef addr-family-type {
    type enumeration {
      enum "ipv4-unicast" {
        value 1;
        description
          "IPv4 address family.";
      }
      enum "ipv6-unicast" {
        value 2;
        description
          "IPv6 address family.";
      }
    }
    description
      "Address family.";
  }
  typedef signaling-mode {
    type enumeration {
      enum "invalid" {
        value 0;
        description
          "Invalid signaling mode.";
      }
      enum "BGP" {
        value 2;
        description
          "BGP signaling mode.";
      }
    }
    description
      "MVPN signal type.";
  }
  typedef tunnel-mode {
    type enumeration {
      enum "p2mp-te" {
        value 3;
        description
          "P2MP TE tunnel.";
      }
      enum "p2mp-mldp" {
        value 4;
        description
          "P2MP mLDP tunnel.";
      }
      enum "vxlan-static" {
        value 6;
        description
          "VXLAN static tunnel.";
      }
      enum "bier" {
        value 7;
        description
          "BIER tunnel.";
      }
      enum "bier-ipv6" {
        value 8;
        description
          "BIER IPv6 tunnel.";
      }
    }
    description
      "MVPN tunnel type.";
  }

  typedef src-dt-address-type {
    type enumeration {
      enum "srv6-locator" {
        value 1;
        description
          "Src-dt addresses using SRv6 locator.";
      }
    }
    description
      "The src-dt addresses type.";
  }

  typedef src-dt-signal-format {
    type enumeration {
      enum "msid" {
        value 1;
        description
          "Multicast service identifier.";
      }
    }
    description
      "Src-dt signal format.";
  }

  typedef auto-discovery-type {
    type enumeration {
      enum "none" {
        value 0;
        description
          "The A-D mode is disabled.";
      }
      enum "MDT" {
        value 1;
        description
          "The A-D mode is Multicast Distribution Tree (MDT).";
      }
    }
    description
      "Auto-Discovery Mode.";
  }
  typedef vpn-target-type {
    type enumeration {
      enum "export-extcommunity" {
        value 2;
        description
          "Extended community attribute carried in routes sent from an outbound interface to the destination VPN.";
      }
      enum "import-extcommunity" {
        value 3;
        description
          "Extended community attribute used to accept routes carrying the specified extended community attribute.";
      }
    }
    description
      "VPN target type.";
  }
  typedef rpt-spt-mode {
    type enumeration {
      enum "none" {
        value 0;
        description
          "PIM SM shared tree is not supported.";
      }
      enum "spt-mode" {
        value 1;
        description
          "SPT-only mode.";
      }
      enum "rpt-spt-mode" {
        value 2;
        description
          "RPT-SPT mode.";
      }
    }
    description
      "The mode of PIM SM shared tree.";
  }
  typedef umh-type {
    type enumeration {
      enum "unicast" {
        value 0;
        description
          "Unicast route preferred.";
      }
      enum "highest-ip" {
        value 1;
        description
          "Highest IP address.";
      }
    }
    description
      "Select upstream multicast hop.";
  }
  typedef bier-entropy-mode {
    type enumeration {
      enum "sg-hash" {
        value 1;
        description
          "SG hash entropy mode of MVPN BIER.";
      }
    }
    description
      "MVPN BIER entropy mode.";
  }

  typedef bit-string-length {
    type enumeration {
      enum "64-bit" {
        value 1;
        description
          "64-bit BitString.";
      }
      enum "128-bit" {
        value 2;
        description
          "128-bit BitString.";
      }
      enum "256-bit" {
        value 3;
        description
          "256-bit BitString.";
      }
    }
    description
      "Enumerated values of the BitString length.";
  }

  typedef msg-type {
	type enumeration {
	  enum "switch" {
        value 1;
	    description
	      "Message type is switch.";
	  }
    }
	description
	  "Enumerated values of the VPN instance control message.";
  }

  typedef tunnel-switch-type {
  type enumeration {
    enum "ipmsi-switch-to-spmsi" {
        value 0;
      description
        "I-PMSI switches to S-PMSI.";
    }
    enum "spmsi-switch-to-ipmsi" {
        value 1;
      description
        "S-PMSI switches to I-PMSI.";
    }
    }
  description
    "Enumerated values of the tunnel switch type.";
  }

  typedef tunnel-state {
    type enumeration {
      enum "unknown" {
        value 0;
        description
          "Tunnel state unknown.";
      }
      enum "up" {
        value 1;
        description
          "Tunnel state up.";
      }
      enum "down" {
        value 2;
        description
          "Tunnel state down.";
      }
    }
    description
      "Tunnel state type. For root nodes, the value is either up or down. For leaf nodes, the tunnel state is not perceived, and the value is always unknown.";
  }

  grouping tunnel-sg-info-type {
    description
      "PMSI tunnel and (S, G) entry state.";
    container tunnels {
      config false;
      description
        "List of PMSI tunnel state.";
      list tunnel {
        key "address";
        description
          "PMSI tunnel state.";
        leaf address {
          type inet:ip-address-no-zone;
          description
            "Tunnel node address.";
        }
        leaf role {
          type string {
            length "0..15";
          }
          description
            "Role of a tunnel node.";
        }
      }
    }
    container sgs {
      config false;
      description
        "List of (S, G) entry state.";
      list sg {
        key "source-addr group-addr";
        description
          "(S, G) entry state.";
        leaf source-addr {
          type inet:ip-address-no-zone;
          description
            "Source address.";
        }
        leaf group-addr {
          type inet:ip-address-no-zone;
          description
            "Group address.";
        }
      }
    }
  }

  grouping bier-tunnel-sg-info-type {
    description
      "PMSI BIER tunnel and (S, G) entry state.";
    container root-leafs {
      config false;
      description
        "List of PMSI tunnel node.";
      list root-leaf {
        key "address";
        description
          "Operational data of PMSI tunnel node.";
        leaf address {
          type inet:ip-address-no-zone;
          description
            "Tunnel node address.";
        }
        leaf role {
          type string {
            length "0..15";
          }
          description
            "Role of a tunnel node.";
        }
        leaf bfr-id {
          type uint16 {
            range "1..65535";
          }
          description
            "BFR-ID of a BIER tunnel node.";
          }
        leaf bfr-prefix {
          type inet:ip-address-no-zone;
          description
            "BFR prefix of a BIER tunnel node.";
        }
      }
    }
    container sgs {
      config false;
      description
        "List of (S, G) entry.";
      list sg {
        key "source-addr group-addr";
        description
          "Statistics of (S, G) entry.";
        leaf source-addr {
          type inet:ip-address-no-zone;
        description
            "Source address.";
          }
        leaf group-addr {
          type inet:ip-address-no-zone;
          description
            "Group address.";
        }
      }
    }
  }
  grouping bier-ipv6-tunnel-sg-info-type {
    description
      "PMSI BIER tunnel and (S, G) entry state.";
    container root-leafs {
      config false;
      description
        "List of PMSI tunnel node.";
      list root-leaf {
        key "address";
        description
          "Operational data of PMSI tunnel node.";
        leaf address {
          type inet:ip-address-no-zone;
          description
            "Tunnel node address.";
        }
        leaf role {
          type string {
            length "0..15";
          }
          description
            "Role of a tunnel node.";
        }
        leaf bfr-id {
          type uint16 {
            range "1..65535";
          }
          description
            "BFR-ID of a BIER tunnel node.";
          }
        leaf bfr-prefix {
          type inet:ip-address-no-zone;
          description
            "BFR prefix of a BIER tunnel node.";
        }
      }
    }
    container sgs {
      config false;
      description
        "List of (S, G) entry.";
      list sg {
        key "source-addr group-addr";
        description
          "Statistics of (S, G) entry.";
        leaf source-addr {
          type inet:ip-address-no-zone;
          description
            "Source address.";
          }
        leaf group-addr {
          type inet:ip-address-no-zone;
          description
            "Group address.";
        }
        leaf flow-label {
          type uint32;
          description
            "Flow label.";
        }
        leaf slice-id {
          type uint32;
          description
            "Network-slice ID of specific flow.";
        }
      }
    }
  }
  grouping bier-flow-statistics-type {
    description
      "Configure flow-statistics function of flow.";
    container global {
      description
        "Configure global flow-statistics function of flow.";
      leaf enable {
        type boolean;
        default "false";
        description
          "Enable/disable flow-statistics of all flow.";
      }
    }
    container sgs {
      description
        "List of enable flow-statistics of specific flow.";
      list sg {
        key "group-addr source-addr";
        description
          "Configure (S, G) entry.";
        leaf group-addr {
          type inet:ip-address-no-zone;
          description
            "Group address.";
        }
        leaf source-addr {
          type inet:ip-address-no-zone;
          description
            "Source address.";
        }
      }
    }
  }
  grouping bier-flow-label-type {
    description
      "Configure flow label for flow with source address and group address.";
    container sgs {
      description
        "List of BIERv6 flow label for flow of (S, G).";
      list sg {
        key "group-addr source-addr";
        unique "label";
        description
          "Configure flow label for flow with source address and group address.";
        leaf group-addr {
          type inet:ip-address-no-zone;
          description
            "Group address.";
        }
        leaf source-addr {
          type inet:ip-address-no-zone;
          description
            "Source address.";
        }
        leaf label {
          type uint16 {
            range "1..2000";
          }
          mandatory true;
          description
            "Flow label.";
        }
      }
    }
  }
  grouping bier-slice-type {
    description
      "Configure network-slice function of flow.";
    container global {
      description
        "Configure global network-slice function of flow.";
      leaf slice-id {
        type leafref {
            path "/net-slice:net-slice/net-slice:instances/net-slice:instance/net-slice:id";
        }
        must "../slice-id!=0";
        must "not(/net-slice:net-slice/net-slice:instances/net-slice:instance[net-slice:id=current()]/net-slice:source-prefix)";
        description
          "Network-slice ID of specific flow. The slice ID 0 cannot be used as the slice ID of the slice interface. It can only be used as the slice ID of the basic interface.";
      }
    }
    container sgs {
      description
        "List of enable network-slice of specific flow.";
      list sg {
        key "group-addr source-addr";
        description
          "Configure (S, G) entry.";
        leaf group-addr {
          type inet:ip-address-no-zone;
          description
            "Group address.";
        }
        leaf source-addr {
          type inet:ip-address-no-zone;
          description
            "Source address.";
        }
        leaf slice-id {
          type leafref {
              path "/net-slice:net-slice/net-slice:instances/net-slice:instance/net-slice:id";
          }
          must "../slice-id!=0";
          must "not(/net-slice:net-slice/net-slice:instances/net-slice:instance[net-slice:id=current()]/net-slice:source-prefix)";
          mandatory true;
          description
          "Network-slice ID of specific flow. The slice ID 0 cannot be used as the slice ID of the slice interface. It can only be used as the slice ID of the basic interface.";
        }
      }
    }
  }
  container mvpn {
    description
      "Configure global MVPN configurations.";
    container globals {
      description
        "List of global MVPN configuration.";
      list global {
        key "address-family";
        description
          "Configure global MVPN.";
        leaf address-family {
          type addr-family-type;
          description
            "IPv4 or IPv6 address family.";
        }
        leaf mvpn-id {
          type inet:ip-address-no-zone;
          must "(not(contains(../mvpn-id, ':')))";
          mandatory true;
          description
            "Specify MVPN ID, IP address mode.";
        }
        leaf enable-inter-area-segmented {
          when "../address-family='ipv4-unicast'";
          type boolean;
          default "false";
          description
            "Enable/disable segmented tunnels globally on the ABR.";
        }
        leaf apply-explicit-null-label {
          when "../address-family='ipv6-unicast'";
          type boolean;
          default "false";
          description
            "Enable/disable IPv6 explicit null to apply label.";
        }
      }
    }
    container ipv6-underlay-globals {
      description
        "List of IPv6 underlay global MVPN configuration.";
      list ipv6-underlay-global {
        key "address-family";
        description
          "Configure IPv6 underlay global MVPN.";
        leaf address-family {
          type addr-family-type;
          description
            "IPv4 or IPv6 address family.";
        }
        leaf mvpn-id {
          type inet:ipv6-address-no-zone;
          mandatory true;
          description
            "Specify IPv6 underlay MVPN ID, IPv6 address mode.";
        }
      }
    }
    container mvpnglbs {
        description
          "List of mvpn local block.";
        list mvpnglb {
            key "begin end";
            description
              "Configure mvpn local block. Currently only one configuration is supported.";
            leaf begin {
              type uint32 {
                range "1..4294967295";
              }
              description
                "MVPN global block begin value. The value range is determined by the PAF file of the corresponding device. Special explanation: Range: The range comes from PAF.";
            }
            leaf end {
              type uint32 {
                range "1..4294967295";
              }
              must "../end >= ../begin";
              description
                "MVPN global block end value. The value range is determined by the PAF file of the corresponding device. Special explanation: Range: The range comes from PAF.";
            }
        }
    }
    container rosen-global {
      description
        "Configure global Rosen MVPN configurations.";
      container source-interface {
        when "/ni:network-instance/ni:instances/ni:instance[ni:name='_public_']/l3mc:multicast/l3mc:ipv4";
        description
          "Configure default interface whose IP address is used as the default IP address of an MTI.";
        leaf source-interface-name {
          type leafref {
            path "/ifm:ifm/ifm:interfaces/ifm:interface/ifm:name";
          }
          must "/ifm:ifm/ifm:interfaces/ifm:interface[ifm:name=current()]/ifm:vrf-name='_public_'";
          description
            "Name of the public network interface whose IP address is used as the default IP address of an MTI.";
        }
      }
    }
    container invalid-switch-group-packets {
      config false;
      description
        "List of invalid switch-group packet.";
      list invalid-switch-group-packet {
        key "packet-index";
        description
          "Operational data of invalid switch-Group packets.";
        leaf packet-index {
          type uint32;
          description
            "Number of a recently received invalid switch-group packet.";
        }
        leaf if-address {
          type inet:ipv4-address-no-zone;
          description
            "IP address of the interface that receives invalid packets.";
        }
        leaf receive-time {
          type yang:date-and-time;
          description
            "Time when invalid packets were received.";
        }
        leaf packet-length {
          type uint32;
          description
            "Length of invalid packets.";
        }
        leaf msg-type {
          type string {
            length "0..32";
          }
          description
            "Type of invalid packets.";
        }
        leaf msg-content {
          type string {
            length "0..64";
          }
          description
            "Contents of invalid packets.";
        }
      }
    }
  }
  rpc get-mvpnglb-by-range {
    description
      "Statistics of mvpn dynamic global block. The range of dynamic global labels reserved for mvpn.";
    input {
      leaf range {
        type uint32 {
          range "1..4294967295";
        }
        description
          "Total number of labels available.";
      }
    }
    output {
      container global-block-ranges {
        description
          "List of the range of dynamic global labels reserved for mvpn.";
        list global-block-range {
          key "begin-value end-value";
          description
            "The range of dynamic global labels reserved for mvpn.";
          leaf begin-value {
            type uint32 {
              range "1..4294967295";
            }
            description
              "The begin value of dynamic global block.";
          }
          leaf end-value {
            type uint32 {
              range "1..4294967295";
            }
            description
              "The end value of dynamic global block.";
          }
          leaf range {
            type uint32 {
              range "1..4294967295";
            }
            description
              "The value range of dynamic global block.";
          }
        }
      }
    }  
  }

  rpc get-mvpn-tunnel-switch-info {
    description
      "Query historical MVPN PMSI tunnel switch information.";
    input {
      leaf address-family {
        type addr-family-type;
        description
          "IPv4 or IPv6 historical MVPN PMSI tunnel switch information.";
      }
    }
    output {
      container mvpn-tunnel-switch-infos {
        description
          "List of historical MVPN PMSI tunnel switch information.";
        list mvpn-tunnel-switch-info {
          key "index";
          description
            "Historical MVPN PMSI tunnel switch information.";
          leaf index {
            type uint16 {
              range "1..1000";
            }
            description
              "Index of each MVPN PMSI tunnel switch information.";
          }
          leaf switch-time {
            type string {
              length "1..32";
            }
            description
              "Time when the tunnel switches, which is in the format yyyy-MM-dd HH:mm:ss:SSS.";
          }
          leaf vpn-instance {
            type leafref {
              path "/ni:network-instance/ni:instances/ni:instance/ni:name";
            }
            description
              "VPN instance name.";
          }
          leaf source-address {
            type inet:ip-address-no-zone;
            description
              "Source address.";
          }
          leaf group-address {
            type inet:ip-address-no-zone;
            description
              "Group address.";
          }
          leaf switch-type {
            type tunnel-switch-type;
            description
              "Record about the type of switching between I-PMSI and S-PMSI tunnels.";
          }
        }
      }
    }  
  }

  augment "/ni:network-instance/ni:instances/ni:instance/l3vpn:afs/l3vpn:af" {
    description
      "Add MVPN configuration to the L3VPN module.";
    container mvpn {
      when "(../l3vpn:type='ipv4-unicast' and ../../../l3mc:multicast/l3mc:ipv4) or (../l3vpn:type='ipv6-unicast' and ../../../l3mc:multicast/l3mc:ipv6)";
      description
        "Configure MVPN in the instance.";
      leaf mvpn-id {
        when "../../../../ni:name!='_public_' and ../../l3vpn:type='ipv4-unicast'";
        type inet:ip-address-no-zone;
        description
          "Specify MVPN ID, IP address mode.";
      }
      leaf local-admin-id {
        when "../../../../ni:name!='_public_' and ../../l3vpn:type='ipv4-unicast'";
        type uint16 {
          range "1..65535";
        }
        must "not(/ni:network-instance/ni:instances/ni:instance[ni:name!=current()/../../../../ni:name]/l3vpn:afs/l3vpn:af[l3vpn:type='ipv4-unicast']/mvpn:mvpn/mvpn:local-admin-id = ../mvpn:local-admin-id)";
        description
          "Specify a number that uniquely identifies the current VPN instance.";
      }
      choice mvpn-type {
        description
          "MVPN type.";
        case ng-mvpn {
          description
            "NG MVPN.";
          container ng {
            must "../../../../ni:name!='_public_' or /mvpn:mvpn/mvpn:ipv6-underlay-globals/mvpn:ipv6-underlay-global[mvpn:address-family=current()/../../l3vpn:type]/mvpn:mvpn-id";
            must "(../../l3vpn:type='ipv4-unicast' and (../mvpn:mvpn-id or /mvpn:mvpn/mvpn:globals/mvpn:global[mvpn:address-family=current()/../../l3vpn:type]/mvpn:mvpn-id or /mvpn:mvpn/mvpn:ipv6-underlay-globals/mvpn:ipv6-underlay-global[mvpn:address-family=current()/../../l3vpn:type]/mvpn:mvpn-id)) or (../../l3vpn:type='ipv6-unicast' and (/mvpn:mvpn/mvpn:globals/mvpn:global[mvpn:address-family=current()/../../l3vpn:type]/mvpn:mvpn-id or /mvpn:mvpn/mvpn:ipv6-underlay-globals/mvpn:ipv6-underlay-global[mvpn:address-family=current()/../../l3vpn:type]/mvpn:mvpn-id))";
            must "../../../../ni:name ='_public_' or ./is-inter-as='false' or ./inter-area-seg-enable='false'";
            must "../../../../ni:name ='_public_' or ./is-ipv6-underlay='false' or ./inter-area-seg-enable='false'";
            must "(./frr-flow-based-rate-acl-name and ./frr-flow-based-threshold) or (not (./frr-flow-based-rate-acl-name) and not (./frr-flow-based-threshold))";
            presence "mvpn enable";
            description
              "Enable/disable NG-MVPN in the instance.";
            leaf signaling-mode {
              type signaling-mode;
              default "invalid";
              description
                "Signaling mode.";
            }
            leaf is-sender-site {
              type boolean;
              default "false";
              description
                "Enable/disable the function of specifying the current PE as a sender PE.";
            }
            leaf sdwan-enable {
              type boolean;
              default "false";
              description
                "Enable/disable the MVPN SD-WAN capability.";
            }
            leaf is-ipv6-underlay {
              type boolean;
              must "../is-ipv6-underlay='false' or /mvpn:mvpn/mvpn:ipv6-underlay-globals/mvpn:ipv6-underlay-global[mvpn:address-family=current()/../../../l3vpn:type]";
              default "false";
              description
                "Enable/disable the IPv6 underlay of the MVPN.";
            }
            choice src-dt-address {
              description
                "The src-dt address of BIER IPv6 underlay for current MVPN.";
              case srv6-locator {
                description
                  "SRv6 locator.";
                container srv6-locator {
                  must "../is-sender-site='true' and ../is-ipv6-underlay='true'";
                  presence "srv6-locator";
                  description
                    "Configure SRv6 locator.";
                  leaf locator {
                     type string {
                       length "1..31";
                     }
                     mandatory true;
                     description
                       "The SRv6 locator of src-dt-sid.";
                  }
                  leaf src-dt-sid {
                    type inet:ipv6-address-no-zone;
                    mandatory true;
                    description
                      "Src-dt-sid for MVPN.";
                  }
                  leaf auto-sid {
                    type boolean;
                    must "../auto-sid='false'";
                    default "false";
                    description
                      "Enable/disable the automatic configuration of Src-dt-sid.";
                  }
                  leaf signal-format {
                    type src-dt-signal-format;
                    description
                      "Src-dt signal format of the sender PE.";
                  }
                }
              }
            }
            leaf rpt-spt-mode {
              type rpt-spt-mode;
              default "none";
              description
                "*G mode.";
            }
            leaf is-inter-as {
              type boolean;
              default "false";
              description
                "Enable/disable the function of specifying the current PE as a auto-discovery inter-as PE.";
            }
            leaf global-static-label {
              when "../../../l3vpn:type='ipv4-unicast' and ../../../../../ni:name!='_public_'";
              type uint32 {
                range "1..4294967295";
              }
              description
                "Mvpn global block label.";
            }
            leaf is-c-multicast-frr {
              type boolean;
              default "false";
              description
                "Enable/disable FRR.";
            }
            leaf frr-acl-name {
              when "../../../l3vpn:type='ipv4-unicast' and ../is-c-multicast-frr='true'";
              type acl:acl4-identity;
              must "(/acl:acl/acl:groups/acl:group[acl:number=number(current())]/acl:type='basic' or /acl:acl/acl:groups/acl:group[acl:number=number(current())]/acl:type='advance') or (/acl:acl/acl:groups/acl:group[acl:identity=current()]/acl:type='basic' or /acl:acl/acl:groups/acl:group[acl:identity=current()]/acl:type='advance')";
              description
                "Configure an IPv4 FRR policy. If no ACL is specified, all (S, G) entries take effect.";
            }
            leaf frr-acl-name6 {
              when "../../../l3vpn:type='ipv6-unicast' and ../is-c-multicast-frr='true'";
              type leafref {
                path "/acl:acl/acl:group6s/acl:group6/acl:identity";
              }
              must "/acl:acl/acl:group6s/acl:group6[acl:identity=current()]/acl:type='basic' or /acl:acl/acl:group6s/acl:group6[acl:identity=current()]/acl:type='advance'";
              description
                "Configure an IPv6 FRR policy. If no ACL is specified, all (S, G) entries take effect.";
            }
            leaf frr-flow-based-acl-name {
              when "../../../l3vpn:type='ipv4-unicast' and ../is-c-multicast-frr='true'";
              type acl:acl4-identity; 
              must "(/acl:acl/acl:groups/acl:group[acl:number=number(current())]/acl:type='basic' or /acl:acl/acl:groups/acl:group[acl:number=number(current())]/acl:type='advance') or (/acl:acl/acl:groups/acl:group[acl:identity=current()]/acl:type='basic' or /acl:acl/acl:groups/acl:group[acl:identity=current()]/acl:type='advance')";
              description
                "Configure a flow-based IPv4 FRR policy. If no ACL is specified, all (S, G) entries do not take effect.";
            }
            leaf frr-flow-based-acl-name6 {
              when "../../../l3vpn:type='ipv6-unicast' and ../is-c-multicast-frr='true'";
              type leafref {
                path "/acl:acl/acl:group6s/acl:group6/acl:identity";
              }
              must "/acl:acl/acl:group6s/acl:group6[acl:identity=current()]/acl:type='basic' or /acl:acl/acl:group6s/acl:group6[acl:identity=current()]/acl:type='advance'";
              description
                "Configure a flow-based IPv6 FRR policy. If no ACL is specified, all (S, G) entries do not take effect.";
            }
            leaf is-compatible-draft {
              when "../../../../../ni:name!='_public_'";
              type boolean;
              default "false";
              description
                "Enable/disable a device to use the packet encapsulation format defined in the draft.";
            }
            leaf is-export-msdp {
              when "../../../l3vpn:type='ipv4-unicast'";
              type boolean;
              default "false";
              description
                "Enable/disable a device to export source active to MSDP.";
            }
            leaf is-import-msdp {
              when "../../../l3vpn:type='ipv4-unicast'";
              type boolean;
              default "false";
              description
                "Enable/disable a device to import source active from MSDP.";
            }
            leaf spmsi-tnl-detect-delay {
              when "../../../../../ni:name!='_public_'";
              type uint16 {
                range "3..65535";
              }
              units "s";
              default "5";
              description
                "The delay in tunnel detection.";
            }
            leaf rpt-prune-delay {
              type uint16 {
                range "0..1800";
              }
              units "s";
              default "60";
              description
                "The delay of RPT pruning.";
            }
            leaf inter-area-seg-enable {
              when "../../../../../ni:name!='_public_'";
              type boolean;
              must "(../inter-area-seg-enable='false' and ../../../l3vpn:type='ipv6-unicast') or ../../../l3vpn:type='ipv4-unicast'";
              default "false";
              description
                "Enable/disable intra-area segmented tunnels.";
            }
            leaf umh-select-type {
              when "../../../../../ni:name!='_public_'";
              type umh-type;
              default "unicast";
              description
                "Configure UMH select type.";
            }
            leaf bier-entropy-mode {
              type bier-entropy-mode;
              description
                "Configure BIER entropy mode.";
            }
            leaf ipmsi-to-spmsi-switch-immediately {
              type boolean;
              default "false";
              description
                "Enable/disable ipmsi to spmsi switch immediately.";
            }
            leaf is-ipv6-underlay-compatible-style {
              type boolean;
              must "../is-ipv6-underlay-compatible-style='false' or ../is-ipv6-underlay='true'";
              default "false";
              description
                "Enable/disable the compatible style of IPv6 specific extended communities attributes of the MVPN.";
            }
            leaf frr-flow-based-rate-acl-name {
              when "../../../l3vpn:type='ipv4-unicast' and ../is-c-multicast-frr='true'";
              type leafref {
                path "/acl:acl/acl:groups/acl:group/acl:identity";
              }
              must "/acl:acl/acl:groups/acl:group[acl:identity=current()]/acl:type='basic' or /acl:acl/acl:groups/acl:group[acl:identity=current()]/acl:type='advance'";
              description
                "Configure a flow-based-threshold IPv4 FRR policy. If no ACL is specified, all (S, G) entries do not take effect.";
            }
            leaf frr-flow-based-threshold {
              when "../../../l3vpn:type='ipv4-unicast' and ../is-c-multicast-frr='true'";
              type uint32 {
                range "1..1000";
              }
              units "pps";
              description
                "Configure a flow-based-threshold flow limited threshold pps. If the flow rate is lower than the threshold, flow detection is disabled.";
            }
            container route-targets {
              //if-feature mvpn-separate-rt;
              description
                "List of MVPN route-targets.";
              list route-target {
                key "rt-type rt-value";
                description
                  "Configure a multicast route-target.";
                leaf rt-type {
                  type vpn-target-type;
                  description
                    "RT type.";
                }
                leaf rt-value {
                  type string {
                    length "3..21";
                  }
                  description
                    "The available MVPN target formats are as follows:
                     - 16-bit AS number:32-bit user-defined number, for example, 1:3. An AS number ranges from 0 to 65535, and a user-defined number ranges from 0 to 4294967295. The AS number and user-defined number cannot be both 0s. That is, a VPN target cannot be 0:0.
                     - 32-bit IP address:16-bit user-defined number, for example, 192.168.122.15:1. The IP address ranges from 0.0.0.0 to 255.255.255.255, and the user-defined number ranges from 0 to 65535.";
                }
              }
            }
            container extranet-rpfs {
              when "../../../l3vpn:type='ipv4-unicast'";
              description
                "List of extranet select-RPF.";
              list extranet-rpf {
                key "group-addr group-addr-mask-length";
                max-elements "16";
                description
                  "Configure extranet select-RPF.";
                leaf group-addr {
                  type inet:ipv4-address-no-zone {
                    pattern '(22[4-9]|23\d)(\.(25[0-5]|2[0-4]\d|1\d\d|[1-9]?\d)){3}';
                  }
                  description
                    "Multicast group address. The value ranges from 224.0.0.0 to 239.255.255.255.";
                }
                leaf group-addr-mask-length {
                  type uint32 {
                    range "4..32";
                  }
                  description
                    "Mask length of a multicast group address.";
                }
                leaf src-vrf-name {
                  type leafref {
                    path "/ni:network-instance/ni:instances/ni:instance/ni:name";
                  }
                  must "(../../../../../../../ni:name!=current() and (../mvpn:src-vrf-name = '_public_' or /ni:network-instance/ni:instances/ni:instance[ni:name=current()]/l3vpn:afs/l3vpn:af[l3vpn:type='ipv4-unicast']/l3vpn:route-distinguisher or /ni:network-instance/ni:global/ni:route-distinguisher-auto-ip))";
                  mandatory true;
                  description
                    "RPF source VPN instance.";
                }
              }
            }
            container ipmsi-tunnel {
              must "../../../../../ni:name!='_public_' or not(./tunnel-mode) or ./tunnel-mode='bier-ipv6'";
              must "not(../spmsi-tunnels/spmsis/star-star) and not(../spmsi-tunnels/spmsis/star-grps/star-grp)";
              must "not(./tunnel-mode) or ./tunnel-mode!='bier' or (./sub-domain-id and ./bsl)";
              must "not(./tunnel-mode) or ./tunnel-mode!='bier-ipv6' or (./sub-domain-id-ipv6 and ./bsl-ipv6)";
              must "not(./tunnel-mode) or (./tunnel-mode!='bier' and ./tunnel-mode!='p2mp-mldp' and ./tunnel-mode!='p2mp-te') or (../../mvpn:mvpn-id or /mvpn:mvpn/mvpn:globals/mvpn:global[mvpn:address-family=current()/../../../l3vpn:type]/mvpn:mvpn-id)";
              must "not(./tunnel-mode) or ./tunnel-mode!='bier-ipv6' or ../srv6-locator";
              presence "ipmsi-tunnel";
              description
                "Enable/disable I-PMSI in the instance. Default MDT or I-PMSI configuration and operational state information.";
              leaf tunnel-mode {
                type tunnel-mode;
                description
                  "Tunnel mode.";
              }
              choice tunnel-attribute {
                description
                  "I-PMSI tunnel attributes configuration.";
                case rsvp-te-p2mp {
                  when "tunnel-mode='p2mp-te'";
                  description
                    "RSVP TE P2MP tunnel.";
                  leaf rsvp-te-p2mp-template {
                    type string {
                      length "1..31";
                      pattern '[^ ]*';
                    }
                    description
                      "RSVP TE P2MP tunnel template.";
                  }
                }
                case bier {
                  when "tunnel-mode='bier' and ../../../l3vpn:type='ipv4-unicast'";
                  description
                    "BIER underlay.";
                  leaf sub-domain-id {
                    type leafref {
                      path "/bier:bier/bier:sub-domains/bier:sub-domain/bier:sub-domain-id";
                    }
                    must "/bier:bier/bier:sub-domains/bier:sub-domain[bier:sub-domain-id=current()][bier:address-family='ipv4-unicast']";
                    must "../../../../../../ni:name ='_public_' or (../../inter-area-seg-enable='false' and ../../is-inter-as='false')";
                    description
                      "Sub-domain ID of BIER.";
                  }
                  leaf bsl {
                    type leafref {
                      path "/bier:bier/bier:sub-domains/bier:sub-domain[bier:sub-domain-id=current()/../sub-domain-id]/bier:encapsulations/bier:encapsulation/bier:bsl";
                    }
                    description
                      "BitString length of BIER.";
                  }
                }
                case bier-ipv6 {
                  when "tunnel-mode='bier-ipv6'";
                  description
                    "BIER IPv6 underlay.";
                  leaf sub-domain-id-ipv6 {
                    type leafref {
                      path "/bier:bier/bier:sub-domains/bier:sub-domain/bier:sub-domain-id";
                    }
                    must "/bier:bier/bier:sub-domains/bier:sub-domain[bier:sub-domain-id=current()][bier:address-family='ipv6-unicast']";
                    must "../../../../../../ni:name ='_public_' or ../../inter-area-seg-enable='false'";
                    description
                      "Sub-domain ID of BIER IPv6.";
                  }
                  leaf bsl-ipv6 {
                    type leafref {
                      path "/bier:bier/bier:sub-domains/bier:sub-domain[bier:sub-domain-id=current()/../sub-domain-id-ipv6]/bier:encapsulations/bier:encapsulation/bier:bsl";
                    }
                    description
                      "BitString length of BIER IPv6.";
                  }
                }
              }
            }
            container ipmsi-infos {
              config false;
              description
                "I-PMSI state.";
              container te-tunnels {
                description
                  "List of I-PMSI TE tunnel state.";
                list te-tunnel {
                  key "te-p2mp-id te-tunnel-id te-extend-tunnel-id";
                  description
                    "I-PMSI TE tunnel state.";
                  leaf te-p2mp-id {
                    type pub-type:hex-binary;
                    description
                      "P2MP ID of the P2MP tunnel.";
                  }
                  leaf te-tunnel-id {
                    type uint32;
                    description
                      "ID of the P2MP tunnel.";
                  }
                  leaf te-extend-tunnel-id {
                    type inet:ip-address-no-zone;
                    description
                      "P2MP extended tunnel interface ID.";
                  }
                  leaf tunnel-state {
                    type tunnel-state;
                    description
                      "Tunnel state.";
                  }
                  uses tunnel-sg-info-type;
                }
              }
              container ldp-tunnels {
                description
                  "List of I-PMSI LDP tunnel state.";
                list ldp-tunnel {
                  key "ldp-route-addr opaque-value";
                  description
                    "I-PMSI LDP tunnel state.";
                  leaf ldp-route-addr {
                    type inet:ip-address-no-zone;
                    description
                      "IP address of the root of a P2MP LSP.";
                  }
                  leaf opaque-value {
                    type string {
                      length "1..255";
                    }
                    description
                      "P2MP LSP ID.";
                  }
                  leaf tunnel-state {
                    type tunnel-state;
                    description
                      "Tunnel state.";
                  }
                  uses tunnel-sg-info-type;
                }
              }
              container bier-tunnels {
                description
                  "List of I-PMSI BIER tunnel.";
                list bier-tunnel {
                  key "tunnel-id root-ip";
                  description
                    "Operational state of I-PMSI BIER tunnel.";
                  leaf tunnel-id {
                    type uint32 {
                      range "0..4294967295";
                    }
                    description
                      "Tunnel ID.";
                  }
                  leaf root-ip {
                    type inet:ip-address-no-zone;
                    description
                      "Root IP address.";
                  }
                  leaf vpn-label {
                    type uint32 {
                      range "0..4294967295";
                    }
                    description
                      "MPLS label.";
                  }
                  leaf sub-domain-id {
                    type uint16 {
                      range "0..255";
                    }
                    description
                      "Sub-domain ID.";
                  }
                  leaf tunnel-state {
                    type tunnel-state;
                    description
                      "Tunnel state.";
                  }
                  uses bier-tunnel-sg-info-type;
                }
              }
              container bier-ipv6-tunnels {
                description
                  "List of I-PMSI BIER IPv6 tunnel.";
                list bier-ipv6-tunnel {
                  key "tunnel-id root-ip";
                  description
                    "Operational state of I-PMSI BIER tunnel.";
                  leaf tunnel-id {
                    type uint32 {
                      range "0..4294967295";
                    }
                    description
                      "Tunnel ID.";
                  }
                  leaf root-ip {
                    type inet:ip-address-no-zone;
                    description
                      "Root IP address.";
                  }
                  choice src-dt-sid {
                    description
                      "Src-dt SID.";
                    case multicast-sid {
                      description
                        "Multicast service identifier attribute.";
                      leaf multicast-sid {
                        type inet:ipv6-address-no-zone;
                        description
                          "Src-dt SID.";
                      }
                      leaf prefix-len {
                        type uint8;
                        description
                          "Prefix length.";
                      }
                      leaf msid-len {
                        type uint8;
                        description
                          "MSID length.";
                      }
                    }
                    case prefix-sid {
                      description
                        "Prefix-sid attribute.";
                      leaf prefix-sid {
                        type inet:ipv6-address-no-zone;
                        description
                          "Src-dt SID.";
                      }
                    }
                  }
                  leaf sub-domain-id {
                    type uint16 {
                      range "0..255";
                    }
                    description
                      "Sub-domain ID.";
                  }
                  leaf tunnel-state {
                    type tunnel-state;
                    description
                      "Tunnel state.";
                  }
                  uses bier-ipv6-tunnel-sg-info-type;
                }
              }
            }
            container spmsi-tunnels {
              presence "spmsi-tunnels";
              description
                "Enable/disable S-PMSI tunnel in the instance. S-PMSI tunnel configuration and operational state information.";
              leaf switch-delay-time {
                type uint8 {
                  range "3..60";
                }
                units "s";
                default "5";
                description
                  "The delay for switching from the I-PMSI to the S-PMSI.";
              }
              leaf switch-back-holddown-time {
                type uint16 {
                  range "0..180";
                }
                units "s";
                default "60";
                description
                  "The delay for switching back from the S-PMSI to the I-PMSI.";
              }
              leaf spmsi-tunnel-withdraw-delay-time {
                type uint16 {
                  range "5..20";
                }
                units "s";
                default "5";
                description
                  "The delay for withdrawing the SPMSI.";
              }
              container spmsis {
                description
                  "Configure NG SPMSI switch policy.";
                container star-star {
                  when "../../../../../l3vpn:type='ipv4-unicast'";
                  must "../../../../../../../ni:name!='_public_' or ./tunnel-mode='bier-ipv6'";
                  must "not(../star-grps/star-grp) and not(../../../ipmsi-tunnel)";
                  presence "spmsi group star-star policy";
                  description
                    "Enable/disable (*, *) S-PMSI swicth policy.";
                  leaf tunnel-mode {
                    type tunnel-mode;
                    must "../tunnel-mode!='p2mp-te' or ../rsvp-te-p2mp-template";
                    must "../tunnel-mode!='bier' or (../sub-domain-id and ../bsl)";
                    must "../tunnel-mode!='bier-ipv6' or (../sub-domain-id-ipv6 and ../bsl-ipv6)";
                    must "../tunnel-mode!='bier-ipv6' or ../../../../srv6-locator";
                    must "(../tunnel-mode!='bier' and ../tunnel-mode!='p2mp-mldp' and ../tunnel-mode!='p2mp-te') or (../../../../../mvpn:mvpn-id or /mvpn:mvpn/mvpn:globals/mvpn:global[mvpn:address-family=current()/../../../../../../l3vpn:type]/mvpn:mvpn-id)";
                    mandatory true;
                    description
                      "Tunnel mode.";
                  }
                  choice tunnel-attribute {
                    description
                      "S-PMSI tunnel attributes configuration.";
                    case rsvp-te-p2mp {
                      when "tunnel-mode='p2mp-te'";
                      description
                        "RSVP TE P2MP tunnel.";
                      leaf rsvp-te-p2mp-template {
                        type string {
                          length "1..31";
                          pattern '[^ ]*';
                        }
                        description
                          "RSVP TE P2MP tunnel template.";
                      }
                    }
                    case bier {
                      when "tunnel-mode='bier'";
                      description
                        "BIER tunnel.";
                      leaf sub-domain-id {
                        type leafref {
                          path "/bier:bier/bier:sub-domains/bier:sub-domain/bier:sub-domain-id";
                        }
                        must "/bier:bier/bier:sub-domains/bier:sub-domain[bier:sub-domain-id=current()][bier:address-family='ipv4-unicast']";
                        must "../../../../../../../../ni:name ='_public_' or (../../../../inter-area-seg-enable='false' and ../../../../is-inter-as='false')";
                        description
                          "S-PMSI BIER sub-domain ID.";
                      }
                      leaf bsl {
                        type leafref {
                          path "/bier:bier/bier:sub-domains/bier:sub-domain[bier:sub-domain-id=current()/../sub-domain-id]/bier:encapsulations/bier:encapsulation/bier:bsl";
                        }
                        description
                          "S-PMSI BIER BitString length.";
                      }
                    }
                    case bier-ipv6 {
                      when "tunnel-mode='bier-ipv6'";
                      description
                        "BIER IPv6 tunnel.";
                      leaf sub-domain-id-ipv6 {
                        type leafref {
                          path "/bier:bier/bier:sub-domains/bier:sub-domain/bier:sub-domain-id";
                        }
                        must "/bier:bier/bier:sub-domains/bier:sub-domain[bier:sub-domain-id=current()][bier:address-family='ipv6-unicast']";
                        must "../../../../../../../../ni:name ='_public_' or ../../../../inter-area-seg-enable='false'";
                        description
                          "S-PMSI BIER IPv6 sub-domain ID.";
                      }
                      leaf bsl-ipv6 {
                        type leafref {
                          path "/bier:bier/bier:sub-domains/bier:sub-domain[bier:sub-domain-id=current()/../sub-domain-id-ipv6]/bier:encapsulations/bier:encapsulation/bier:bsl";
                        }
                        description
                          "S-PMSI BIER IPv6 BitString length.";
                      }
                    }
                  }
                }
                container star-grps {
                  when "../../../../../l3vpn:type='ipv4-unicast'";
                  description
                    "List of (*, G) S-PMSI switch policys.";
                  list star-grp {
                    must "not(../../star-star) and not(../../../../ipmsi-tunnel)";
                    must "./tunnel-mode!='p2mp-te' or ./rsvp-te-p2mp-template";
                    must "./tunnel-mode!='bier' or (./sub-domain-id and ./bsl)";
                    must "./tunnel-mode!='bier-ipv6' or (./sub-domain-id-ipv6 and ./bsl-ipv6)";
                    must "./tunnel-mode!='bier-ipv6' or ../../../../srv6-locator";
                    must "(./tunnel-mode!='bier' and ./tunnel-mode!='p2mp-mldp' and ./tunnel-mode!='p2mp-te') or (../../../../../mvpn:mvpn-id or /mvpn:mvpn/mvpn:globals/mvpn:global[mvpn:address-family=current()/../../../../../../l3vpn:type]/mvpn:mvpn-id)";
                    must "../../../../../../../../ni:name!='_public_' or ./tunnel-mode='bier-ipv6'";
                    must "./tunnel-mode!='bier' or not(../star-grp[tunnel-mode!='bier'])";
                    must "./tunnel-mode!='bier-ipv6' or not(../star-grp[tunnel-mode!='bier-ipv6'])";
                    must "(./tunnel-mode!='p2mp-mldp' and ./tunnel-mode!='p2mp-te') or (not(../star-grp[tunnel-mode='bier']) and not(../star-grp[tunnel-mode='bier-ipv6']))";
                    key "group-addr group-mask-length";
                    description
                      "Apply (*, G) S-PMSI switch policy.";
                    leaf group-addr {
                      type inet:ip-address-no-zone;
                      description
                        "Start address of the IPv4 group address range in private network.";
                    }
                    leaf group-mask-length {
                      type uint8 {
                        range "4..32";
                      }
                      description
                        "Group mask length for the IPv4 group address range in private network.";
                    }
                    leaf tunnel-mode {
                      type tunnel-mode;
                      mandatory true;
                      description
                        "Tunnel mode.";
                    }
                    leaf per-item-tunnel-limit {
                      type uint32 {
                        range "1..10240";
                      }
                      ext:dynamic-default {
                        ext:default-value 16 {
                          when "../tunnel-mode='p2mp-te' or ../tunnel-mode='p2mp-mldp'";
                          description "The default value of p2mp-te or p2mp-mldp tunnel.";
                        }
                        ext:default-value 256 {
                          when "../tunnel-mode!='p2mp-te' and ../tunnel-mode!='p2mp-mldp'";
                          description "The default value of other tunnel.";
                        }
                      }
                      description
                        "Maximum number of S-PMSI tunnels allowed per S-PMSI configuration item per MVPN instance. The actual maximum value range depends on the tunnel mode.";
                    }
                    choice tunnel-attribute {
                      description
                        "S-PMSI tunnel attributes configuration.";
                      case rsvp-te-p2mp {
                        when "tunnel-mode='p2mp-te'";
                        description
                          "RSVP TE P2MP tunnel.";
                        leaf rsvp-te-p2mp-template {
                          type string {
                            length "1..31";
                            pattern '[^ ]*';
                          }
                          description
                            "RSVP TE P2MP tunnel template.";
                        }
                      }
                      case bier {
                        when "tunnel-mode='bier'";
                        description
                          "BIER tunnel.";
                        leaf sub-domain-id {
                          type leafref {
                            path "/bier:bier/bier:sub-domains/bier:sub-domain/bier:sub-domain-id";
                          }
                          must "../../../../../../../../../ni:name ='_public_' or ../../../../../inter-area-seg-enable='false' and ../../../../../is-inter-as='false'";
                          must "not(../../star-grp[sub-domain-id!=current()])";
                          must "/bier:bier/bier:sub-domains/bier:sub-domain[bier:sub-domain-id=current()][bier:address-family='ipv4-unicast']";
                          description
                            "S-PMSI BIER sub-domain ID.";
                        }
                        leaf bsl {
                          type leafref {
                            path "/bier:bier/bier:sub-domains/bier:sub-domain[bier:sub-domain-id=current()/../sub-domain-id]/bier:encapsulations/bier:encapsulation/bier:bsl";
                          }
                          must "not(../../star-grp[bsl!=current()])";
                          description
                            "S-PMSI BIER BitString length.";
                        }
                      }
                      case bier-ipv6 {
                        when "tunnel-mode='bier-ipv6'";
                        description
                          "BIER IPv6 tunnel.";
                        leaf sub-domain-id-ipv6 {
                          type leafref {
                            path "/bier:bier/bier:sub-domains/bier:sub-domain/bier:sub-domain-id";
                          }
                          must "../../../../../../../../../ni:name ='_public_' or ../../../../../inter-area-seg-enable='false'";
                          must "not(../../star-grp[sub-domain-id-ipv6!=current()])";
                          must "/bier:bier/bier:sub-domains/bier:sub-domain[bier:sub-domain-id=current()][bier:address-family='ipv6-unicast']";
                          description
                            "S-PMSI BIER IPv6 sub-domain ID.";
                        }
                        leaf bsl-ipv6 {
                          type leafref {
                            path "/bier:bier/bier:sub-domains/bier:sub-domain[bier:sub-domain-id=current()/../sub-domain-id-ipv6]/bier:encapsulations/bier:encapsulation/bier:bsl";
                          }
                          must "not(../../star-grp[bsl-ipv6!=current()])";
                          description
                            "S-PMSI BIER BitString length.";
                        }
                      }
                    }
                  }
                }
                container src-grps {
                  description
                    "List of (S, G) S-PMSI switch policys.";
                  list src-grp {
                    must "../../star-star or ../../../../ipmsi-tunnel";
                    must "./tunnel-mode!='p2mp-te' or ./rsvp-te-p2mp-template";
                    must "./tunnel-mode!='bier' or (./sub-domain-id and ./bsl)";
                    must "./tunnel-mode!='bier-ipv6' or (./sub-domain-id-ipv6 and ./bsl-ipv6)";
                    must "../../../../../../../../ni:name!='_public_' or ./tunnel-mode='bier-ipv6'";
                    key "group-addr group-mask-length source-addr source-mask-length";
                    description
                      "Apply (S, G) S-PMSI switch policy.";
                    leaf group-addr {
                      type inet:ip-address-no-zone;
                      description
                        "Start address of the IP group address range in private net.";
                    }
                    leaf group-mask-length {
                      type uint8 {
                        range "4..128";
                      }
                      description
                        "Group mask length for the IP group address range in private net. In the case of an IPv4 address family, the value ranges from 4 to 32. In the case of an IPv6 address family, the value ranges from 8 to 128.";
                    }
                    leaf source-addr {
                      type inet:ip-address-no-zone;
                      description
                        "Start address of the IP source address range in private net.";
                    }
                    leaf source-mask-length {
                      type uint8 {
                        range "0..128";
                      }
                      description
                        "Source mask length for the IP source address range in private net. In the case of an IPv4 address family, the value ranges from 0 to 32. In the case of an IPv6 address family, the value ranges from 0 to 128.";
                    }
                    leaf tunnel-mode {
                      type tunnel-mode;
                      must "(../tunnel-mode!='p2mp-te' and ../tunnel-mode!='p2mp-mldp') or (../../../star-star/tunnel-mode='p2mp-te' or ../../../star-star/tunnel-mode='p2mp-mldp' or ../../../../../ipmsi-tunnel/tunnel-mode='p2mp-te' or ../../../../../ipmsi-tunnel/tunnel-mode='p2mp-mldp')";
                      must "(../tunnel-mode!='bier') or ((../../../star-star/tunnel-mode and ../../../star-star/tunnel-mode='bier') or (../../../../../ipmsi-tunnel/tunnel-mode and ../../../../../ipmsi-tunnel/tunnel-mode='bier'))";
                      must "(../tunnel-mode!='bier-ipv6') or ((../../../star-star/tunnel-mode and ../../../star-star/tunnel-mode='bier-ipv6') or (../../../../../ipmsi-tunnel/tunnel-mode and ../../../../../ipmsi-tunnel/tunnel-mode='bier-ipv6'))";
                      mandatory true;
                      description
                        "Tunnel mode.";
                    }
                    leaf switch-threshold {
                      type uint32 {
                        range "0..4194304";
                      }
                      units "kbit/s";
                      default "0";
                      description
                        "Multicast packet rate threshold for triggering the switching from the I-PMSI to the S-PMSI.";
                    }
                    leaf per-item-tunnel-limit {
                      type uint32 {
                        range "1..10240";
                      }
                      ext:dynamic-default {
                        ext:default-value 16 {
                          when "../tunnel-mode='p2mp-te' or ../tunnel-mode='p2mp-mldp'";
                          description "The default value of p2mp-te or p2mp-mldp tunnel.";
                        }
                        ext:default-value 256 {
                          when "../tunnel-mode!='p2mp-te' and ../tunnel-mode!='p2mp-mldp'";
                          description "The default value of other tunnel.";
                        }
                      }
                      description
                        "Maximum number of S-PMSI tunnels allowed per S-PMSI configuration item per MVPN instance. The actual maximum value range depends on the tunnel mode.";
                    }
                    choice tunnel-attribute {
                      description
                        "S-PMSI tunnel attributes configuration.";
                      case rsvp-te-p2mp {
                        when "tunnel-mode='p2mp-te'";
                        description
                          "RSVP TE P2MP tunnel.";
                        leaf rsvp-te-p2mp-template {
                          type string {
                            length "1..31";
                            pattern '[^ ]*';
                          }
                          description
                            "RSVP TE P2MP tunnel template.";
                        }
                      }
                      case bier {
                        when "tunnel-mode='bier' and ../../../../../../l3vpn:type='ipv4-unicast'";
                        description
                          "BIER tunnel.";
                        leaf sub-domain-id {
                          type leafref {
                            path "/bier:bier/bier:sub-domains/bier:sub-domain/bier:sub-domain-id";
                          }
                          must "../../../../../../../../../ni:name ='_public_' or (../../../../../inter-area-seg-enable='false' and ../../../../../is-inter-as='false')";
                          must "../../../star-star[sub-domain-id=current()] or ../../../../../ipmsi-tunnel[sub-domain-id=current()]";
                          must "/bier:bier/bier:sub-domains/bier:sub-domain[bier:sub-domain-id=current()][bier:address-family='ipv4-unicast']";
                          description
                            "S-PMSI BIER sub-domain ID.";
                        }
                        leaf bsl {
                          type leafref {
                            path "/bier:bier/bier:sub-domains/bier:sub-domain[bier:sub-domain-id=current()/../sub-domain-id]/bier:encapsulations/bier:encapsulation/bier:bsl";
                          }
                          must "../../../star-star[bsl=current()] or ../../../../../ipmsi-tunnel[bsl=current()]";
                          description
                            "S-PMSI BIER BitString length.";
                        }
                      }
                      case bier-ipv6 {
                        when "tunnel-mode='bier-ipv6'";
                        description
                          "BIER IPv6 tunnel.";
                        leaf sub-domain-id-ipv6 {
                          type leafref {
                            path "/bier:bier/bier:sub-domains/bier:sub-domain/bier:sub-domain-id";
                          }
                          must "../../../../../../../../../ni:name ='_public_' or ../../../../../inter-area-seg-enable='false'";
                          must "../../../star-star[sub-domain-id-ipv6=current()] or ../../../../../ipmsi-tunnel[sub-domain-id-ipv6=current()]";
                          must "/bier:bier/bier:sub-domains/bier:sub-domain[bier:sub-domain-id=current()][bier:address-family='ipv6-unicast']";
                          description
                            "S-PMSI BIER IPv6 sub-domain ID.";
                        }
                        leaf bsl-ipv6 {
                          type leafref {
                            path "/bier:bier/bier:sub-domains/bier:sub-domain[bier:sub-domain-id=current()/../sub-domain-id-ipv6]/bier:encapsulations/bier:encapsulation/bier:bsl";
                          }
                          must "../../../star-star[bsl-ipv6=current()] or ../../../../../ipmsi-tunnel[bsl-ipv6=current()]";
                          description
                            "S-PMSI BIER IPv6 BitString length.";
                        }
                      }
                    }
                  }
                }
              }
            }
            container spmsis {
              config false;
              description
                "Operational state of S-PMSI.";
              container te-tunnels {
                description
                  "List of S-PMSI TE tunnel state.";
                list te-tunnel {
                  key "te-p2mp-id te-tunnel-id te-extend-tunnel-id";
                  description
                    "S-PMSI TE tunnel state.";
                  leaf te-p2mp-id {
                    type pub-type:hex-binary;
                    description
                      "P2MP ID of the P2MP tunnel.";
                  }
                  leaf te-tunnel-id {
                    type uint32;
                    description
                      "ID of the P2MP tunnel.";
                  }
                  leaf te-extend-tunnel-id {
                    type inet:ip-address-no-zone;
                    description
                      "P2MP extended tunnel interface ID.";
                  }
                  uses tunnel-sg-info-type;
                }
              }
              container ldp-tunnels {
                description
                  "List of S-PMSI LDP tunnel state.";
                list ldp-tunnel {
                  key "ldp-route-addr opaque-value";
                  description
                    "S-PMSI LDP tunnel state.";
                  leaf ldp-route-addr {
                    type inet:ip-address-no-zone;
                    description
                      "IP address of the root of a P2MP LSP.";
                  }
                  leaf opaque-value {
                    type string {
                      length "1..255";
                    }
                    description
                      "P2MP LSP ID.";
                  }
                  uses tunnel-sg-info-type;
                }
              }
              container bier-tunnels {
                description
                  "List of S-PMSI BIER tunnel.";
                list bier-tunnel {
                  key "tunnel-id root-ip";
                  description
                    "Operational state of S-PMSI BIER tunnel.";
                  leaf tunnel-id {
                    type uint32 {
                      range "0..4294967295";
                    }
                    description
                      "Tunnel ID.";
                  }
                  leaf root-ip {
                    type inet:ip-address-no-zone;
                    description
                      "Root IP address.";
                  }
                  leaf vpn-label {
                    type uint32 {
                      range "0..4294967295";
                    }
                    description
                      "MPLS label.";
                  }
                  leaf sub-domain-id {
                    type uint16 {
                      range "0..255";
                    }
                    description
                      "Sub-domain ID.";
                  }
                  uses bier-tunnel-sg-info-type;
                }
              }
              container bier-ipv6-tunnels {
                description
                  "List of S-PMSI BIER IPv6 tunnel.";
                list bier-ipv6-tunnel {
                  key "tunnel-id root-ip";
                  description
                    "Operational state of S-PMSI BIER tunnel.";
                  leaf tunnel-id {
                    type uint32 {
                      range "0..4294967295";
                    }
                    description
                      "Tunnel ID.";
                  }
                  leaf root-ip {
                    type inet:ip-address-no-zone;
                    description
                      "Root IP address.";
                  }
                  choice src-dt-sid {
                    description
                      "Src-dt SID.";
                    case multicast-sid {
                      description
                        "Multicast service identifier attribute.";
                      leaf multicast-sid {
                        type inet:ipv6-address-no-zone;
                        description
                          "Src-dt SID.";
                      }
                      leaf prefix-len {
                        type uint8;
                        description
                          "Prefix length.";
                      }
                      leaf msid-len {
                        type uint8;
                        description
                          "MSID length.";
                      }
                    }
                    case prefix-sid {
                      description
                        "Prefix-sid attribute.";
                      leaf prefix-sid {
                        type inet:ipv6-address-no-zone;
                        description
                          "Src-dt SID.";
                      }
                    }
                  }
                  leaf sub-domain-id {
                    type uint16 {
                      range "0..255";
                    }
                    description
                      "Sub-domain ID.";
                  }
                  uses bier-ipv6-tunnel-sg-info-type;
                }
              }
            }
            container flow-statistics-enable {
              description
                "Configure flow-statistics function of flow.";
              container bier-ipv6 {
                description
                  "Configure BIERv6 flow-statistics function of flow.";
                uses bier-flow-statistics-type;
              }
            }
            container flow-label-static {
              description
                "Configure flow label function of flow.";
              container bier-ipv6 {
                description
                  "Configure BIERv6 flow label function of flow.";
                uses bier-flow-label-type;
              }
            }
            container network-slice {
              description
                "Configure network slice function of flow.";
              container bier-ipv6 {
                description
                  "Configure BIERv6 network slice function of flow.";
                uses bier-slice-type;
              }
            }
            container send-c-multicast-routes {
              config false;
              description "List of C-Multicast routes sent.";
              list send-c-multicast-route {
                key "source-address group-address global-administrator";
                description "Statistics of C-Multicast route sent.";
                leaf source-address {
                  type inet:ip-address-no-zone;
                  description
                    "Source address.";
                }
                leaf group-address {
                  type inet:ip-address-no-zone;
                  description
                    "Group address.";
                }
                leaf global-administrator {
                  type inet:ip-address-no-zone;
                  description
                    "Global administrator.";
                }
                leaf local-administrator {
                  type "uint32";
                  description
                    "Local administrator.";
                }
                leaf rp-address {
                  type inet:ip-address-no-zone;
                  description
                    "RP address.";
                }
                leaf source-as {
                  type string {
                    length "1..64";
                  }
                  description
                    "Source AS.";
                }
                leaf route-distinguisher {
                  type string {
                    length "3..21";
                  }
                  description
                    "Route distinguisher.";
                }
                leaf create-time {
                  type pub-type:time-tick;
                  units "s";
                  description
                    "Time when the C-Multicast route is sent.";
                }
              }
            }
            container receive-c-multicast-routes {
              config false;
              description "List of C-Multicast routes received.";
              list receive-c-multicast-route {
                key "source-address group-address";
                description "Statistics of C-Multicast route received.";
                leaf source-address {
                  type inet:ip-address-no-zone;
                  description
                    "Source address.";
                }
                leaf group-address {
                  type inet:ip-address-no-zone;
                  description
                    "Group address.";
                }
                leaf rp-address {
                  type inet:ip-address-no-zone;
                  description
                    "RP address.";
                }
                leaf active-time {
                  type pub-type:time-tick;
                  units "s";
                  description
                    "Time since received C-Multicast route.";
                }
                leaf source-as {
                  type string {
                    length "1..64";
                  }
                  description
                    "Source AS.";
                }
                leaf route-distinguisher {
                  type string {
                    length "3..21";
                  }
                  description
                    "Route distinguisher.";
                }
              }
            }
            container sdwan-infos {
              config false;
              description
                "SD-WAN tunnel state.";
              container root-tunnels {
                description
                  "List of SD-WAN Root tunnel state.";
                list root-tunnel {
                  key "source-address group-address";
                  description
                    "SD-WAN Root tunnel state.";
                  leaf source-address {
                    type inet:ip-address-no-zone;
                    description
                      "Source address.";
                  }
                  leaf group-address {
                    type inet:ip-address-no-zone;
                    description
                      "Group address.";
                  }
                  leaf root-site {
                    type "uint32";
                    description
                      "Root SD-WAN Site.";
                  }
                  container leaf-sites {
                    description
                      "List of SD-WAN leaf state.";
                    list leaf-site {
                      key "leaf-site";
                      description
                        "SD-WAN leaf state.";
                      leaf leaf-site {
                        type "uint32";
                        description
                          "Leaf SD-WAN Site.";
                      }
                    }
                  }
                }
              }
              container leaf-tunnels {
                description
                  "List of SD-WAN Leaf tunnel state.";
                list leaf-tunnel {
                  key "source-address group-address";
                  description
                    "SD-WAN Leaf tunnel state.";
                  leaf source-address {
                    type inet:ip-address-no-zone;
                    description
                      "Source address.";
                  }
                  leaf group-address {
                    type inet:ip-address-no-zone;
                    description
                      "Group address.";
                  }
                  leaf root-site {
                    type "uint32";
                    description
                      "Root SD-WAN Site.";
                  }
                  leaf leaf-site {
                    type "uint32";
                    description
                      "Leaf SD-WAN Site.";
                  }
                }
              }
            }
            container send-c-multicast-ext-routes {
              config false;
              description "List of SD-WAN C-Multicast routes sent.";
              list send-c-multicast-ext-route {
                key "source-address group-address";
                description "Statistics of SD-WAN C-Multicast route sent.";
                leaf source-address {
                  type inet:ip-address-no-zone;
                  description
                    "Source address.";
                }
                leaf group-address {
                  type inet:ip-address-no-zone;
                  description
                    "Group address.";
                }
                leaf global-administrator {
                  type "uint32";
                  description
                    "Global administrator.";
                }
                leaf local-administrator {
                  type "uint32";
                  description
                    "Local administrator.";
                }
                leaf source-as {
                  type string {
                    length "1..64";
                  }
                  description
                    "Source AS.";
                }
                leaf route-distinguisher {
                  type string {
                    length "1..21";
                  }
                  description
                    "Route distinguisher.";
                }
                leaf originating-ip {
                  type inet:ip-address-no-zone;
                  description
                    "Originating ip.";
                }
                leaf vrf-route-import {
                  type "uint32";
                  description
                    "Vrf route import.";
                }
                leaf tunnel-encap-attribute {
                  type "uint32";
                  description
                    "Tunnel encapsulate attribute.";
                }
              }
            }
            container receive-c-multicast-ext-routes {
              config false;
              description "List of SD-WAN C-Multicast routes received.";
              list receive-c-multicast-ext-route {
                key "source-address group-address";
                description "Statistics of SD-WAN C-Multicast route received.";
                leaf source-address {
                  type inet:ip-address-no-zone;
                  description
                    "Source address.";
                }
                leaf group-address {
                  type inet:ip-address-no-zone;
                  description
                    "Group address.";
                }
                leaf active-time {
                  type pub-type:time-tick;
                  units "s";
                  description
                    "Time since received C-Multicast route.";
                }
                leaf source-as {
                  type string {
                    length "1..64";
                  }
                  description
                    "Source AS.";
                }
                leaf route-distinguisher {
                  type string {
                    length "3..21";
                  }
                  description
                    "Route distinguisher.";
                }
                leaf originating-ip {
                  type inet:ip-address-no-zone;
                  description
                    "Originating ip.";
                }
              }
            }
          }
        }
        case rosen-mvpn {
          when "../l3vpn:type='ipv4-unicast'";
          description
            "Rosen MVPN.";
          container rosen {
            when "../../../../ni:name!='_public_'";
            description
              "Configure Rosen MVPN.";
            container extranet-rpfs {
              description
                "List of extranet select-RPF.";
              list extranet-rpf {
                key "group-addr group-addr-mask-length";
                max-elements "16";
                description
                  "Configure extranet select-RPF.";
                leaf group-addr {
                  type inet:ipv4-address-no-zone {
                    pattern '(22[4-9]|23\d)(\.(25[0-5]|2[0-4]\d|1\d\d|[1-9]?\d)){3}';
                  }
                  description
                    "Multicast group address. The value ranges from 224.0.0.0 to 239.255.255.255.";
                }
                leaf group-addr-mask-length {
                  type uint32 {
                    range "4..32";
                  }
                  description
                    "Mask length of a multicast group address.";
                }
                leaf src-vrf-name {
                  type leafref {
                    path "/ni:network-instance/ni:instances/ni:instance/ni:name";
                  }
                  must "(../../../../../../../ni:name!=current() and (../mvpn:src-vrf-name = '_public_' or /ni:network-instance/ni:instances/ni:instance[ni:name=current()]/l3vpn:afs/l3vpn:af[l3vpn:type='ipv4-unicast']/l3vpn:route-distinguisher or /ni:network-instance/ni:global/ni:route-distinguisher-auto-ip))";
                  mandatory true;
                  description
                    "RPF source VPN instance.";
                }
              }
            }
            container share-group {
              presence "config share group";
              description
                "Enable/disable multicast-domain share-group.";
              leaf address {
                type inet:ip-address-no-zone;
                mandatory true;
                description
                  "Default MDT or I-PMSI group address for SM mode.";
              }
              leaf mtunnel-number {
                type uint32 {
                  range "0..4095";
                }
                must "(../ip-address and ../ip-mask-length) or not(../ip-address or ../ip-mask-length)";
                mandatory true;
                description
                  "MTI ID.";
              }
              choice mtunnel-ip-configuration {
                description
                  "Mtunnel IP configuration.";
                case use-exist-interface-ip {
                  description
                    "Use IP of an exist interface.";
                  leaf unnumbered-if-name {
                    type leafref {
                      path "/ifm:ifm/ifm:interfaces/ifm:interface/ifm:name";
                    }
                    must "../../../../../../ni:name=/ifm:ifm/ifm:interfaces/ifm:interface[ifm:name=current()]/ifm:vrf-name";
                    must "/ifm:ifm/ifm:interfaces/ifm:interface[ifm:name=current()]/ifm:type='LoopBack'";
                    description
                      "Interface whose IP address is used as the default IP address of an MTI.";
                  }
                }
                case specify-mtunnel-ip {
                  description
                    "Specify an IP.";
                  leaf ip-address {
                    type inet:ipv4-address-no-zone;
                    description
                      "MTI IP address.";
                  }
                  leaf ip-mask-length {
                    type uint32 {
                      range "0..32";
                    }
                    description
                      "Mask length of the MTI IP address.";
                  }
                }
              }
              container remotes {
                config false;
                description
                  "List of remote share-group.";
                list remote {
                  key "address peer-address";
                  description
                    "Remote share-group state.";
                  leaf address {
                    type inet:ip-address-no-zone;
                    description
                      "Remote share-group address.";
                  }
                  leaf peer-address {
                    type inet:ip-address-no-zone;
                    description
                      "Remote MTI IP address.";
                  }
                }
              }
            }
            container switch-group {
              when "../mvpn:share-group";
              description
                "Configure Switch-MDT.";
              leaf switch-delay-time {
                type uint32 {
                  range "3..60";
                }
                units "s";
                default "5";
                description
                  "The delay for switching from the Share-MDT to the Switch-MDT.";
              }
              leaf switch-back-holddown-time {
                type uint32 {
                  range "0..512";
                }
                units "s";
                default "60";
                description
                  "The delay for switching back from the Switch-MDT to the Share-MDT.";
              }
              leaf is-reuse-log {
                type boolean;
                default "false";
                description
                  "Enable/disable the function to record switch-group address reuse information.";
              }
              container group {
                presence "configure switch group";
                description
                  "Enable/disable swicth group policy in MDT.";
                leaf pool-addr {
                  type inet:ipv4-address-no-zone {
                    pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
                  }
                  mandatory true;
                  description
                    "Indicates the start IP address of the switch-group-pool.";
                }
                leaf pool-mask-length {
                  type uint8 {
                    range "24..32";
                  }
                  mandatory true;
                  description
                    "Specifies the mask length of the switch-group-pool.";
                }
                leaf acl-name {
                  type acl:acl4-identity;
                  must "/acl:acl/acl:groups/acl:group[acl:number=number(current())]/acl:type='advance' or /acl:acl/acl:groups/acl:group[acl:identity=current()]/acl:type='advance'";
                  description
                    "Specifies an ACL policy for filtering (S, G) entries that take effect in a switch-group-pool. If no value is specified, the switch-group-pool takes effect for all (S, G) entries.";
                }
                leaf threshold-value {
                  type uint32 {
                    range "0..4194304";
                  }
                  default "0";
                  description
                    "Indicates the multicast packet rate threshold for triggering the switchover from the Share-MDT to the Switch-MDT.";
                }
              }
            }
            container attributes {
              description
                "Configure Rosen MVPN attributes.";
              leaf auto-discovery-mode {
                when "../../mvpn:share-group";
                type auto-discovery-type;
                default "none";
                description
                  "A-D mode.";
              }
              leaf is-switch-without-register {
                when "../../mvpn:share-group";
                type boolean;
                default "false";
                description
                  "Enable/disable the source PE from sending register packets to the RP to establish the SPT on the public network before the switch-group address is used to encapsulate VPN data.";
              }
              leaf ad-import-policy-name {
                when "../auto-discovery-mode='MDT'";
                type leafref {
                  path "/rtp:routing-policy/rtp:policy-definitions/rtp:policy-definition/rtp:name";
                }
                description
                  "AD route-policy.";
              }
              leaf source-interface-name {
                type leafref {
                  path "/ifm:ifm/ifm:interfaces/ifm:interface/ifm:name";
                }
                must "/ifm:ifm/ifm:interfaces/ifm:interface[ifm:name=current()]/ifm:vrf-name='_public_'";
                description
                  "Name of the public network interface whose IP address is used as the default IP address of an MTI.";
              }
            }
            container switch-group-sends {
              config false;
              description
                "List of sent switch-group.";
              list switch-group-send {
                key "switch-group-addr";
                description
                  "Operational data of switch-group sent by a specified VPN instance.";
                leaf switch-group-addr {
                  type inet:ip-address-no-zone;
                  description
                    "Switch-group address.";
                }
                leaf reference-count {
                  type uint32;
                  description
                    "Number of VPN multicast groups joining a switch-group.";
                }
                container sgs {
                  description
                    "List of (S, G) entry.";
                  list sg {
                    key "source-addr group-addr";
                    description
                      "Operational data of (S, G) entry.";
                    leaf source-addr {
                      type inet:ipv4-address-no-zone;
                      description
                        "Source address on the MVPN.";
                    }
                    leaf group-addr {
                      type inet:ipv4-address-no-zone;
                      description
                        "Group address on the MVPN.";
                    }
                    leaf switch-time {
                      type pub-type:time-tick;
                      units "s";
                      description
                        "Switching duration of the VPN multicast (S, G) entry joining the switch-group.";
                    }
                  }
                }
              }
            }
            container switch-group-recvs {
              config false;
              description
                "List of received switch-group.";
              list switch-group-recv {
                key "group-addr";
                description
                  "Operational data of switch-group received by a specified VPN instance.";
                leaf group-addr {
                  type inet:ip-address-no-zone;
                  description
                    "Switch-group address.";
                }
                leaf reference-count {
                  type uint32;
                  description
                    "Number of VPN multicast groups joining the switch-group.";
                }
                leaf active-count {
                  type uint32;
                  description
                    "Number of active VPN multicast groups (with receivers) joining a switch-group.";
                }
                container senders {
                  description
                    "List of peer.";
                  list sender {
                    key "address";
                    description
                      "Operational data of Peer.";
                    leaf address {
                      type inet:ip-address-no-zone;
                      description
                        "BGP peer address of the PE that sends switch-group information.";
                    }
                    leaf active-count {
                      type uint32;
                      description
                        "Number of active VPN multicast groups (with receivers) referenced by a sender.";
                    }
                    container sgs {
                      description
                        "List of VPN (S, G) entries referenced by a switch-group.";
                      list sg {
                        key "source-addr group-addr";
                        description
                          "Operational data of (S, G) entry.";
                        leaf source-addr {
                          type inet:ipv4-address-no-zone;
                          description
                            "MVPN source address.";
                        }
                        leaf group-addr {
                          type inet:ipv4-address-no-zone;
                          description
                            "MVPN group address.";
                        }
                        leaf up-time {
                          type pub-type:time-tick;
                          units "s";
                          description
                            "Creation time of switching messages in which the VPN multicast (S, G) entry is referenced by the Switch-group.";
                        }
                        leaf expire-time {
                          type pub-type:time-tick;
                          units "s";
                          description
                            "Timeout duration of VPN (S, G) entries.";
                        }
                        leaf is-active {
                          type boolean;
                          description
                            "Flag indicating whether a VPN (S, G) entry is active.";
                        }
                      }
                    }
                  }
                }
              }
            }
            container switch-invalid-packet-statistics {
              config false;
              description
                "Switch invalid packet statistics.";
              leaf packet-length {
                type uint32;
                description
                  "Number of messages with invalid lengths.";
              }
              leaf msg-type {
                type uint32;
                description
                  "Number of messages with invalid message types.";
              }
              leaf source-address {
                type uint32;
                description
                  "Number of messages with invalid multicast source addresses.";
              }
              leaf group-address {
                type uint32;
                description
                  "Number of messages with invalid multicast group addresses.";
              }
              leaf switch-group-addr {
                type uint32;
                description
                  "Number of messages with invalid switch group addresses.";
              }
            }
            container control-message-counters {
	          config false;
	          description
	            "List of the sent and received MDT switch messages.";
	          list control-message-counter {
	            key "msg-type";
	            description
	              "Statistics of the sent and received MDT switch messages.";
	            leaf msg-type {
	              type msg-type;
	              description
	                "MDT switch message.";
	            }
	            leaf rcvd-msg-num {
	              type uint32;
	              description
	                "Number of received messages.";
	            }
	            leaf send-msg-num {
	              type uint32;
	              description
	                "Number of sent messages.";
	            }
	            leaf invalid-msg-num {
                  type uint32;
	              description
	                "Number of received invalid messages.";
                }
              }
	        }
          }
        }
        case mldp-in-band-signaling-mvpn {
          when "../l3vpn:type='ipv4-unicast'";
          description 
            "Function mLDP in-band MVPN.";
          container mldp-in-band-signaling {
            when "../../../../ni:name!='_public_'";
            presence "enable mLDP in-band MVPN function";
            description
              "Enable/disable mLDP in-band MVPN function.";
            container extranet-rpfs {
              description
                "List of extranet select-RPF.";
              list extranet-rpf {
                key "group-addr group-addr-mask-length";
                max-elements "16";
                description
                  "Configure extranet select-RPF.";
                leaf group-addr {
                  type inet:ipv4-address-no-zone {
                    pattern '(22[4-9]|23\d)(\.(25[0-5]|2[0-4]\d|1\d\d|[1-9]?\d)){3}';
                  }
                  description
                    "Multicast group address. The value ranges from 224.0.0.0 to 239.255.255.255.";
                }
                leaf group-addr-mask-length {
                  type uint32 {
                    range "4..32";
                  }
                  description
                    "Mask length of a multicast group address.";
                }
                leaf src-vrf-name {
                  type leafref {
                    path "/ni:network-instance/ni:instances/ni:instance/ni:name";
                  }
                  must "(../../../../../../../ni:name!=current() and (../mvpn:src-vrf-name = '_public_' or /ni:network-instance/ni:instances/ni:instance[ni:name=current()]/l3vpn:afs/l3vpn:af[l3vpn:type='ipv4-unicast']/l3vpn:route-distinguisher or /ni:network-instance/ni:global/ni:route-distinguisher-auto-ip))";
                  mandatory true;
                  description
                    "RPF source VPN instance.";
                }
              }
            }
            leaf frr-enable {
              type boolean;
              default "false";
              description
              "Enable/disable MVPN fast reroute function.";
            }
          }
        }
      }
    }
  }
}
