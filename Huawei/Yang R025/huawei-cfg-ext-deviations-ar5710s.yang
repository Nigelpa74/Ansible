/*
Copyright (C) 2025 Huawei Technologies Co., Ltd. All rights reserved.
*/
module huawei-cfg-ext-deviations-ar5710s {
  yang-version 1.1;
  namespace "urn:huawei:yang:huawei-cfg-ext-deviations-ar5710s";
  prefix cfg-ext-devs-ar5710s;

  import huawei-cfg-ext {
    prefix cfg-ext;
  }

  organization
    "Huawei Technologies Co., Ltd.";
  contact
    "Huawei Industrial Base
     Bantian, Longgang
     Shenzhen 518129
     People's Republic of China
     Website: http://www.huawei.com
     Email: support@huawei.com";
  description
    "This module defines deviation statements for huawei-cfg-ext module.";

  revision 2025-02-24 {
    description
      "Initial revision.";
    reference "Huawei private.";
  }

  deviation "/cfg-ext:get-configuration-change" {
    deviate not-supported;
  }
  deviation "/cfg-ext:load-configuration-change" {
    deviate not-supported;
  }
  deviation "/cfg-ext:load-configuration-result" {
    deviate not-supported;
  }
  deviation "/cfg-ext:get-candidate-change" {
    deviate not-supported;
  }
}
