/*
Copyright (C) 2025 Huawei Technologies Co., Ltd. All rights reserved.
*/
module huawei-arp-notification-deviations-ar5710s {
  yang-version 1;
  namespace "urn:huawei:yang:huawei-arp-notification-deviations-ar5710s";
  prefix arp-notification-devs-ar5710s;

  import huawei-arp-notification {
    prefix arp-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-arp-notification module.";

  revision 2025-02-24 {
    description
      "Initial revision.";
    reference "Huawei private.";
  }

  deviation "/arp-notification:detect-abnormal" {
    deviate not-supported;
  }
  deviation "/arp-notification:detect-abnormal-resume" {
    deviate not-supported;
  }
}
