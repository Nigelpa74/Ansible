/*
Copyright (C) 2020-2025 Huawei Technologies Co., Ltd. All rights reserved.
*/
module huawei-openconfig-telemetry-ext {
  // namespace
  namespace "urn:huawei:yang:huawei-openconfig-telemetry-ext";

  prefix "hw-telemetry-ext";

  import openconfig-telemetry { prefix ot;}
  import openconfig-inet-types { prefix oc-inet; }
  import openconfig-telemetry-types { prefix oc-telemetry-types; }
  import ietf-yang-types { prefix yang; }
  import huawei-network-instance { prefix ni; }
  import huawei-extension {prefix ext; }
  import huawei-pub-type { prefix pub-type; }
  
  organization "Huawei Technologies Co., Ltd.";
  contact
      "Huawei Industrial Base
       Bantian, Longgang
       Shenzhen 518129
       People's Republic of China
       Website: http://www.huawei.com
       Email: support@huawei.com
       ";

  description "Data model which creates the condition for the telemetry.";

  //oc-ext:openconfig-version "0.3.0";
  revision 2025-02-18 {
    description
      "Add leaf max-pack-delay to specify the maximum waiting time for packing data.";
    reference
      "Huawei private.";
  }
  revision 2024-09-06 {
    description
      "Add must condition for pack-enable and STREAM_UDP.
       Add leaf fragment max size to specify the maximum size of telemetry packets sent through UDP.";
    reference
      "Huawei private.";
  }
  revision 2024-01-03 {
    description
      "Add rpc resync-subscription.";
    reference
      "Huawei private.";
  }
  revision 2023-07-26 {
    description
      "Add leaf resync-interval and anchor-time.";
    reference
      "Huawei private.";
  }
  revision 2023-02-23 {
    description
      "Add dampening-interval and modify task-name,augment node order.";
    reference
      "Huawei private.";
  }
  revision 2023-01-11 {
    description
      "Add range of sample-interval for sample-adaptive.";
    reference
      "Huawei private.";
  }
  revision 2023-01-09 {
    description
      "Add must condition for sample-adaptive.";
    reference
      "Huawei private.";
  }
  revision 2022-11-19 {
    description
      "Add leaf udp-message-header.";
    reference
      "Huawei private.";
  }
  revision 2022-11-03 {
    description
      "Add leaf udp-max-packet-size.";
    reference
      "Huawei private.";
  }
  revision 2022-04-24 {
    description
      "Add sample-mode for sensor-path. Add sensor-path white list query.";
    reference
      "Huawei private.";
  }
  revision 2022-04-11 {
    description
      "Add work-mode for destination-group.";
    reference
      "Huawei private.";
  }
  revision 2022-02-11 {
    description
      "Modify leaf pack-enable description.";
    reference
      "Huawei private.";
  }
  revision 2022-01-21 {
    description
      "Add pack enable.";
    reference
      "Huawei private.";
  }
  revision 2020-01-10 {
    description
      "Initial revision.";
    reference
      "Huawei private.";
  }
  ext:task-name "telemetry";

  // identity statements
  identity STREAM_UDP {
    base "oc-telemetry-types:STREAM_PROTOCOL";
    description
      "Telemetry stream is carried over a UDP connection.";
  }

  identity ALGORITHM {
  description
    "Base identity for compression algorithm.";
  }

  identity NONE {
    base ALGORITHM;
    description
      "Not compression.";
  }
  identity GZIP {
    base ALGORITHM;
    description
      "GZIP compression algorithm.";
  }

  typedef sample-mode-type {
    type enumeration {
      enum "yang" {
        value 1;		
        description
          "YANG model sample mode.";
      }
    }
    description
      "Sample mode type.";
  }
  typedef udp-msghdr-type {
    type enumeration {
      enum "ietf-netconf-udp-notif" {
        value 1;		
        description
          "Draft-ietf-netconf-udp-notif-08.";
      }
    }
    description
      "Udp message header type.";
  }

  grouping telemetry-global-attribute-config{
    description
      "The global attribute of telemetry.";
    
    leaf json-only-content {
      type boolean;
      default "false";
      description
        "Enable/disable its operation when telemetry-stream-encoding-config.encoding is specified to literal ENC_JSON_IETF within any subscription. If it is set to true, json format will only act on real data content while telemetry message layer will keep on gpb format.";
    }

    leaf cpu-max-usage {
      type uint8 {
        range "1..50";
      }
      units %;
      default "5";
      description
        "Maximum usage of the main control board's CPU used when telemetry collects data.";
    }

    leaf udp-packet-max-size {
      type uint32 {
        range "1472";
      }
      description
        "Maximum UDP packet size.";
    }
    leaf udp-message-header {
      type udp-msghdr-type;
      description
        "The format of the telemetry udp message header.";
    }
    leaf fragment-max-size {
      type uint32 {
        range "1000..65535";
      }
      description
        "Maximum UDP fragment size.";
    }
  }
  
  grouping  telemetry-sensor-path-condition-op-config {
    description
      "Parameters for a filter criterion.";
    
    leaf op-field{
      type string {
        length "1..63";
      }
      description
        "Reference field in the filter criterion. Different paths support different reference fields.";
    }

    leaf op-type{
      type enumeration {
        enum eq {
          value 0;
          description
            "Equal.";
        }
        enum gt {
          value 1;
          description
            "Greater than.";
        }
        enum ge {
          value 2;
          description
            "Greater than or equal.";
        }
        enum lt {
          value 3;
          description
            "Less than.";
        }
        enum le {
          value 4;
          description
            "Less than or equal.";
        }
      }
      description 
        "Reference to the op-type of the filter criterion.";
    }

    leaf op-value{
      type string {
        length "1..20";
      }
      description
        "Comparison value of the filter criterion. Op-value must be an integer and the maximum value range is [0, 9223372036854775807]. For the actual value range, see the definition of op-field in the YANG model.";
    }
      
  }
  
  grouping  telemetry-sensor-path-filter-condition-config {
    description
      "Parameters for filter criteria.";
    
    container conditions {
      description
        "List of filter criteria, including the filter information such as op-field, op-type, and op-value.";

      list condition {
        key "op-field op-type op-value";
        max-elements  "2";
        description
          "Configure the filter criteria.";
        
        leaf "op-field" {
          type leafref {
            path "../config/op-field";
          }
          description
            "Reference to the op-field of the filter criterion.";
        }
        
        leaf "op-type" {
          type leafref {
            path "../config/op-type";
          }
          description
            "Reference to the op-type of the filter criterion.";
        }
        
        leaf "op-value" {
          type leafref {
            path "../config/op-value";
          }
          description
            "Comparison value of the filter criterion. Op-value must be an integer and the maximum value range is [0, 9223372036854775807]. For the actual value range, see the definition of op-field in the YANG model.";
        }
        
        container config {
          description
            "Configure the parameters for a filter criterion.";
          uses  telemetry-sensor-path-condition-op-config;
        }
        container state {
          config false;
          description
            "Operational state of a filter criterion.";
          uses  telemetry-sensor-path-condition-op-config;
        }
      }
    }
  }
  
  grouping  telemetry-sensor-path-filter-attribute-config {
    description
      "Configuration parameters relating to the configured name of the telemetry sensor path filter.";
    
    leaf name {
      type string {
        length "1..8";
        pattern "[A-Za-z0-9]+";
      }
      description "Filter name for the telemetry sensor path filter.";
    }

    leaf op-object {
      type string {
        length "1..128";
      }
      description 
        "Single or multiple objects in the filter criterion. example gpon.0.2.0~gpon.0.2.3, gpon.0.2.5.";
    }

    leaf condition-relation{
      type enumeration {
        enum and {
          value 1;
          description
            "The relationship between filter criteria in a filter of a sampling path is and.";
        }
        enum or {
          value 2;
          description
            "The relationship between filter criteria in a filter of a sampling path is or.";
        }
      }
      default "and";
      description 
        "Relationship between filter criteria in a filter of a sampling path.";
    }
  }
  
  grouping telemetry-sensor-path-filter-config {
      description
        "Condition-based filtering's parameter of the sampling path. If the conditions are met, the data is reported.";
      
      container filters {
        description
          "List of the top level container for filters. If the filter criteria are met, sampled data is sent to a collector. A filter and heartbeat interval or redundancy suppression cannot be configured at the same time.";

        list filter {
          key "name";
          max-elements "1";
          description
            "Configure the sampling path.";
          
          leaf name {
            type leafref {
              path "../config/name";
            }
            description
              "Filter name of a sampling path.";
          }
           
          container config {
            description
              "Configure the parameters for a filter in a sampling path.";
            uses telemetry-sensor-path-filter-attribute-config;
          }
          
          container state {
            config false;
            description
              "Operational state of a filter in a sampling path.";
            uses telemetry-sensor-path-filter-attribute-config;
          }

          uses telemetry-sensor-path-filter-condition-config;
        }
      }    
  }

  grouping telemetry-sensor-path-self-define-event-config { 
    description
      "Parameters for a customized event.";

    leaf description {
      type string {
        length "1..55";
      }
      description
        "Description of a customized event.";
    }
    leaf level {
      type uint32 {
        range "0..255";
      }
      default "0";
      description
        "Level of a customized event.";
    }
    leaf suppress-period {
      type uint32 {
        range "0..3600";
      }
      units s;
      default "10";
      description
        "Suppression period for customized event reporting.";
    }
    leaf depth {
      type uint8 {
        range "1..3";
      }
      default "1";
      description
        "Sampling depth.";
    }
    leaf sample-mode {
      type sample-mode-type;
      description "Switch the sample Mode of the sensor path, only Probe sample mode can be set to Yang model sample mode.";
    }
  }  
  
  grouping telemetry-sensor-path-config-self-define-event {
    description
      "Configuration parameters relating to the grouping of data model paths comprising a sensor grouping.";
      leaf path {
        type string {
          length "1..511";
        }
        description
          "Path to a section of operational state of interest (the sensor).";
      }
      uses telemetry-sensor-path-self-define-event-config;
  }
  grouping telemetry-stream-destination-with-vpn-config {
    description
      "Configuration parameters for the stream destinations.";
      leaf destination-address {
        type oc-inet:ip-address;
        description
          "IP address of the telemetry stream destination. 
           When the destination-address is an IPv4 address, it can only be configured as an class A/B/C address. 
           When the destination-address is an IPv6 address, it cannot be configured as an unspecified address, multicast address, link-local address, loopback address, IPv4-compatible IPv6 address, or IPv4-mapped IPv6 address.";
      }
      leaf destination-port {
        type uint16{
          range 1..65535;
        }
        description
          "Protocol (UDP or TCP) port number for the telemetry stream destination.";
      }
      leaf vpn-instance{
        type leafref {
          path "/ni:network-instance/ni:instances/ni:instance/ni:name";
        }
        description
          "Name of a VPN instance for the telemetry stream destination.";
      }
  
      leaf protocol{
        type identityref {
          base oc-telemetry-types:STREAM_PROTOCOL;
        }
        description "Selection of the transport protocol for the telemetry stream.";
      }

      leaf tls {
        when "../protocol='oc-telemetry-types:STREAM_GRPC'";
        type boolean;
        default "true";
        description
          "Enable/disable data encryption at the transport layer. If encryption is allowed, whether the data is encrypted depends on the SSL policy of the gRPC client. If an SSL policy is configured, data at the transport layer is encrypted. Otherwise, the data is not encrypted.";
      }

      leaf compression {
        when "../protocol='oc-telemetry-types:STREAM_GRPC'";
        type identityref {
          base "ALGORITHM";
        }
        default "NONE";
        description
          "Enable/disable data compression for grpc transportation. Default not compress data. Support gzip currently.";
      }
  }

  grouping telemetry-subscription-sample-adaptive-attribute-config {
    description
    "Configuration parameters relating to the configured name of the telemetry subscription sample adaptive.";
    leaf sensor-group {
      type leafref {
        path "/ot:telemetry-system/ot:sensor-groups/ot:sensor-group/ot:config/ot:sensor-group-id";
      }
      description
        "Reference to the sensor group sample adaptive.";
    }
    leaf sample-interval {
        type uint32 {
            range 1000|5000|10000|30000|60000|180000|300000|900000|1800000;
        }
        description
            "Time in milliseconds between the device's sample of a
            telemetry data source. For example, setting this to 100
            would require the local device to collect the telemetry
            data every 100 milliseconds. There can be latency or jitter
            in transmitting the data, but the sample must occur at
            the specified interval.
            The timestamp must reflect the actual time when the data
            was sampled, not simply the previous sample timestamp +
            sample-interval.";
    }
    leaf op-field {
      type string {
            length "1..63";
          }
      description 
          "Leaf node under a sensor path.";
    }
    leaf op-type {
      type enumeration {
        enum eq {
          value 0;
          description
            "Equal.";
        }
        enum gt {
          value 1;
          description
            "Greater than.";
        }
        enum ge {
          value 2;
          description
            "Greater than or equal.";
        }
        enum lt {
          value 3;
          description
            "Less than.";
        }
        enum le {
          value 4;
          description
            "Less than or equal.";
        }
      }
      description 
        "Reference to the op-type of the sampling adaptive criterion.";
    }
    leaf op-value{
      type string {
        length "1..20";
      }
      description
        "Comparison value of the sampling adaptive criterion. Op-value must be an integer and the maximum value range is [0, 9223372036854775807]. For the actual value range, see the definition of op-field in the YANG model.";
    }
  }

  grouping telemetry-subscription-sample-adaptive-config {
    description
    "Condition-based adaptive parameter of the sampling path leaf. If the conditions are met, the sampling period takes effect based on the adaptive setting.";
    container sample-policys {
      description
      "List of the sample policy for telemetry subscription.";
      list sample-policy {
        key "sensor-group sample-interval op-field op-type op-value";
        description
        "Configure the adaptive sampling interval.";
        leaf sensor-group {
          type leafref {
            path "../config/sensor-group";
          }
          must "count(/ot:telemetry-system/ot:sensor-groups/ot:sensor-group[ot:sensor-group-id=current()]/ot:sensor-paths/ot:sensor-path)=1";
          description
            "Reference to the sensor group sample adaptive.";
        }
        leaf sample-interval {
          type leafref {
            path "../config/sample-interval";
          }
          description "Reference to the sample interval of sample adaptive.";
        }
        leaf op-field {
          type leafref {
            path "../config/op-field";
          }
          description "Reference to the op-field of sample adaptive. The sampling period is changed based on the path data content.";
        }
        leaf op-type {
          type leafref {
            path "../config/op-type";
          }
          description "Reference to the op-type of sample adaptive. The sampling period is changed based on the path data content.";
        }
        leaf op-value {
          type leafref {
            path "../config/op-value";
          }
          description "Reference to the op-value of sample adaptive. The sampling period is changed based on the path data content.";
        }
        container config {
          description
          "Configure the parameters for a sampling adaptive in a sampling subscription.";
          uses telemetry-subscription-sample-adaptive-attribute-config;
        }
        container state {
          config false;
          description
          "Operational state of a sampling adaptive in a sampling subscription.";
          uses telemetry-subscription-sample-adaptive-attribute-config;
        }
      }
    }
  }

  grouping telemetry-destination-group {
    description
      "Parameters for destination group.";
    leaf work-mode {
      type enumeration {
        enum normal {
          value 0;
          description
          "Connect to all destination addresses.";
        }
        enum priority {
          value 1;
          description
          "Connect to the max priority destination address.";
        }
      }
      default "normal";
      description "The work mode of telemetry destionation-group.";
    }
  }

  rpc resync-subscription {
    description "This RPC allows a subscriber of an active onchange subscription to request a full push of objects.";
    input {
      leaf subscription {
        type leafref {
          path "/ot:telemetry-system/ot:subscriptions/ot:persistent/ot:subscription/ot:subscription-name";
        }
        mandatory true;
        description "Reference to the telemetry subscription that is to be resynced.";
      }
      leaf-list sensor-profile {
        type leafref {
          path "/ot:telemetry-system/ot:subscriptions/ot:persistent/ot:subscription[ot:subscription-name=current()/../subscription]/ot:sensor-profiles/ot:sensor-profile/ot:sensor-group";
        }
        description "Reference to the telemetry sensor-profile that is to be resynced.";
      }
    }
  }

  // typedef statements
  augment "/ot:telemetry-system" {
    description
        "Top level configuration and state for the device's telemetry system.";
         
    container global {
      description "Configure the global attribute of telemetry.";
      
      container config {
        description
          "Configure the parameters relating to the telemetry global attribute.";
        uses telemetry-global-attribute-config;
      }
      
      container state {
        config false;
        description
          "Operational state of information relating to the telemetry global attribute.";
        uses telemetry-global-attribute-config;
        container telemetry-sensor-path-white-list {
          description
            "Statistics of Telemetry sensor path white list.";
          list sensor-paths {
            key "sensor-path";
            description
              "Statistics of Telemetry sensor paths.";
            leaf sensor-path {
              type string{
                length "1..512";
              }
              description
                "The sensor path. for example: openconfig-interfaces:interfaces/interface/state/counters.";
            }
            leaf sample-type{
              type enumeration {
                enum period-sample-probe {
                  value 0;
                  description
                    "The period probe sample type.";
                }
                enum period-sample-yang {
                  value 1;
                  description
                    "The period YANG model sample type.";
                }
                enum onchange {
                  value 2;
                  description
                    "The onchange sample type.";
                }
                enum onchange-plus {
                  value 3;
                  description
                    "The onchange+ sample type.";
                }
                enum alarm {
                  value 4;
                  description
                    "The alarm sample type.";
                }
                enum event {
                  value 5;
                  description
                    "The event sample type.";
                }
              }
              description
                "The default sample type for this sample path.";
              ext:support-filter "true";
            }
            leaf sample-period{
              type uint32;
              units ms;
              description "The minimum sample period.";
            }
            leaf period-count {
              type uint32;
              description
                "The number of nodes acquired in the minimum sample period.";
            }
          }
        }
      }      
    }
  }
  
  augment "/ot:telemetry-system/ot:destination-groups/ot:destination-group/ot:destinations/ot:destination/ot:config" {
    description
      "Configuration parameters relating to telemetry destinations.";

    leaf protocol{
      type identityref {
        base oc-telemetry-types:STREAM_PROTOCOL;
      }
      must "(../protocol!='hw-telemetry-ext:STREAM_UDP') or (../../../../../../ot:subscriptions/ot:persistent/ot:subscription/ot:config/ot:protocol='oc-telemetry-types:STREAM_GRPC') or ((../../../../../../ot:subscriptions/ot:persistent/ot:subscription/ot:destination-groups/ot:destination-group/ot:group-id=../../../../ot:group-id) and (../../../../../../ot:subscriptions/ot:persistent/ot:subscription/ot:config/hw-telemetry-ext:pack-enable='false'))";
      description "Selection of the transport protocol for the telemetry stream.";
    }

    leaf tls {
      when "../protocol='oc-telemetry-types:STREAM_GRPC'";
      type boolean;
      default "true";
      description
        "Enable/disable data encryption at the transport layer. If encryption is allowed, whether the data is encrypted depends on the SSL policy of the gRPC client. If an SSL policy is configured, data at the transport layer is encrypted. Otherwise, the data is not encrypted.";
    }

    leaf compression {
      when "../protocol='oc-telemetry-types:STREAM_GRPC'";
      type identityref {
        base "ALGORITHM";
      }
      default "NONE";
      description
        "Enable/disable data compression for grpc transportation. Default not compress data. Support gzip currently.";
    }

    leaf priority {
      type enumeration {
        enum high {
          value 1;
          description
          "High priority.";
        }
        enum medium {
          value 2;
          description
          "Medium priority.";
        }
        enum low {
          value 3;
          description
          "Low priority.";
        }
      }
      must "(../../../../ot:config/work-mode='priority') and not (../protocol='hw-telemetry-ext:STREAM_UDP')";
      description "Priority value of destination. It only takes effect in priority working mode.";
    }
  }

  augment "/ot:telemetry-system/ot:destination-groups/ot:destination-group/ot:destinations/ot:destination/ot:state" {
    description
      "State information associated with telemetry destinations.";

    leaf protocol{
      type identityref {
        base oc-telemetry-types:STREAM_PROTOCOL;
      }
      must "(../protocol!='hw-telemetry-ext:STREAM_UDP') or (../../../../../../ot:subscriptions/ot:persistent/ot:subscription/ot:config/ot:protocol='oc-telemetry-types:STREAM_GRPC') or ((../../../../../../ot:subscriptions/ot:persistent/ot:subscription/ot:destination-groups/ot:destination-group/ot:group-id=../../../../ot:group-id) and (../../../../../../ot:subscriptions/ot:persistent/ot:subscription/ot:config/hw-telemetry-ext:pack-enable='false'))";
      description "Selection of the transport protocol for the telemetry stream.";
    }

    leaf tls {
      when "../protocol='oc-telemetry-types:STREAM_GRPC'";
      type boolean;
      default "true";
      description
        "Whether data encryption at the transport layer is allowed. If encryption is allowed, whether the data is encrypted depends on the SSL policy of the gRPC client. If an SSL policy is configured, data at the transport layer is encrypted. Otherwise, the data is not encrypted.";
    }

    leaf compression {
      when "../protocol='oc-telemetry-types:STREAM_GRPC'";
      type identityref {
        base "ALGORITHM";
      }
      description
        "Enable/disable data compression for grpc transportation. Default not compress data. Support gzip currently.";
    }
  
    leaf priority {
      type enumeration {
        enum high {
          value 1;
          description
          "High priority.";
        }
        enum medium {
          value 2;
          description
          "Medium priority.";
        }
        enum low {
          value 3;
          description
          "Low priority.";
        }
      }
      description "Priority value of destination. It only takes effect in priority working mode.";
    }
  }

  augment "/ot:telemetry-system/ot:destination-groups/ot:destination-group/ot:config" {
    description
      "Configuration parameters relating to telemetry destinations.";
    uses telemetry-destination-group;
  }

  augment "/ot:telemetry-system/ot:destination-groups/ot:destination-group/ot:state" {
    description
      "State parameters relating to the telemetry destination-group on the local device.";
    uses telemetry-destination-group;
  }

  augment "/ot:telemetry-system/ot:sensor-groups/ot:sensor-group/ot:sensor-paths/ot:sensor-path"{
    description
      "List of paths in the model which together comprise a sensor grouping. Filters for each path to exclude items are also provided.";

    uses telemetry-sensor-path-filter-config;

  }

  augment "/ot:telemetry-system/ot:sensor-groups/ot:sensor-group/ot:sensor-paths/ot:sensor-path/ot:config"{
    description
      "Configuration parameters to configure a set of data model paths as a sensor grouping.";

    leaf reset-when-start {
      type boolean;
      default "false";
      description 
        "Enable/disable clearing a field in the sampling path when a sampling sensor group is associated with subscription. The fields that can be cleared in different sampling paths are different. The value true indicates that the field is cleared, and the value false indicates that the field is not cleared. Currently, only the sampling path huawei-qos:qos/qosPortQueueStatInfos/qosPortQueueStatInfo allows reset-when-start to be set to true.";
    }
    leaf depth{
      type uint8 {
        range "1..3";
      }
      default "1";
      description
        "Sampling depth.";
    }
    leaf sample-mode {
      type sample-mode-type;
      description "Switch the sample Mode of the sensor path, only Probe sample mode can be set to Yang model sample mode.";
    }
  }
  
  augment "/ot:telemetry-system/ot:sensor-groups/ot:sensor-group/ot:sensor-paths/ot:sensor-path/ot:state"{
    description
      "Configuration parameters to configure a set of data model paths as a sensor grouping.";
  
    leaf reset-when-start {
      type boolean;
      default "false";
      description 
        "Enable/disable clearing a field in the sampling path when a sampling sensor group is associated with subscription. The fields that can be cleared in different sampling paths are different. The value true indicates that the field is cleared, and the value false indicates that the field is not cleared. Currently, only the sampling path huawei-qos:qos/global-query/default-queue-statisticss/default-queue-statistics allows reset-when-start to be set to true.";
    }
    leaf depth{
      type uint8 {
        range "1..3";
      }
      default "1";
      description
        "Sampling depth.";
    }
    leaf sample-mode {
      type sample-mode-type;
      description "Switch the sample Mode of the sensor path, only Probe sample mode can be set to Yang model sample mode.";
    }
  }

  augment "/ot:telemetry-system/ot:subscriptions/ot:persistent/ot:subscription/ot:config" {
    description
      "Config parameters relating to the telemetry subscriptions on the local device.";

    leaf local-source-port {
      when "../ot:local-source-address or ../hw-telemetry-ext:local-source-interface";
      type uint16 {
        range "1..65535";
      }
      description "Source port of UDP packets from the device to a telemetry collector destination. The port range is 1025..65535 when used by IPv6.";
    }

    leaf tls {
      when "../ot:protocol='oc-telemetry-types:STREAM_GRPC'";
      type boolean;
      default "true";
      description
        "Enable/disable data encryption at the transport layer. If encryption is allowed, whether the data is encrypted depends on the SSL policy of the gRPC client. If an SSL policy is configured, data at the transport layer is encrypted. Otherwise, the data is not encrypted.";
    }

    leaf local-source-interface {
      type pub-type:if-name;
      must "not(../ot:local-source-address)";
      description
        "Interface which will be the source of packets from the device to a telemetry collector destination.";
    }

    leaf compression {
      when "../ot:protocol='oc-telemetry-types:STREAM_GRPC'";
      type identityref {
        base "ALGORITHM";
      }
      default "NONE";
      description
        "Enable/disable data compression for grpc transportation. Default not compress data. Support gzip currently.";
    }

    leaf pack-enable {
      type boolean;
      must "(../hw-telemetry-ext:pack-enable='false') or ((../ot:protocol='oc-telemetry-types:STREAM_GRPC') or (not(../ot:protocol) and (../../../../../ot:destination-groups/ot:destination-group/ot:config/ot:group-id=../../ot:destination-groups/ot:destination-group/ot:group-id) and (../../../../../ot:destination-groups/ot:destination-group/ot:destinations/ot:destination/ot:config/hw-telemetry-ext:protocol!='hw-telemetry-ext:STREAM_UDP')))";
      default "false";
      description
        "Enable/disable packing of sampled data. Data packing is disabled by default.";
    }

    leaf max-pack-delay {
      when "../hw-telemetry-ext:pack-enable='true'";
      type uint32 {
        range "10000..1800000";
      }
      units ms;
      description
        "Maximum waiting time for packing data.";
    }

    leaf dampening-interval {
      type uint32 {
        range "100..60000";
      }
      units ms;
      must "not (../../ot:sensor-profiles/ot:sensor-profile/ot:config/ot:sample-interval) or (../../ot:sensor-profiles/ot:sensor-profile/ot:config/ot:sample-interval=0)";
      description
        "Minimum interval between the report of onchange datas. The new changes during the interval are accumulated.";
    }

    leaf resync-interval {
      type uint32 {
          range "60..10080";
      }
      units min;
      must "../../ot:sensor-profiles/ot:sensor-profile/ot:config/ot:sample-interval = 0";
      description
        "A full push of sampled data of a onchange plus task will be re-sent once per resync interval in minute regardless of whether the value has changed or not.";
    }

	leaf anchor-time {
      type yang:date-and-time;
      must "(../../ot:sensor-profiles/ot:sensor-profile/ot:config/ot:sample-interval >= 60000) and (../../ot:sensor-profiles/ot:sensor-profile/ot:config/ot:suppress-redundant = 'false' or not (../../ot:sensor-profiles/ot:sensor-profile/ot:config/ot:suppress-redundant)) and (../../ot:sensor-profiles/ot:sensor-profile/ot:config/ot:heartbeat-interval = 0 or not (../../ot:sensor-profiles/ot:sensor-profile/ot:config/ot:heartbeat-interval)) and (not (../../hw-telemetry-ext:sample-policys/sample-policy)) and (../hw-telemetry-ext:anchor-time = '1970-01-01T00:00:00Z')";
      description
        "Designates a timestamp before or after which a series of periodic push updates are determined. The next update will take place at a point in time that is a multiple of a period from the 'anchor-time'. For example, for an 'anchor-time' that is set for the top of a particular minute and a period interval of a minute, updates will be sent at the top of every minute that this subscription is active.";    
    }
  }  

  augment "/ot:telemetry-system/ot:subscriptions/ot:persistent/ot:subscription/ot:state" {
    description
      "State parameters relating to the telemetry subscriptions on the local device.";
  
    leaf local-source-port {
      when "../ot:local-source-address or ../hw-telemetry-ext:local-source-interface";
      type uint16 {
        range "1..65535";
      }
      description "Source port of UDP packets from the device to a telemetry collector destination. The port range is 1025..65535 when used by IPv6.";
    }

    leaf tls {
      when "../ot:protocol='oc-telemetry-types:STREAM_GRPC'";
      type boolean;
      default "true";
      description
        "Whether data encryption at the transport layer is allowed. If encryption is allowed, whether the data is encrypted depends on the SSL policy of the gRPC client. If an SSL policy is configured, data at the transport layer is encrypted. Otherwise, the data is not encrypted.";
    }

    leaf local-source-interface {
      type pub-type:if-name;
      must "not(../ot:local-source-address)";
      description
        "Interface which will be the source of packets from the device to a telemetry collector destination.";
    }

    leaf compression {
      when "../ot:protocol='oc-telemetry-types:STREAM_GRPC'";
      type identityref {
        base "ALGORITHM";
      }
      description
        "Enable/disable data compression for grpc transportation. Default not compress data. Support gzip currently.";
    }

    leaf pack-enable {
      type boolean;
      must "(../hw-telemetry-ext:pack-enable='false') or ((../ot:protocol='oc-telemetry-types:STREAM_GRPC') or (not(../ot:protocol) and (../../../../../ot:destination-groups/ot:destination-group/ot:config/ot:group-id=../../ot:destination-groups/ot:destination-group/ot:group-id) and (../../../../../ot:destination-groups/ot:destination-group/ot:destinations/ot:destination/ot:config/hw-telemetry-ext:protocol!='hw-telemetry-ext:STREAM_UDP')))";
      default "false";
      description
        "Enable/disable packing of sampled data. Data packing is disabled by default.";
    }

    leaf max-pack-delay {
      when "../hw-telemetry-ext:pack-enable='true'";
      type uint32 {
        range "10000..1800000";
      }
      units ms;
      description
        "Maximum waiting time for packing data.";
    }

    leaf dampening-interval {
      type uint32 {
        range "100..60000";
      }
      units ms;
      must "not (../../ot:sensor-profiles/ot:sensor-profile/ot:config/ot:sample-interval) or (../../ot:sensor-profiles/ot:sensor-profile/ot:config/ot:sample-interval=0)";
      description
        "Minimum interval between the report of onchange datas. The new changes during the interval are accumulated.";
    }

    leaf resync-interval {
      type uint32 {
          range "60..10080";
      }
      units min;
      must "../../ot:sensor-profiles/ot:sensor-profile/ot:config/ot:sample-interval = 0";
      description
        "A full push of sampled data of a onchange plus task will be re-sent once per resync interval in minute regardless of whether the value has changed or not.";
    }

	leaf anchor-time {
      type yang:date-and-time;
      must "(../../ot:sensor-profiles/ot:sensor-profile/ot:config/ot:sample-interval >= 60000) and (../../ot:sensor-profiles/ot:sensor-profile/ot:config/ot:suppress-redundant = 'false' or not (../../ot:sensor-profiles/ot:sensor-profile/ot:config/ot:suppress-redundant)) and (../../ot:sensor-profiles/ot:sensor-profile/ot:config/ot:heartbeat-interval = 0 or not (../../ot:sensor-profiles/ot:sensor-profile/ot:config/ot:heartbeat-interval)) and (not (../../hw-telemetry-ext:sample-policys/sample-policy)) and (../hw-telemetry-ext:anchor-time = '1970-01-01T00:00:00Z')";
      description
        "Designates a timestamp before or after which a series of periodic push updates are determined. The next update will take place at a point in time that is a multiple of a period from the 'anchor-time'. For example, for an 'anchor-time' that is set for the top of a particular minute and a period interval of a minute, updates will be sent at the top of every minute that this subscription is active.";    
    }
  }
  augment "/ot:telemetry-system/ot:subscriptions/ot:persistent/ot:subscription" {
    description
      "Configuration parameters relating to the telemetry sample adaptive on the local device.";
    uses telemetry-subscription-sample-adaptive-config;
  }
  augment "/ot:telemetry-system/ot:sensor-groups/ot:sensor-group"{
    description
      "List of telemetry sensory groups on the local system, where a sensor grouping represents a resuable grouping of multiple paths and excludes filters.";

    container sensor-paths-self-define-event {
      description
        "Configure the top level container to hold a set of customized events' sensor paths grouped together. Customized events and heartbeat interval or redundancy suppression cannot be configured at the same time. A customized event can take effect only after at least one filter criterion is configured for the event.";

        list sensor-path {
          key "path";
          description
            "Configure the customized events.";

          leaf path {
            type leafref {
              path "../config/path";
            }
            description
              "Reference to the path of interest.";
            }
          container config {
            description
              "Configure the parameters for a customized event.";
            uses telemetry-sensor-path-config-self-define-event;
          }
          container state {
            config false;
            description
              "Operational state of a customized event.";
            uses telemetry-sensor-path-config-self-define-event;
          }
          uses telemetry-sensor-path-filter-config;
        }
    }
  }
  
  augment "/ot:telemetry-system/ot:destination-groups/ot:destination-group" {
    description
      "List of destination-groups. Destination groups allow the reuse of common telemetry destinations across the telemetry configuration. An operator references a set of destinations via the configurable destination-group-identifier. A destination group may contain one or more telemetry destinations.";

    container destinations-with-vpn {
      description
        "Configure the destination container to list the information about the destination with VPN information such as the IP address, port, and VPN instance of the telemetry messages from the network element.";
      list destination-with-vpn {
        key "destination-address destination-port vpn-instance";
        description
          "Configure the telemetry stream destinations, including vpn-instance.";

        leaf destination-address {
          type leafref {
             path "../config/destination-address";
          }
          description
             "Reference to the destination address of the telemetry stream.";
        }

        leaf destination-port {
          type leafref {
            path "../config/destination-port";
          }
          description
            "Reference to the port number of the stream destination.";
        }

        leaf vpn-instance {
          type leafref {
            path "../config/vpn-instance";
          }
          description
            "Name of a VPN instance for the telemetry stream destination.";
        }

        container config {
          description
            "Configure the parameters relating to telemetry destinations.";
          uses telemetry-stream-destination-with-vpn-config;
        }

        container state {
          config false;
          description
            "Telemetry destinations-associated state.";
          uses telemetry-stream-destination-with-vpn-config;
        }
      }
    }
  }
  
  augment "/ot:telemetry-system/ot:destination-groups/ot:destination-group/hw-telemetry-ext:destinations-with-vpn/hw-telemetry-ext:destination-with-vpn/hw-telemetry-ext:config" {
    description
      "Configuration parameters relating to telemetry destination-with-vpn.";
    leaf priority {
      type enumeration {
        enum high {
          value 1;
          description
          "High priority.";
        }
        enum medium {
          value 2;
          description
          "Medium priority.";
        }
        enum low {
          value 3;
          description
          "Low priority.";
        }
      }
      must "(../../../../ot:config/work-mode='priority') and not (../protocol='hw-telemetry-ext:STREAM_UDP')";
      description "Priority value of destination. It only takes effect in priority working mode.";
    }
  }

  augment "/ot:telemetry-system/ot:destination-groups/ot:destination-group/hw-telemetry-ext:destinations-with-vpn/hw-telemetry-ext:destination-with-vpn/hw-telemetry-ext:state" {
    description
      "State information associated with telemetry destination-with-vpn.";
    leaf priority {
      type enumeration {
        enum high {
          value 1;
          description
          "High priority.";
        }
        enum medium {
          value 2;
          description
          "Medium priority.";
        }
        enum low {
          value 3;
          description
          "Low priority.";
        }
      }
      description "Priority value of destination. It only takes effect in priority working mode.";
    }
  }
}
