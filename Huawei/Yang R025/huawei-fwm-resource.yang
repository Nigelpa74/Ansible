/*
Copyright (C) 2020-2025 Huawei Technologies Co., Ltd. All rights reserved.
*/
module huawei-fwm-resource {
  yang-version 1;
  namespace "urn:huawei:yang:huawei-fwm-resource";
  prefix fwm-resource;
  import huawei-extension {
    prefix ext;
  }
  import huawei-fib {
    prefix fib;
  }
  import huawei-arp {
    prefix arp;
  }
  import huawei-ipv6-nd {
    prefix ipv6-nd;
  }

  organization
    "Huawei Technologies Co., Ltd.";
  contact
    "Huawei Industrial Base
    Bantian, Longgang
    Shenzhen 518129
    People's Republic of China
    Website: http://www.huawei.com
    Email: support@huawei.com";
  description
    "FWM resource statistics.";
  revision 2025-05-25 {
    description
      "Add super-mac mode.";
    reference
      "Huawei private.";
  }
  revision 2025-03-21 {
    description
      "Add enhance mode.";
    reference
      "Huawei private.";
  }
  revision 2024-09-27 {
    description
      "Delete the condition of fwm-resource-mode.";
    reference
      "Huawei private.";
  }
  revision 2024-09-26 {
    description
      "Modify ext:advised-node for resource-modes.";
    reference
      "Huawei private.";
  }
  revision 2024-03-14 {
    description
      "Add ext:advised-node for resource-modes.";
    reference
      "Huawei private.";
  }
  revision 2024-02-28 {
    description
      "Add fwm-resource-mode node.";
    reference
      "Huawei private.";
  }
  revision 2023-08-16 {
    description
      "Delete the mandatory attribute of the key node 'mode'.";
    reference
      "Huawei private.";
  }
  revision 2023-08-04 {
    description
      "Add resource-mode-type enum large-user and large-flow.";
    reference
      "Huawei private.";
  }
  revision 2023-07-13 {
    description
      "Add resource-type enum mfibv4v6.";
    reference
      "Huawei private.";
  }
  revision 2022-09-29 {
    description
      "Add resource-usages node.";
    reference
      "Huawei private.";
  }
  revision 2022-05-28 {
    description
      "Delete slot-id.";
    reference
      "Huawei private.";
  }
  revision 2022-05-10 {
    description
      "Add large-multicast mode for CE-P5.";
    reference
      "Huawei private.";
  }
  revision 2022-04-01 {
    description
      "Add balance mode for CE5981.";
    reference
      "Huawei private.";
  }
  revision 2022-03-18 {
    description
      "The default config is added and the leaf mode is mandatory.";
    reference
      "Huawei private.";
  }
  revision 2021-12-03 {
    description
      "Leaf slot-id is unique.";
    reference
      "Huawei private.";
  }
  revision 2020-09-01 {
    description
      "List of resource mode is added.";
    reference
      "Huawei private.";
  }
  revision 2020-06-02 {
    description
      "Initial revision.";
    reference
      "Huawei private.";
  }
  typedef resource-mode-type {
    type enumeration {
      enum "standard" {
        value 1;
        description
          "Standard resource mode.";
      }
      enum "large-mac" {
        value 2;
        description
          "Big MAC mode.";
      }
      enum "large-route" {
        value 3;
        description
          "Big route mode.";
      }
      enum "user-defined" {
        value 4;
        description
          "User defined mode.";
      }
      enum "balance" {
        value 5;
        description
          "Balance mode.";
      }
      enum "large-multicast" {
        value 6;
        description
          "Big multicast mode.";
      }
      enum "large-user" {
        value 7;
        description
          "Big user mode.";
      }
      enum "large-flow" {
        value 8;
        description
          "Big flow mode.";
      }
      enum "super-mac" {
        value 16;
        description
          "Super mac mode.";
      }
    }
    description
      "Enumerations of resource mode.";
  }
  typedef resource-type {
    type enumeration {
      enum "mcid" {
        value 1;
        description
          "Resource type is MCID.";
      }
      enum "elb" {
        value 2;
        description
          "Resource type is ELB.";
      }
      enum "mfibv4" {
        value 3;
        description
          "Resource type is MFIBV4.";
      }
      enum "mfibv6" {
        value 4;
        description
          "Resource type is MFIBV6.";
      }
      enum "mfibv4v6" {
        value 5;
        description
          "Resource type is the sum of MFIBV4 and MFIBV6.";
      }
    }
    description
      "Enumerations of resource type.";
  }
  container fwm-resource {
    description
      "FWM resource management.";
    container resource-modes {
      status deprecated;
      description
        "List of resource mode's configurations.";
      list resource-mode {
        must "(./mode='user-defined' and (./mac-num>=32 and ./mac-num <= 800)) or (./mode!='user-defined')";
        key "mode";
        status deprecated;
        description
          "Configure resource mode.";
        ext:generated-by system {
          ext:filter "mode = 'standard'";
        }
        leaf mode {
          type resource-mode-type;
          status deprecated;
          description
            "Resource mode.";
        }
        leaf mac-num {
          when "../mode='user-defined'";
          type uint32 {
            range "32..800";
          }
          status deprecated;
          description
            "User defined MAC number.";
        }
        ext:advised-node "../../fwm-resource:fwm-resource-mode";
      }
    }
    container fwm-resource-mode {
      description
        "Configure resource mode.";
      leaf mode {
        type resource-mode-type;
        default "standard";
        description
          "Resource mode.";
      }
      leaf mac-num {
        when "../mode='user-defined'";
        type uint32 {
          range "32..800";
        }
        description
          "User defined MAC number.";
      }
      leaf enhance {
        type empty;
        description
          "Enhance mode.";
      }
    }
    container resource-usages {
      config false;
      description
      "List of resource usage statistics.";
      list resource-usage {
        key "slot type";
        description
          "Resource usage statistics.";
        leaf slot {
          type string {
            length "0..32";
          }
          description
            "Slot ID.";
        }
        leaf type {
          type resource-type;
          description
            "Resource type.";
        }
        leaf total {
          type uint32;
          description
            "Resource total num.";
        }
        leaf used {
          type uint32;
          description
            "Resource used num.";
        }
      }
    }
  }
  augment /fib:fib {
    description
      "FIB resource statistics.";
    container forward-table-resources {
      config false;
      description
        "List of table resource statistics.";
      list forward-table-resource {
        key "slot-id";
        description
          "List of table resource statistics.";
        leaf slot-id {
          type string {
            length "0..32";
          }
          description
            "Slot ID.";
        }
        leaf fib4-total {
          type uint32;
          description
            "FIB4 total number.";
        }
        leaf fib4-used {
          type uint32;
          description
            "FIB4 used number.";
        }
        leaf fib6-total {
          type uint32;
          description
            "FIB6 total number.";
        }
        leaf fib6-used {
          type uint32;
          description
            "FIB6 used number.";
        }
      }
    }
    container soft-table-resources {
      config false;
      description
        "List of soft table resource statistics.";
      list soft-table-resource {
        key "slot-id";
        description
          "List of soft table resource statistics.";
        leaf slot-id {
          type string {
            length "0..32";
          }
          description
            "Slot ID.";
        }
        leaf fib4-total {
          type uint32;
          description
            "FIB4 total number.";
        }
        leaf fib4-used {
          type uint32;
          description
            "FIB4 used number.";
        }
        leaf fib6-total {
          type uint32;
          description
            "FIB6 total number.";
        }
        leaf fib6-used {
          type uint32;
          description
            "FIB6 used number.";
        }
      }
    }
  }
  augment /arp:arp {
    description
      "ARP resource statistics.";
    container forward-table-resources {
      config false;
      description
        "List of table resource statistics.";
      list forward-table-resource {
        key "slot-id";
        description
          "List of table resource statistics.";
        leaf slot-id {
          type string {
            length "0..32";
          }
          description
            "Slot ID.";
        }
        leaf arp-total {
          type uint32;
          description
            "ARP total number.";
        }
        leaf arp-used {
          type uint32;
          description
            "ARP used number.";
        }
      }
    }
    container soft-table-resources {
      config false;
      description
        "List of soft table resource statistics.";
      list soft-table-resource {
        key "slot-id";
        description
          "List of soft table resource statistics.";
        leaf slot-id {
          type string {
            length "0..32";
          }
          description
            "Slot ID.";
        }
        leaf arp-total {
          type uint32;
          description
            "ARP total number.";
        }
        leaf arp-used {
          type uint32;
          description
            "ARP used number.";
        }
      }
    }
  }
  augment /ipv6-nd:ipv6-nd {
    description
      "ND resource statistics.";
    container forward-table-resources {
      config false;
      description
        "List of table resource statistics.";
      list forward-table-resource {
        key "slot-id";
        description
          "List of table resource statistics.";
        leaf slot-id {
          type string {
            length "0..32";
          }
          description
            "Slot ID.";
        }
        leaf nd-total {
          type uint32;
          description
            "ND total number.";
        }
        leaf nd-used {
          type uint32;
          description
            "ND used number.";
        }
      }
    }
    container soft-table-resources {
      config false;
      description
        "List of soft table resource statistics.";
      list soft-table-resource {
        key "slot-id";
        description
          "List of soft table resource statistics.";
        leaf slot-id {
          type string {
            length "0..32";
          }
          description
            "Slot ID.";
        }
        leaf nd-total {
          type uint32;
          description
            "ND total number.";
        }
        leaf nd-used {
          type uint32;
          description
            "ND used number.";
        }
      }
    }
  }
  ext:task-name "forwarding";
}
