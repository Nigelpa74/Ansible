/*
Copyright (C) 2019-2023 Huawei Technologies Co., Ltd. All rights reserved.
*/
submodule huawei-nqa-global {
  yang-version 1;
  belongs-to huawei-nqa {
    prefix nqa;
  }
  import huawei-ifm {
    prefix ifm;
  }
  organization
    "Huawei Technologies Co., Ltd.";
  contact
    "Huawei Industrial Base
     Bantian, Longgang
     Shenzhen 518129
     People's Republic of China
     Website: http://www.huawei.com
     Email: support@huawei.com";
  description
    "Description of submodule nqa-global.";
  revision 2023-08-30 {
    description
      "Delete cir-interval and pir-interval must condiation.";
    reference
      "Huawei private.";
  }
  revision 2020-07-04 {
    description
      "Add BIER IPv6 OAM.";
    reference
      "Huawei private.";
  }
  revision 2019-03-30 {
    description
      "Initial revision.";
    reference
      "Huawei private.";
  }
  grouping global-type {
    description
      "Global configuration.";
    leaf fec-validation-ldp-enable {
      type boolean;
      default "true";
      description
        "Enable/disable LDP FEC validation.";
    }
    leaf fec-validation-sr-prefix-enable {
      type boolean;
      default "true";
      description
        "Enable/disable sr-prefix FEC validation.";
    }
    leaf lspv-cpu-limit {
      type uint16 {
        range "10..65535";
      }
      default "1000";
      description
        "Lspv cpu limit.";
    }
    leaf jitter-tag-version {
      type uint32 {
        range "1..2";
      }
      default "1";
      description
        "Version number of jitter.";
    }
    leaf lbm-receive-enable {
      type boolean;
      default "true";
      description
        "Enable/disable a device from receiving LBM packets.";
    }
    leaf ltm-receive-enable {
      type boolean;
      default "true";
      description
        "Enable/disable a device from receiving LTM packets.";
    }
    leaf gmac-ltm-receive-enable {
      type boolean;
      default "true";
      description
        "Enable/disable a device from receiving GMAC-LTM packets.";
    }
    leaf lspv-enable {
      type boolean;
      default "true";
      description
        "Enable/disable a device to respond to MPLS echo request packets.";
    }
    leaf lspv-ipv6-enable {
      type boolean;
      default "true";
      description
        "Enable/disable a device to respond to MPLS echo request IPv6 packets.";
    }
    leaf lspv-fec-compitable-enable {
      type boolean;
      default "false";
      description
        "Enable/disable the LSPV's compatibility function, and reply response packets don't carry FEC information.";
    }
    leaf gmac-ping-enable {
      type boolean;
      default "false";
      description
        "Enable/disable general GMAC ping function.";
    }
    leaf gmac-trace-enable {
      type boolean;
      default "false";
      description
        "Enable/disable general GMAC trace function.";
    }
    leaf test-max-flow-id {
      type uint16;
      config false;
      description
        "Maximum NQA test flow ID.";
    }
    leaf reflector-max-id {
      type uint32;
      config false;
      description
        "Maximum NQA reflector ID.";
    }
    leaf trunk-member-inspect-enable {
      type boolean;
      default "false";
      description
        "Enable/disable NQA trunk member inspect function.";
    }
    container vxlan-echo-v4 {
      presence "If enabled vxlan echo IPv4";
      description
        "Enable/disable NQA VXLANECHO.";
      leaf port {
        type uint16 {
          range "1..65535";
        }
        mandatory true;
        description
          "Port of NQA VXLANECHO server.";
      }
      leaf source-ip-if-name {
        type leafref {
          path "/ifm:ifm/ifm:interfaces/ifm:interface/ifm:name";
        }
        description
          "Source IP interface of VXLANECHO.";
      }
    }
    container vxlan-echo-v6 {
      presence "If enabled IPv6 vxlan echo";
      description
        "Enable/disable NQA IPv6 VXLANECHO.";
      leaf port {
        type uint16 {
          range "1..65535";
        }
        mandatory true;
        description
          "Port of IPv6 NQA VXLANECHO server.";
      }
      leaf source-ip-if-name {
        type leafref {
          path "/ifm:ifm/ifm:interfaces/ifm:interface/ifm:name";
        }
        description
          "Source IP interface of IPv6 VXLANECHO.";
      }
    }
    container icmp-session-car {
      description
        "Configure ICMP Session CAR.";
      leaf enable {
        type boolean;
        default "true";
        description
          "Enable/disable ICMP Session CAR.";
      }
      leaf cir-interval {
        type uint32 {
          range "1..100";
        }
        units "kbit/s";
        default "2";
        description
          "Specify the Session CAR CIR interval.";
      }
      leaf cbs-interval {
        type uint32 {
          range "1000..100000";
        }
        units "Byte";
        default "10000";
        description
          "Specify the Session CAR CBS interval.";
      }
      leaf pir-interval {
        type uint32 {
          range "100..1000";
        }
        units "kbit/s";
        default "512";
        description
          "Specify the Session CAR PIR interval.";
      }
      leaf pbs-interval {
        type uint32 {
          range "100000..1000000";
        }
        units "Byte";
        default "256000";
        description
          "Specify the Session CAR PBS interval.";
      }
    }
    container icmpv6-session-car {
      description
        "Configure ICMPv6 Session CAR.";
      leaf enable {
        type boolean;
        default "true";
        description
          "Enable/disable ICMPv6 Session CAR.";
      }
      leaf cir-interval {
        type uint32 {
          range "1..100";
        }
        units "kbit/s";
        default "2";
        description
          "Specify the Session CAR CIR interval.";
      }
      leaf cbs-interval {
        type uint32 {
          range "1000..100000";
        }
        units "Byte";
        default "10000";
        description
          "Specify the Session CAR CBS interval.";
      }
      leaf pir-interval {
        type uint32 {
          range "100..1000";
        }
        units "kbit/s";
        default "512";
        description
          "Specify the Session CAR PIR interval.";
      }
      leaf pbs-interval {
        type uint32 {
          range "100000..1000000";
        }
        units "Byte";
        default "256000";
        description
          "Specify the Session CAR PBS interval.";
      }
    }
    container bier6-oam {
      description
        "Configure BIER IPv6 OAM.";
      leaf dest-port {
        type uint16 {
          range "1..65535";
        }
        default "49100";
        description
          "Destination UDP port of BIER IPv6 echo packet.";
      }
      leaf echo-reply-disable {
        type boolean;
        default "false";
        description
          "Enable/disable BIER IPv6 reply function.";
      }
      leaf rate-limit {
        type uint16 {
          range "10..65535";
        }
        units "pps";
        default "1000";
        description
          "BIER IPv6 receive rate limit.";
      }
    }
  }
}
