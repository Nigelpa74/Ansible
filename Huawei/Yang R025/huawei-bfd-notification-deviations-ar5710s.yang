/*
Copyright (C) 2025 Huawei Technologies Co., Ltd. All rights reserved.
*/
module huawei-bfd-notification-deviations-ar5710s {
  yang-version 1;
  namespace "urn:huawei:yang:huawei-bfd-notification-deviations-ar5710s";
  prefix bfd-notification-devs-ar5710s;

  import huawei-bfd-notification {
    prefix bfd-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd-notification module.";

  revision 2025-02-24 {
    description
      "Initial revision.";
    reference "Huawei private.";
  }

  deviation "/bfd-notification:bfd-pw-sess-down" {
    deviate not-supported;
  }
  deviation "/bfd-notification:bfd-pw-sess-up" {
    deviate not-supported;
  }
  deviation "/bfd-notification:bfd-sess-down-brief" {
    deviate not-supported;
  }
  deviation "/bfd-notification:bfd-sess-up-brief" {
    deviate not-supported;
  }
  deviation "/bfd-notification:bfd-v6-multi-hop-sess-down" {
    deviate not-supported;
  }
  deviation "/bfd-notification:bfd-v6-multi-hop-sess-up" {
    deviate not-supported;
  }
  deviation "/bfd-notification:bfd-v6-single-hop-sess-down" {
    deviate not-supported;
  }
  deviation "/bfd-notification:bfd-v6-single-hop-sess-up" {
    deviate not-supported;
  }
  deviation "/bfd-notification:bfd-bit-err-det-sess-reach-limit" {
    deviate not-supported;
  }
  deviation "/bfd-notification:bfd-sess-create-fail" {
    deviate not-supported;
  }
  deviation "/bfd-notification:bfd-sess-create-fail-resume" {
    deviate not-supported;
  }
  deviation "/bfd-notification:bfd-select-board-warn" {
    deviate not-supported;
  }
  deviation "/bfd-notification:bfd-select-board-warn-resume" {
    deviate not-supported;
  }
}
