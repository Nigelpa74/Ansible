/*
Copyright (C) 2022-2025 Huawei Technologies Co., Ltd. All rights reserved.
*/
module huawei-wlan-ap-group-profile {
  yang-version 1;
  namespace "urn:huawei:yang:huawei-wlan-ap-group-profile";
  prefix hw-wlan-agp;
  import huawei-extension {
    prefix ext;
  }
  import huawei-wlan-ap {
    prefix hw-wlan-ap;
  }
  organization
    "Huawei Technologies Co., Ltd.";
  contact
    "Huawei Industrial Base
     Bantian, Longgang
     Shenzhen 518129
     People's Republic of China
     Website: http://www.huawei.com
     Email: support@huawei.com";
  description
    "AP group service package.";
  revision 2025-06-12 {
    description
      "Add feature security switch.";
    reference
      "Huawei private.";
  }

  revision 2025-06-11 {
    description
      "Add feature security rpc by ap group.";
    reference
      "Huawei private.";
  }
  revision 2025-03-08 {
    description
      "Add cross-room-cov, altitude and asfn-id.";
    reference
      "Huawei private.";
  }
  revision 2024-09-10 {
    description
      "Update ap-group pattern.";
    reference
      "Huawei private.";
  }
  revision 2024-08-23 {
    description
      "Add leaf latitude, longitude.";
    reference
      "Huawei private.";
  }
  revision 2024-06-19 {
    description
      "Porfile name support Chinese.";
    reference
      "Huawei private.";
  }
  revision 2024-06-11 {
    description
      "Ap-group support UTF-8.";
    reference
      "Huawei private.";
  }
  revision 2024-05-16 {
    description
      "The default profile cannot be deleted.";
    reference
      "Huawei private.";
  }
  revision 2024-03-11 {
    description
      "Add profile name pattern.";
    reference
      "Huawei private.";
  }
  revision 2024-03-08 {
    description
      "Add profile name pattern.";
    reference
      "Huawei private.";
  }
  revision 2024-01-09 {
    description
      "Add site code.";
    reference
      "Huawei private.";
  }
  revision 2022-12-23 {
    description
      "Add AP IP-version.";
    reference
      "Huawei private.";
  }
  revision 2022-08-19 {
    description
      "Add location.";
    reference
      "Huawei private.";
  }
  revision 2022-07-15 {
    description
      "Add ap group name pattern.";
    reference
      "Huawei private.";
  }
  revision 2022-06-15 {
    description
      "Fix task name.";
    reference
      "Huawei private.";
  }
  revision 2022-04-11 {
    description
      "Initial revision.";
    reference
      "Huawei private.";
  }
  container wlan-ap-group-profile {
    description
      "AP group configuration.";
    container ap-group-profiles {
      description
        "List of AP group.";
      list ap-group-profile {
        ext:generated-by "system" {
          description
            "The default profile is generated by system.";
          ext:filter "ap-group-name='default'";
        }
        ext:operation-exclude "delete" {
          ext:filter "ap-group-name='default'";
          description
            "The default profile cannot be deleted.";
        }
        key "ap-group-name";
        description
          "Configure ap groups.";
        leaf ap-group-name {
          type string {
            length "1..35";
            pattern '[ \S]+';
            pattern '[^?/]+';
            pattern '([^ ]|[^ ].*[^ ])';
          }
          description
            "The ap group name.";
        }
        leaf location {
          type string {
            length "1..63";
          }
          description
            "AP location.";
        }
        leaf ap-ip-version {
          type enumeration {
            enum "ipv4" {
              value 0;
              description
              "Configure AP ip-version only IPv4.";
            }
            enum "ipv6" {
	          value 1;
	          description
	           "Configure AP ip-version only IPv6.";
	        }
	        enum "all" {
	          value 2;
	          description
	           "Configure AP ip-version all for IPv4 and IPv6.";
	        }
	      }
	      default "all";
	     description
	        "Configure AP ip-version.";		
	    }
	    leaf scene {	      
	      type enumeration {
            enum "cross-room" {
	          value 0;
	          description
			     "Cross room.";
	        }
            enum "cross-room-cov" {
              value 1;
              description
                "Cross room cov.";
            }
	      } 
          description  "Configure scene."; 		
	    }
        leaf site-code {
          type string {
            length "14";
          }
          description "Configure site-code.";
        }
	    leaf longitude {
	        type decimal64 {
	            fraction-digits 16;
	        }
            description "Configure longitude.";
	    }
	    leaf latitude {
	        type decimal64 {
	            fraction-digits 16;
	        }
            description "Configure latitude.";
	    }
        leaf altitude {
          type decimal64 {
            fraction-digits 10;
          }
          units "m";
          description
            "Configure altitude.";
        }
        leaf asfn-id {
          type uint32 {
            range "0..255";
          }
          description
            "The ASFN ID.";
        }
      }
    }
  }

  rpc enable-feature-security-by-apgroup {
    description
      "Switch feature security by ap group.";
    input  {
      leaf ap-group-name {
        type string {
          length "1..35";
          pattern '[ \S]+';
          pattern '[^?/]+';
          pattern '([^ ]|[^ ].*[^ ])';
        }
        description "The ap group name.";
      }
      leaf switch {
        type boolean;
        description "The switch of feature security.";
      }
    }
    output  {
      container result-info {
        description
          "The output.";
        leaf result {
          type string {
            length "1..300";
          }
          description
            "The output.";
        }
      }
    }
  }

  augment /hw-wlan-ap:wlan-ap/hw-wlan-ap:ap-instances/hw-wlan-ap:ap-instance {
    description
      "Specifies the group to which the AP belongs.";
    container binding-group {
      description
        "Configure ap-group to ap.";
      leaf binding-group {
        type leafref {
          path "/hw-wlan-agp:wlan-ap-group-profile/hw-wlan-agp:ap-group-profiles/hw-wlan-agp:ap-group-profile/hw-wlan-agp:ap-group-name";
        }
        default "default";
        description
          "Specifies the group to which the AP belongs.";
      }
    }
  }
  ext:task-name "pcm";
}
