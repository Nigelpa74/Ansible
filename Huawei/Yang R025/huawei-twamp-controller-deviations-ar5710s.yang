/*
Copyright (C) 2024 Huawei Technologies Co., Ltd. All rights reserved.
*/
module huawei-twamp-controller-deviations-ar5710s {
  namespace "urn:huawei:yang:huawei-twamp-controller-deviations-ar5710s";
  prefix twamp-controller-devs-ar5710s;

  import huawei-twamp-controller {
    prefix twamp-controller;
  }

  organization
    "Huawei Technologies Co., Ltd.";
  contact
    "Huawei Industrial Base
     Bantian, Longgang
     Shenzhen 518129
     People's Republic of China
     Website: http://www.huawei.com
     Email: support@huawei.com";
  description
    "This module defines deviation statements for huawei-twamp-controller module.";

  revision 2024-10-27 {
    description
      "Initial revision.";
    reference "Huawei private.";
  }

  deviation "/twamp-controller:twamp-controller" {
    deviate not-supported;
  }
  deviation "/twamp-controller:start-on-demand-test" {
    deviate not-supported;
  }
  deviation "/twamp-controller:stop-on-demand-test" {
    deviate not-supported;
  }
  deviation "/twamp-controller:reset-statistics" {
    deviate not-supported;
  }
}
