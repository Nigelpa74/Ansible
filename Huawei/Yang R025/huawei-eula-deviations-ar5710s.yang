/*
Copyright (C) 2023 Huawei Technologies Co., Ltd. All rights reserved.
*/
module huawei-eula-deviations-ar5710s {
  namespace "urn:huawei:yang:huawei-eula-deviations-ar5710s";
  prefix eula-devs-ar5710s;

  import huawei-eula {
    prefix eula;
  }

  organization
    "Huawei Technologies Co., Ltd.";
  contact
    "Huawei Industrial Base
     Bantian, Longgang
     Shenzhen 518129
     People's Republic of China
     Website: http://www.huawei.com
     Email: support@huawei.com";
  description
    "This module defines deviation statements for huawei-eula module.";

  revision 2023-10-27 {
    description
      "Initial revision.";
    reference "Huawei private.";
  }

  deviation "/eula:eula" {
    deviate not-supported;
  }
  deviation "/eula:accept-eula" {
    deviate not-supported;
  }
}
