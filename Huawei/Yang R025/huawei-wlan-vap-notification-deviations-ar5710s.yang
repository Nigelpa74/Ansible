/*
Copyright (C) 2019 Huawei Technologies Co., Ltd. All rights reserved.
*/
module huawei-wlan-vap-notification-deviations-ar5710s {
  yang-version 1;
  namespace "urn:huawei:yang:huawei-wlan-vap-notification-deviations-ar5710s";
  prefix hw-wvpntf-devs-ar5710s;

  import huawei-wlan-vap-notification {
    prefix hw-wvpntf;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-vap-notification module.";

  revision 2019-11-06 {
    description
      "Initial revision.";
    reference "Huawei private.";
  }

  deviation "/hw-wvpntf:vap-num-exceed" {
    deviate not-supported;
  }
}
