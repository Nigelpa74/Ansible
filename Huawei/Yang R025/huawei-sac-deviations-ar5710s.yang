/*
Copyright (C) 2019 Huawei Technologies Co., Ltd. All rights reserved.
*/
module huawei-sac-deviations-ar5710s {
  yang-version 1.1;
  namespace "urn:huawei:yang:huawei-sac-deviations-ar5710s";
  prefix huawei-sac-devs-ar5710s;

  import huawei-sac {
    prefix huawei-sac;
  }
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "This module defines deviation statements for huawei-sac module.";

  revision 2019-11-06 {
    description
      "Initial revision.";
    reference "Huawei private.";
  }

  deviation "/huawei-sac:sac/huawei-sac:authorization-enable" {
    deviate not-supported;
  }
  ext:deviation-ext "/huawei-sac:sac" {
    ext:deviate-ext "add" {
      ext:operation-exclude "create|delete";
    }
  }
}
