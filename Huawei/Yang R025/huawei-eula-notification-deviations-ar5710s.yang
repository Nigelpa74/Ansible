/*
Copyright (C) 2023 Huawei Technologies Co., Ltd. All rights reserved.
*/
module huawei-eula-notification-deviations-ar5710s {
  namespace "urn:huawei:yang:huawei-eula-notification-deviations-ar5710s";
  prefix eula-notification-devs-ar5710s;

  import huawei-eula-notification {
    prefix eula-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-eula-notification module.";

  revision 2023-10-27 {
    description
      "Initial revision.";
    reference "Huawei private.";
  }

  deviation "/eula-notification:eula-not-signed" {
    deviate not-supported;
  }
  deviation "/eula-notification:eula-not-signed-clear" {
    deviate not-supported;
  }
}
