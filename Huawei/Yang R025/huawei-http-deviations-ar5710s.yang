/*
Copyright (C) 2025 Huawei Technologies Co., Ltd. All rights reserved.
*/
module huawei-http-deviations-ar5710s {
  namespace "urn:huawei:yang:huawei-http-deviations-ar5710s";
  prefix http-devs-ar5710s;

  import huawei-http {
    prefix http;
  }
  import huawei-pub-type {
    prefix pub-type;
  }
  import huawei-acl {
    prefix acl;
  }

  organization
    "Huawei Technologies Co., Ltd.";
  contact
    "Huawei Industrial Base
     Bantian, Longgang
     Shenzhen 518129
     People's Republic of China
     Website: http://www.huawei.com
     Email: support@huawei.com";
  description
    "This module defines deviation statements for huawei-http module.";

  revision 2025-02-24 {
    description
      "Initial revision.";
    reference "Huawei private.";
  }

  deviation "/http:http/http:transfer-tasks" {
    deviate not-supported;
  }
  deviation "/http:httpc-transfer-file/http:output" {
    deviate not-supported;
  }
  deviation "/http:httpc-cancel-transfer-task" {
    deviate not-supported;
  }
  deviation "/http:http/http:servers/http:server/http:acl-name" {
    deviate delete {
      must "/acl:acl/acl:groups/acl:group[acl:identity=current()]/acl:type='basic' or /acl:acl/acl:groups/acl:group[acl:identity=current()]/acl:type='advance' or /acl:acl/acl:groups/acl:group[acl:number=number(current())]/acl:type='basic' or /acl:acl/acl:groups/acl:group[acl:number=number(current())]/acl:type='advance'";
    }
    deviate add {
      must "/acl:acl/acl:groups/acl:group[acl:identity=current()]/acl:type='basic' or /acl:acl/acl:groups/acl:group[acl:identity=current()]/acl:type='advance'";
    }
  }
  deviation "/http:httpc-transfer-file/http:input/http:password" {
    deviate replace {
      type pub-type:password-extend {
        length "1..127";
      }
    }
  }
}
