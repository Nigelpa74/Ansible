/*
Copyright (C) 2019-2024 Huawei Technologies Co., Ltd. All rights reserved.
*/
module huawei-file-operation {
  namespace "urn:huawei:yang:huawei-file-operation";
  prefix file-operation;

  import ietf-yang-types {
    prefix yang;
  }
  import huawei-pub-type {
    prefix pub-type;
  }
  import huawei-extension {
    prefix ext;
  } 

  organization
    "Huawei Technologies Co., Ltd.";
  contact
    "Huawei Industrial Base
     Bantian, Longgang
     Shenzhen 518129
     People's Republic of China
     Website: http://www.huawei.com
     Email: support@huawei.com";
  description
    "Indicate file system management.";
  revision 2024-06-03 {
    description
      "Add container file-digest-results for file digests.";
    reference
      "Huawei private.";
  }
  revision 2023-02-03 {
    description
      "Add leaf node of password for zip-file and unzip-file.";
    reference
      "Huawei private.";
  }
  revision 2022-08-18 {
    description
      "Modify node description of zip-file and zip-file's leaf node src-file-name.";
    reference
      "Huawei private.";
  }
  revision 2021-09-17 {
    description
      "Modify leafref path of the leaf file-name of rpc.";
    reference
      "Huawei private.";
  }
  revision 2021-06-17 {
    description
      "Modify leafref path of the leaf node dir-name.";
    reference
      "Huawei private.";
  }
  revision 2020-08-12 {
    description
      "Modify data type of the node size from int32 to uint32.";
    reference
      "Huawei private.";
  }
  revision 2020-04-02 {
    description
      "YANG check.";
    reference
      "Huawei private.";
  }
  revision 2020-02-13 {
    description
      "Add leaf node of copy-file and delete-file.";
    reference
      "Huawei private.";
  }
  revision 2019-12-20 {
    description
      "Modify node description.";
    reference
      "Huawei private.";
  }
  revision 2019-12-09 {
    description
      "Initial revision.";
    reference
      "Huawei private.";
  }

  ext:task-name "rpm";
  typedef delete-type {
    type enumeration {
      enum "unreserved" {
        value 0;
        description
          "Delete file permanently. The deleted file cannot be restored.";
      }
    }
    description
      "Specify the action of deleting file.";
  }
  typedef overwrite-type {
    type enumeration {
      enum "overwrite" {
        value 0;
        description
          "Overwrite the file with same name as the destination file while compressing or decompressing.";
      }
      enum "not-overwrite" {
        value 1;
      description
          "Not to overwrite the file with same name as the destination file while compressing or decompressing.";
      }
    }
    description
      "The overwrite strategy when there exists a file with same name as the destination file, should be overwrite or not-overwrite.";
  }
  typedef reset-recycle-type {
    type enumeration {
      enum "all" {
        value 0;
        description
          "Delete all files in the recycle bin.";
      }
    }
    description
      "Specify the action type of reseting the recycle bin.";
  }
  typedef digest-algorithm-type {
    type enumeration {
      enum "sha256" {
        value 1;
        description
          "SHA256 hash algorithm.";
      }
      enum "md5" {
        value 2;
        description
          "MD5 hash algorithm.";
      }
    }
    description
      "Specify the hash algorithm.";
  }
  typedef operation-status {
    type enumeration {
      enum "operating" {
        value 0;
        description
          "The current status of comparing digest values.";
      }
      enum "succeed" {
        value 1;
        description
          "The current status of comparing digest values.";
      }
      enum "failed" {
        value 2;
        description
          "The current status of comparing digest values.";
      }
    }
    description
      "Specify file-digest calculating operation status.";
  }
  typedef digest-compared-result-type {
    type enumeration {
      enum "match" {
        value 0;
        description
          "Match.";
      }
      enum "not-match" {
        value 1;
        description
          "Not match.";
      }
      enum "not-compared" {
        value 2;
        description
          "Not compared.";
      }
    }
    description
      "Specify the result of comparing hash values.";
  }
  container file-operation {
    config false;
    description
      "Indicate file system management.";
    container dirs {
      description
        "List of operational data of file information.";
      list dir {
        key "file-name dir-name";
        description
          "Operational data of file information.";
        leaf file-name {
          type string {
            length "1..255";
          }
          description
            "Name of a folder or file.";
        }
        leaf dir-name {
          type string {
            length "1..255";
          }
          description
            "Name of the current folder. You can also specify a subfolder path to query the files in the subfolder.";
        }
        leaf attribute {
          type string {
            length "1..16";
          }
          description
            "Attributes of a folder or file.";
        }
        leaf modify-time {
          type yang:date-and-time;
          description
            "Last modified time of a folder or file.";
        }
        leaf size {
          type uint32;
          units Byte;
          description
            "Size of a folder or file. Integer type and the size of a folder is expressed as 4096.";
        }
      }
    }

    container disk-usages {
      description
        "List of operational data of disk space information.";
      list disk-usage {
        key "name";
        description
          "Operational data of disk space information.";
        leaf name {
          type string {
            length "1..64";
          }
          description
            "Name of a file system partition.";
        }
        leaf path {
          type string {
            length "1..64";
          }
          description
            "Directory of a file system partition.";
        }
        leaf total-size {
          type string {
            length "1..32";
          }
          units kB;
          description
            "Total size of a file system partition.";
        }
        leaf free-size {
          type string {
            length "1..32";
          }
          units kB;
          description
            "Size of the free space in a file system partition.";
        }
        leaf usage {
          type pub-type:percent;
          description
            "Usage of a file system partition.";
        }
      }
    }

    container file-digest-results {
      config false;
      description
        "List of file digest results.";
      list file-digest-result {
        key "file-name";
        description
          "Operational data of file information.";
        leaf file-name {
          type string {
            length "1..255";
          }
          description
            "File name.";
        }
        leaf operation-result {
          type operation-status;
          description
            "The operation result of comparing digest values.";
        }
        leaf digest-value {
          when "../operation-result = 'succeed'";
          type string {
            length "1..65";
          }
          description
            "Digest value.";
        }
        leaf compared-result {
          when "../operation-result = 'succeed'";
          type digest-compared-result-type;
          description
            "The result of comparing digest values.";
        }
        leaf failed-reason {
        when "../operation-result = 'failed'";
          type string {
              length "1..128";
          }
          description
              "The failed reason of comparing digest values.";
        }
      }
    }
  }

  rpc reset-recycle-bin {
    description
      "Delete all files in the recycle bin.";
    input {
      leaf reset-type {
        type reset-recycle-type;
        description
          "Delete all files in the recycle bin.";
      }
    }
  }
  rpc copy-file {
    description
      "Copy a file. A folder, however, cannot be copied.";
    ext:node-ref "/file-operation/dirs/dir";  
    input {
      leaf src-file-name {
        type string {
          length "1..255";
        }
        mandatory true;
        description
          "Specify a source file name that can be listed in a full directory or a relative directory.";
      }
      leaf des-file-name {
        type string {
          length "1..255";
        }
        mandatory true;
        description
          "Specify a destination file name that can be listed in a full path or a relative path.";
      }
      leaf all {
        type boolean;
        description
          "Copy a file to both of the main board and slave board. A folder, however, cannot be copied.";
      }
    }
  }

  rpc delete-file {
    description
      "Delete file permanently. A folder, however, cannot be deleted.";
    ext:node-ref "/file-operation/dirs/dir";
    input {
      leaf file-name {
        type string {
          length "1..255";
        }
        mandatory true;
        description
          "Specify a file name that can be listed in a full directory or a relative directory.";
      }
      leaf delete-type {
        type delete-type;
        mandatory true;
        description
          "Specify the action of deleting file.";
      }
      leaf all {
        type boolean;
        description
          "Delete a file of the main board and slave board permanently. A folder, however, cannot be deleted.";
      }
    }
  }

  rpc zip-file {
    description
      "Compress a file or folder.";
    ext:node-ref "/file-operation/dirs/dir";
    input {
      leaf src-file-name {
        type string {
          length "1..255";
        }
        mandatory true;
        description
          "Specify a source file or folder name that can be listed in a full directory or a relative directory.";
      }
      leaf des-file-name {
        type string {
          length "1..255";
        }
        mandatory true;
        description
          "Specify a destination file name that can be listed in a full directory or a relative directory.";
      }
      leaf overwrite-type {
        type overwrite-type;
        default "not-overwrite";
        description
          "Specify the overwrite strategy when there exists a file with same name as the destination file, should be overwrite or not-overwrite.";
      }
      leaf password {
        type pub-type:password-extend {
          length "8..20";
        }
        description
          "Password used for encrypt-compressing a file. The password consists of letters, digits, and special characters.";
      }
    }
  }

  rpc unzip-file {
    description
      "Decompress a file. A folder, however, cannot be decompressed.";
    ext:node-ref "/file-operation/dirs/dir";
    input {
      leaf src-file-name {
        type string {
          length "1..255";
        }
        mandatory true;
        description
          "Specify a source file name that can be listed in a full directory or a relative directory.";
      }
      leaf des-file-name {
        type string {
          length "1..255";
        }
        mandatory true;
        description
          "Specify a destination file name that can be listed in a full path or a relative path.";
      }
      leaf overwrite-type {
        type overwrite-type;
        default "not-overwrite";
        description
          "Specify the overwrite strategy when there exists a file with same name as the destination file, should be overwrite or not-overwrite.";
      }
      leaf password {
        type pub-type:password-extend {
          length "8..20";
        }
        description
          "Password used for decompressing an encrypt-decompressed file. The password consists of letters, digits, and special characters.";
      }
    }
  }

  rpc move-file {
    description
      "Move a file. A folder, however, cannot be moved.";
    ext:node-ref "/file-operation/dirs/dir";
    input {
      leaf src-file-name {
        type string {
          length "1..255";
        }
        mandatory true;
        description
          "Specify a source file name that can be listed in a full directory or a relative directory.";
      }
      leaf des-file-name {
        type string {
          length "1..255";
        }
        mandatory true;
        description
          "Specify a destination file name that can be listed in a full directory or a relative directory.";
      }
    }
  }

  rpc rename {
    description
      "Rename a file or folder.";
    ext:node-ref "/file-operation/dirs/dir";
    input {
      leaf src-name {
        type string {
          length "1..255";
        }
        mandatory true;
        description
          "Specify a source file or folder name that can be listed in a full directory or a relative directory.";
      }
      leaf des-name {
        type string {
          length "1..255";
        }
        mandatory true;
        description
          "Specify a destination file or folder name that can be listed in a full directory or a relative directory.";
      }
    }
  }

  rpc make-dir {
    description
      "Create a folder.";
    ext:node-ref "/file-operation/dirs/dir";
    input {
      leaf dir-name {
        type string {
            length "1..255";
          }
        mandatory true;
        description
          "Specify a folder that will be created.";
      }
    }
  }

  rpc remove-dir {
    description
      "Remove a folder.";
    ext:node-ref "/file-operation/dirs/dir";
    input {
      leaf dir-name {
        type leafref {
          path "/file-operation/dirs/dir/file-name";
        }
        mandatory true;
        description
          "Specify a folder that will be removed.";
      }
    }
  }
  rpc calculate-file-digest {
    description
      "Calculate the hash value of a file.";
    input {
      leaf file-name {
        type string {
          length "1..255";
        }
        mandatory true;
        description
          "Specify a file name that can be listed in a full directory or a relative directory.";
      }
      leaf digest-algorithm {
        type digest-algorithm-type;
        mandatory true;
        description
          "Specify the digest algorithm.";
      }
    }
  }
  rpc compare-file-digest {
    description
      "Calculate the hash value of a file and compare it with the input digest value.";
    input {
      leaf file-name {
        type string {
          length "1..255";
      }
      mandatory true;
      description
        "Specify a file name that can be listed in a full directory or a relative directory.";
      }
      leaf digest-algorithm {
        type digest-algorithm-type;
        mandatory true;
        description
          "Specify the digest algorithm.";
      }
      leaf digest-value {
        type string {
          length "1..65";
        }
        description
          "Specify the digest value to be compared.";
      }
    }
  }
}
