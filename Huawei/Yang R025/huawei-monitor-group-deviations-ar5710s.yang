/*
Copyright (C) 2025 Huawei Technologies Co., Ltd. All rights reserved.
*/
module huawei-monitor-group-deviations-ar5710s {
  yang-version 1;
  namespace "urn:huawei:yang:huawei-monitor-group-deviations-ar5710s";
  prefix monitor-group-devs-ar5710s;

  import huawei-monitor-group {
    prefix monitor-group;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-monitor-group module.";

  revision 2025-02-24 {
    description
      "Initial revision.";
    reference "Huawei private.";
  }

  deviation "/monitor-group:monitor-group" {
    deviate not-supported;
  }
  deviation "/ifm:ifm/ifm:interfaces/ifm:interface/monitor-group:track-monitor-group" {
    deviate not-supported;
  }
}
