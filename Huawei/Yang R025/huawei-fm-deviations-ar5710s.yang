/*
Copyright (C) 2025 Huawei Technologies Co., Ltd. All rights reserved.
*/
module huawei-fm-deviations-ar5710s {
  namespace "urn:huawei:yang:huawei-fm-deviations-ar5710s";
  prefix fm-devs-ar5710s;

  import huawei-fm {
    prefix fm;
  }
  import huawei-snmp {
    prefix snmp;
  }

  organization
    "Huawei Technologies Co., Ltd.";
  contact
    "Huawei Industrial Base
     Bantian, Longgang
     Shenzhen 518129
     People's Republic of China
     Website: http://www.huawei.com
     Email: support@huawei.com";
  description
    "This module defines deviation statements for huawei-fm module.";

  revision 2025-02-24 {
    description
      "Initial revision.";
    reference "Huawei private.";
  }

  deviation "/fm:fm/fm:global/fm:inverse-mode" {
    deviate not-supported;
  }
  deviation "/fm:fm/fm:inverse-ports" {
    deviate not-supported;
  }
  deviation "/fm:fm/fm:active-alarms/fm:active-alarm/fm:vsname" {
    deviate not-supported;
  }
  deviation "/fm:fm/fm:history-alarms/fm:history-alarm/fm:vsname" {
    deviate not-supported;
  }
  deviation "/snmp:snmp/snmp:target-hosts/snmp:target-host/fm:host-alarm" {
    deviate not-supported;
  }
}
