/*
Copyright (C) 2019-2025 Huawei Technologies Co., Ltd. All rights reserved.
*/
module huawei-qos {
  namespace "urn:huawei:yang:huawei-qos";
  prefix qos;
  import huawei-pub-type {
    prefix pub-type;
  }
  import huawei-extension {
    prefix ext;
  }
  import huawei-network-instance {
    prefix ni;
  }
  import huawei-ifm {
    prefix ifm;
  }
  import huawei-acl {
    prefix acl;
  }
  import huawei-bfd {
    prefix bfd;
  }
  import ietf-yang-types {
    prefix yang;
  }
  import ietf-inet-types {
    prefix inet;
  }
  import huawei-time-range {
    prefix timerange;
  }
  import huawei-license {
    prefix lcs;
  }
  import huawei-vlan {
    prefix vlan;
  }
  import huawei-nqa {
    prefix nqa;
  }
  import huawei-ethernet {
    prefix ethernet;
  }
  include huawei-qos-type;
  
  organization
    "Huawei Technologies Co., Ltd.";
  contact
    "Huawei Industrial Base
     Bantian, Longgang
     Shenzhen 518129
     People's Republic of China
     Website: http://www.huawei.com
     Email: support@huawei.com";
  description
    "Quality of service.";
  revision 2025-09-15 {
    description
      "1.Add container micro-burst-queue-monitors.
       2.Add container micro-burst-rate-monitors.
       3.Add container interface-chip-infos.
       4.Add container trust-remote-inners.
       5.Modify the wrong word.
       6.Add remark type.
       7.Add container resource-usages.
       8.Add container inner-mark-statistics.
       9.Add new default choice case for user-queue.
       10.Add container pfc-statistics-infos.
       11.Add rpc reset-pfc-statistics-infos.
       12.Modify profile-car.
       13.Add leaf for interface-monitoring-result.";
    reference
      "Huawei private.";
  }
  revision 2025-06-26 {
    description
      "1.Add multicast-burst-modes container and add multicast-burst-mode container.
       2.Modify must condition for remark-action-colors.
       3.Add when condition for qos-lr.
       4.Modify must condition for qos-lr-outbound/cir-unit.
       5.Add must condition for qos.
       6.Add must condition for queue-buffer-monitor.
       7.Add must condition for remark-action-colors.";
    reference
      "Huawei private.";
  }
  revision 2025-04-29 {
    description
      "Modify the length of interface-name.";
    reference
      "Huawei private.";
  }
  revision 2025-04-28 {
    description
      "Modify the length of interface-name.";
    reference
      "Huawei private.";
  }
  revision 2025-03-28 {
    description
      "Modify the length of interface-name.";
    reference
      "Huawei private.";
  }
  revision 2025-03-24 {
    description
      "Modify group-name leaf pattern.";
    reference
      "Huawei private.";
  }
  revision 2024-12-16 {
    description
      "Modify traffic-behavior-queue packet-number and add slot-id pattern.";
    reference
      "Huawei private.";
  }
  revision 2024-09-11 {
    description
      "Add container map-to-interface.";
    reference
      "Huawei private.";
  }
  revision 2024-08-31 {
    description
      "Add type pattern.";
    reference
      "Huawei private.";
  }  
  revision 2024-08-24 {
    description
      "Add color-remark-8021p case for car parameters.";
    reference
      "Huawei private.";
  }
  revision 2024-08-15 {
    description
      "Move container auto-buffer.";
    reference
      "Huawei private.";
  }
  revision 2024-08-01 {
    description
      "Add the dynamic default to leaf priority.";
    reference
      "Huawei private.";
  }
  revision 2024-07-30 {
    description
      "Add the must condition to container rule ce VLANs.";
    reference
      "Huawei private.";
  }
  revision 2024-07-15 {
    description
      "1. Add New container auto-buffer.
       2. Add New leaf map-to-interface.
       3. Add container intf-ing-buf-usage-statisticss.";
    reference
      "Huawei private.";
  }
  revision 2024-05-31 {
    description
      "Modify value of qos queue buffer.";
    reference
      "Huawei private.";
  }
  revision 2024-05-27 {
    description
      "Modify used-percentage unit type.";
    reference
      "Huawei private.";
  }
  revision 2024-05-13 {
    description
      "Add new container traffic-policy.";
    reference
      "Huawei private.";
  }
  revision 2024-05-11 {
    description
      "Modify must condition for encapsulation-overhead.";
    reference
      "Huawei private.";
  }
  revision 2024-04-12 {
    description
      "Add new enum policy-apply-state.";
    reference
      "Huawei private.";
  }
  revision 2024-02-28 {
    description
      "Add weight-fixed of drr queue.";
    reference
      "Huawei private.";
  }
  revision 2024-02-21 {
    description
      "Add policy name and classifier name.";
    reference
      "Huawei private.";
  }
  revision 2024-02-20 {
    description
      "Add new container acl-core-resource-usages and acl-core-bank-resource-usages.";
    reference
      "Huawei private.";
  }
  revision 2024-01-29 {
    description
      "Add new enum blind.";
    reference
      "Huawei private.";
  }
  revision 2023-12-14 {
    description
      "Add new enum inherit-inner-8021p.";
    reference
      "Huawei private.";
  }
  revision 2023-11-07 {
    description
      "Add queue ecn.";
    reference
      "Huawei private.";
  }
  revision 2023-10-12 {
    description
      "Modify the max length of qos-profile-name to 64.";
    reference
      "Huawei private.";
  }
  revision 2023-09-12 {
    description
      "Add default for ecn.";
    reference
      "Huawei private.";
  }
  revision 2023-08-21 {
    description
      "Modify the length of qos-profile-name.";
    reference
      "Huawei private.";
  }
  revision 2023-08-10 {
    description
      "Modify filter conditions of generated-by and operation-exclude for behavior-aggregation and per-hop-behavior.";
    reference
      "Huawei private.";
  }
  revision 2023-07-29 {
    description
      "1.Add new node bas-load-balances.
       2.Add new leaf for default-user-group-queues.";
    reference
      "Huawei private.";
  }
  revision 2023-07-04 {
    description
      "Acl-bank-resource-usage add node and key.";
    reference
      "Huawei private.";
  }
  revision 2023-06-16 {
    description
      "Modify tlm para slot type.";
    reference
      "Huawei private.";
  }
  revision 2023-06-12 {
    description
      "Modify the parameter value range.";
    reference
      "Huawei private.";
  }
  revision 2023-03-31 {
    description
      "Change default pir of percent-reference to dynamic default.";
    reference
      "Huawei private.";
  }
  revision 2023-03-16 {
    description
      "Add network-slice node.";
    reference
      "Huawei private.";
  }
  revision 2022-12-09 {
    description
      "Delete unused error-app-tag undefined code, and delete must condition for traffic-behavior-user-queues pbs.";
    reference
      "Huawei private.";
  }
  revision 2022-11-15 {
    description
      "Add mandatory for flow queue and user queue.";
    reference
      "Huawei private.";
  }
  revision 2022-11-14 {
    description
      "Add must condition for qos-profile car.";
    reference
      "Huawei private.";
  }
  revision 2022-11-11 {
    description
      "Delete must condition for flow-wred.";
    reference
      "Huawei private.";
  }
  revision 2022-11-03 {
    description
      "Add must condition for config-mode.";
    reference
      "Huawei private.";
  }
  revision 2022-10-28 {
    description
      "Add must condition for cbs-unit, pir-unit and pbs-unit.";
    reference
      "Huawei private.";
  }
  revision 2022-10-10 {
    description
      "1. Add new node schedule-profiles in queue-scheduler-template.
       2. Add new node schedule-profile for interface.";
    reference
      "Huawei private.";
  }
  revision 2022-09-27 {
    description
      "Port-wred queue-depth support time mode.";
    reference
      "Huawei private.";
  }
  revision 2022-09-20 {
    description
      "Add default for qos lr outbound.";
    reference
      "Huawei private.";
  }
  revision 2022-09-16 {
    description
      "Add new node traffic-policy-protocol-protects in global-config.";
    reference
      "Huawei private.";
  }
  revision 2022-08-30 {
    description
      "Add diffserv-mode in global-config.";
    reference
      "Huawei private.";
  }
  revision 2022-08-19 {
    description
      "Add new son container for traffic-policy.";
    reference
      "Huawei private.";
  }
  revision 2022-07-26 {
    description
      "1. Modify must condition for profile-apply and when condition for queue-4cos-mapping-name.
       2. Add must condition for trust.
       3. Modify must condition for yellow-action.";
    reference
      "Huawei private.";
  }
  revision 2022-07-25 {
    description
      "1. Delete node dei-enables.
       2. Delete the default value of traffic-inloop-enable and queue-capability-enable.";
    reference
      "Huawei private.";
  }
  revision 2022-07-19 {
    description
      "Add must condition for netstream-sampler-action.";
    reference
      "Huawei private.";
  }
  revision 2022-07-08 {
    description
      "Add default for wred mode.";
    reference
      "Huawei private.";
  }
  revision 2022-07-07 {
    description
      "Modify queue-depth value.";
    reference
      "Huawei private.";
  }
  revision 2022-06-30 {
    description
      "Modify the value range of cir-pct and pir-pct.";
    reference
      "Huawei private.";
  }
  revision 2022-06-25 {
    description
      "Add new son container for traffic-policy.";
    reference
      "Huawei private.";
  }
  revision 2022-06-18 {
    description
      "Modify the value range of cir-pct and pir-pct.";
    reference
      "Huawei private.";
  }
  revision 2022-06-05 {
    description
      "Pbs/cbs and flow-wred queue-depth support time mode.";
    reference
      "Huawei private.";
  }
  revision 2022-05-28 {
    description
      "Add must for linkage-bandwidth.";
    reference
      "Huawei private.";
  }
  revision 2022-05-20 {
    description
      "Add private syntax.";
    reference
      "Huawei private.";
  }
  revision 2022-05-09 {
    description
      "Add packets-value of static.";
    reference
      "Huawei private.";
  }
  revision 2022-05-05 {
    description
      "Add percent car source.";
    reference
      "Huawei private.";
  }	
  revision 2022-04-20 {
    description
      "Add choice-case for car-actions.";
    reference
      "Huawei private.";
  }
  revision 2022-04-16 {
    description
      "Add schedule-tree-mode.";
    reference
      "Huawei private.";
  }
  revision 2022-04-01 {
    description
      "Add dynamic-default for flow-queue/normal-mode-queues.";
    reference
      "Huawei private.";
  }
  revision 2022-03-23 {
    description
      "Add port-phb-trusts default record description.";
    reference
      "Huawei private.";
  }
  revision 2022-03-20 {
    description
      "Update the tunnel-encap-overhead and the desciption of rate-limiting-overhead.";
    reference
      "Huawei private.";
  }
  revision 2022-03-15 {
    description
      "1. Add wreds default template description.
       2. Add port-phb-trusts and trust-upstream node dynamic-default.
       3. Update the slot of burst-modes descript.
       4. Add rate-limiting-overhead and tunnel-encap-overhead.";
    reference
      "Huawei private.";
  }
  revision 2022-03-10 {
    description
      "Add must for traffic-policy-apply and trust-remote.";
    reference
      "Huawei private.";
  }
  revision 2022-03-04 {
    description
      "Update qos-type description of qos-service-class.";
    reference
      "Huawei private.";
  }
  revision 2022-03-02 {
    description
      "Add mandatory in burst-modes.";
    reference
      "Huawei private.";
  }
  revision 2022-03-01 {
    description
      "Add must in pir-percent and modify must in queue-buffer-monitor-threds.";
    reference
      "Huawei private.";
  }
  revision 2022-02-24 {
    description
      "Add queue-discard-alarms in global-config.";
    reference
      "Huawei private.";
  }
  revision 2022-02-17 {
    description
      "Modify must in traffic-policy-apply.";
    reference
      "Huawei private.";
  }
  revision 2022-01-28 {
    description
      "Add is-decapsulate.";
    reference
      "Huawei private.";
  }
  revision 2022-01-18 {
    description
      "Add reset flow-car.";
    reference
      "Huawei private.";
  }
  revision 2022-01-17 {
    description
      "Add policy ID and classifier ID.";
    reference
      "Huawei private.";
  }
  revision 2022-01-13 {
    description
      "Add mode-flexe-queue-statisticss.";
    reference
      "Huawei private.";
  }
  revision 2022-01-11 {
    description
      "Modify trust-8021p-dscp default value.";
    reference
      "Huawei private.";
  }
  revision 2021-12-25 {
    description
      "Add must for interface qos car cir-percent.";
    reference
      "Huawei private.";
  }
  revision 2021-12-23 {
    description
      "Add integration-template and modify slot-id type.";
    reference
      "Huawei private.";
  }
  revision 2021-12-04 {
    description
      "Modify rule-mac-and-masks must condition.";
    reference
      "Huawei private.";
  }	
  revision 2020-09-10 {
    description
      "Add user-queue-resource-8cos-enhances.";
    reference
      "Huawei private.";
  }
  revision 2020-09-08 {
    description
      "Add qppb-local-id, gtp teid, policy-apply-order, tunnel qos-local-id.";
    reference
      "Huawei private.";
  }	
  revision 2020-08-27 {
    description
      "Add traffic-behavior-queues and traffic-behavior-user-queues.";
    reference
      "Huawei private.";
  }	
  revision 2020-08-11 {
    description
      "Add interface-simple-car-statisticss and traffic-policys nodes.";
    reference
      "Huawei private.";
  }
  revision 2020-08-10 {
    description
      "Add new nodes.";
    reference
      "Huawei private.";
  }
  revision 2020-08-06 {
    description
      "Delete container port-pfc-statisticss and queue-hdrm-statisticss.";
    reference
      "Huawei private.";
  }
  revision 2020-07-06 {
    description
      "Modify container qos-lr-outbound rule-packet-types car-template and vlan-classifier-statisticss.";
    reference
      "Huawei private.";
  }
  revision 2020-06-18 {
    description
      "Modify container tcp-flag and rule-rocev2.";
    reference
      "Huawei private.";
  }
  revision 2020-06-16 {
    description
      "Modify container rule-gre-inner and add key node to queue-buffer.";
    reference
      "Huawei private.";
  }
  revision 2020-06-11 {
    description
      "Modify descriptions and add units.";
    reference
      "Huawei private.";
  }
  revision 2020-06-01 {
    description
      "Add new nodes.";
    reference
      "Huawei private.";
  }
  revision 2020-05-27 {
    description
      "Add new nodes.";
    reference
      "Huawei private.";
  }
  revision 2020-04-10 {
    description
      "Add new nodes.";
    reference
      "Huawei private.";
  }
  revision 2020-04-01 {
    description
      "Add new nodes.";
    reference
      "Huawei private.";
  }
  revision 2020-03-20 {
    description
      "Add new nodes.";
    reference
      "Huawei private.";
  }
  revision 2020-03-11 {
    description
      "Add new nodes.";
    reference
      "Huawei private.";
  }
  revision 2020-02-03 {
    description
      "Add new nodes.";
    reference
      "Huawei private.";
  }
  revision 2020-01-18 {
    description
      "Add new nodes.";
    reference
      "Huawei private.";
  }
  revision 2019-12-02 {
    description
      "Add new nodes.";
    reference
      "Huawei private.";
  }
  revision 2019-11-04 {
    description
      "Add new nodes.";
    reference
      "Huawei private.";
  }
  revision 2019-10-18 {
    description
      "Initial revision.";
    reference
      "Huawei private.";
  }
  grouping track-nqa-pub {
    description
      "Track nqa pub.";
    container track-nqa {
      description
        "Track nqa.";
      leaf admin-name {
        type leafref {
          path "/nqa:nqa/nqa:instances/nqa:instance/nqa:admin-name";
        }
        mandatory true;
        description
          "NQA test admin name.";
      }
      leaf test-name {
        type leafref {
          path "/nqa:nqa/nqa:instances/nqa:instance/nqa:test-name";
        }
        mandatory true;
        description
          "Test name.";
      }
      leaf probe-fail-times {
        type uint8 {
          range "1..15";
        }
        default "1";
        description
          "NQA probe fail times.";
      }
    }
  }
  grouping low-precedence {
    description
      "Low-precedence.";
    container low-precedence {
      description
        "Low-precedence.";
      leaf low-pre {
        type empty;
        description
          "Low precedence enable control.";
      }
      leaf source-vpn-inst {
        type leafref {
          path "/ni:network-instance/ni:instances/ni:instance/ni:name";
        }
        description
          "Source vpn instance name.";
      }
    }
  }
  grouping policy-statistics-type {
    description
      "Traffic policy statistics information.";
    leaf match-packets {
      type uint64;
      units "packet";
      description
        "Number of matched packets.";
    }
    leaf match-bytes {
      type uint64;
      units "Byte";
      description
        "Number of matched bytes.";
    }
    leaf match-packet-rate {
      type uint64;
      units "pps";
      description
        "Rate of matched packets.";
    }
    leaf match-byte-rate {
      type uint64;
      units "Byte/s";
      description
        "Rate of matched bytes.";
    }
    leaf miss-packets {
      type uint64;
      units "packet";
      description
        "Number of unmatched packets.";
    }
    leaf miss-bytes {
      type uint64;
      units "Byte";
      description
        "Number of unmatched bytes.";
    }
    leaf match-pass-packets {
      type uint64;
      units "packet";
      description
        "Number of matched and passed packets.";
    }
    leaf match-pass-bytes {
      type uint64;
      units "Byte";
      description
        "Number of matched and passed bytes.";
    }
    leaf match-drop-packets {
      type uint64;
      units "packet";
      description
        "Number of matched but discarded packets.";
    }
    leaf match-drop-bytes {
      type uint64;
      units "Byte";
      description
        "Number of matched but discarded bytes.";
    }
    leaf miss-packet-rate {
      type uint64;
      units "pps";
      description
        "Rate of the packets that do not match the policy.";
    }
    leaf miss-byte-rate {
      type uint64;
      units "Byte/s";
      description
        "Rate of the bytes that do not match the policy.";
    }
    leaf match-pass-packet-rate {
      type uint64;
      units "pps";
      description
        "Rate of the packets that match the policy and passed.";
    }
    leaf match-pass-byte-rate {
      type uint64;
      units "Byte/s";
      description
        "Rate of the bytes that match the policy and passed.";
    }
    leaf match-drop-packet-rate {
      type uint64;
      units "pps";
      description
        "Rate of the packets that match the policy but are discarded.";
    }
    leaf match-drop-byte-rate {
      type uint64;
      units "Byte/s";
      description
        "Rate of the bytes that match the policy but are discarded.";
    }
    leaf urpf-packets {
      type uint64;
      units "packet";
      description
        "Number of packets discarded by URPF.";
    }
    leaf urpf-bytes {
      type uint64;
      units "Byte";
      description
        "Number of bytes discarded by URPF.";
    }
    leaf urpf-packet-rate {
      type uint64;
      units "pps";
      description
        "Rate of packets discarded by URPF.";
    }
    leaf urpf-byte-rate {
      type uint64;
      units "Byte/s";
      description
        "Rate of bytes discarded by URPF.";
    }
    leaf car-packets {
      type uint64;
      units "packet";
      description
        "Number of packets processed by CAR.";
    }
    leaf car-bytes {
      type uint64;
      units "Byte";
      description
        "Number of bytes processed by CAR.";
    }
    leaf car-packet-rate {
      type uint64;
      units "pps";
      description
        "Rate of packets processed by CAR.";
    }
    leaf car-byte-rate {
      type uint64;
      units "Byte/s";
      description
        "Rate of bytes processed by CAR.";
    }
    leaf filter-packets {
      type uint64;
      units "packet";
      description
        "Number of filtered packets.";
    }
    leaf filter-bytes {
      type uint64;
      units "Byte";
      description
        "Number of filtered bytes.";
    }
    leaf filter-packet-rate {
      type uint64;
      units "pps";
      description
        "Rate of filtered packets.";
    }
    leaf filter-byte-rate {
      type uint64;
      units "Byte/s";
      description
        "Rate of filtered bytes.";
    }
  }
  grouping multi-policy-statistics-type {
    description
      "Multiple traffic policy statistics information.";
    leaf match-packets {
      type uint64;
      units "packet";
      description
        "Number of matched packets.";
    }
    leaf match-bytes {
      type uint64;
      units "Byte";
      description
        "Number of matched bytes.";
    }
    leaf match-packet-rate {
      type uint64;
      units "pps";
      description
        "Rate of matched packets.";
    }
    leaf match-byte-rate {
      type uint64;
      units "Byte/s";
      description
        "Rate of matched bytes.";
    }
    leaf miss-packets {
      type uint64;
      units "packet";
      description
        "Number of unmatched packets.";
    }
    leaf miss-bytes {
      type uint64;
      units "Byte";
      description
        "Number of unmatched bytes.";
    }
    leaf match-pass-packets {
      type uint64;
      units "packet";
      description
        "Number of matched and passed packets.";
    }
    leaf match-pass-bytes {
      type uint64;
      units "Byte";
      description
        "Number of matched and passed bytes.";
    }
    leaf match-drop-packets {
      type uint64;
      units "packet";
      description
        "Number of matched but discarded packets.";
    }
    leaf match-drop-bytes {
      type uint64;
      units "Byte";
      description
        "Number of matched but discarded bytes.";
    }
    leaf miss-packet-rate {
      type uint64;
      units "pps";
      description
        "Rate of the packets that do not match the policy.";
    }
    leaf miss-byte-rate {
      type uint64;
      units "Byte/s";
      description
        "Rate of the bytes that do not match the policy.";
    }
    leaf match-pass-packet-rate {
      type uint64;
      units "pps";
      description
        "Rate of the packets that match the policy and passed.";
    }
    leaf match-pass-byte-rate {
      type uint64;
      units "Byte/s";
      description
        "Rate of the bytes that match the policy and passed.";
    }
    leaf match-drop-packet-rate {
      type uint64;
      units "pps";
      description
        "Rate of the packets that match the policy but are discarded.";
    }
    leaf match-drop-byte-rate {
      type uint64;
      units "Byte/s";
      description
        "Rate of the bytes that match the policy but are discarded.";
    }
    leaf filter-packets {
      type uint64;
      units "packet";
      description
        "Number of filtered packets.";
    }
    leaf filter-bytes {
      type uint64;
      units "Byte";
      description
        "Number of filtered bytes.";
    }
    leaf filter-packet-rate {
      type uint64;
      units "pps";
      description
        "Rate of filtered packets.";
    }
    leaf filter-byte-rate {
      type uint64;
      units "Byte/s";
      description
        "Rate of filtered bytes.";
    }
  }
  grouping classifier-statistics-type {
    description
      "Traffic classifier statistics information.";
    leaf match-packets {
      type uint64;
      units "packet";
      description
        "Number of matched packets.";
    }
    leaf match-bytes {
      type uint64;
      units "Byte";
      description
        "Number of matched bytes.";
    }
    leaf match-packet-rate {
      type uint64;
      units "pps";
      description
        "Rate of matched packets.";
    }
    leaf match-byte-rate {
      type uint64;
      units "Byte/s";
      description
        "Rate of matched bytes.";
    }
    leaf match-pass-packets {
      type uint64;
      units "packet";
      description
        "Number of matched and passed packets.";
    }
    leaf match-pass-bytes {
      type uint64;
      units "Byte";
      description
        "Number of matched and passed bytes.";
    }
    leaf match-drop-packets {
      type uint64;
      units "packet";
      description
        "Number of matched but discarded packets.";
    }
    leaf match-drop-bytes {
      type uint64;
      units "Byte";
      description
        "Number of matched but discarded bytes.";
    }
    leaf match-pass-packet-rate {
      type uint64;
      units "pps";
      description
        "Rate of the packets matching the traffic classifier and passed.";
    }
    leaf match-pass-byte-rate {
      type uint64;
      units "Byte/s";
      description
        "Rate of the bytes matching the traffic classifier and passed.";
    }
    leaf match-drop-packet-rate {
      type uint64;
      units "pps";
      description
        "Rate of the packets matching the traffic classifier but discarded.";
    }
    leaf match-drop-byte-rate {
      type uint64;
      units "Byte/s";
      description
        "Rate of the bytes matching the traffic classifier but discarded.";
    }
    leaf filter-packets {
      type uint64;
      units "packet";
      description
        "Number of filtered packets.";
    }
    leaf filter-bytes {
      type uint64;
      units "Byte";
      description
        "Number of filtered bytes.";
    }
    leaf filter-packet-rate {
      type uint64;
      units "pps";
      description
        "Rate of filtered packets.";
    }
    leaf filter-byte-rate {
      type uint64;
      units "Byte/s";
      description
        "Rate of filtered bytes.";
    }
    leaf urpf-drop-packets {
      type uint64;
      units "packet";
      description
        "Number of the discarded packets by URPF check.";
    }
    leaf urpf-drop-bytes {
      type uint64;
      units "Byte";
      description
        "Number of the discarded bytes by URPF check.";
    }
    leaf urpf-drop-packet-rate {
      type uint64;
      units "pps";
      description
        "Rate of the discarded packets by URPF check.";
    }
    leaf urpf-drop-byte-rate {
      type uint64;
      units "Byte/s";
      description
        "Rate of the discarded bytes by URPF check.";
    }
    leaf car-packets {
      type uint64;
      units "packet";
      description
        "Number of the processed packets by CAR.";
    }
    leaf car-bytes {
      type uint64;
      units "Byte";
      description
        "Number of the processed bytes by CAR.";
    }
    leaf car-packet-rate {
      type uint64;
      units "pps";
      description
        "Rate of the passed packets by CAR.";
    }
    leaf car-byte-rate {
      type uint64;
      units "Byte/s";
      description
        "Rate of the passed bytes by CAR.";
    }
    leaf car-pass-packets {
      type uint64;
      units "packet";
      description
        "Number of the passed packets by CAR.";
    }
    leaf car-pass-bytes {
      type uint64;
       units "Byte";
      description
        "Number of the passed bytes by CAR.";
    }
    leaf car-drop-packets {
    type uint64;
      units "packet";
      description
        "Number of the discarded packets by CAR.";
    }
    leaf car-drop-bytes {
      type uint64;
      units "Byte";
      description
        "Number of the discarded bytes by CAR.";
    }
    leaf car-pass-packet-rate {
      type uint64;
      units "pps";
      description
        "Rate of the passed packets CAR.";
    }
    leaf car-pass-byte-rate {
      type uint64;
      units "Byte/s";
      description
        "Rate of the passed bytes by CAR.";
    }
    leaf car-drop-packet-rate {
      type uint64;
      units "pps";
      description
        "Rate of the discarded packets by CAR.";
    }
    leaf car-drop-byte-rate {
      type uint64;
      units "Byte/s";
      description
        "Rate of the discarded bytes by CAR.";
    }
    leaf car-green-packets {
      type uint64;
      units "packet";
      description
        "Number of green packets by CAR.";
    }
    leaf car-green-bytes {
      type uint64;
      units "Byte";
      description
        "Number of the bytes of green packets by CAR.";
    }
    leaf car-yellow-packets {
      type uint64;
      units "packet";
      description
        "Number of yellow packets by CAR.";
    }
    leaf car-yellow-bytes {
      type uint64;
      units "Byte";
      description
        "Number of the bytes of yellow packets by CAR.";
    }
    leaf car-red-packets {
      type uint64;
      units "packet";
      description
        "Number of red packets by CAR.";
    }
    leaf car-red-bytes {
      type uint64;
      units "Byte";
      description
        "Number of the bytes of red packets by CAR.";
    }
    leaf car-green-packet-rate {
      type uint64;
      units "pps";
      description
        "Rate of green packets by CAR.";
    }
    leaf car-green-byte-rate {
      type uint64;
      units "Byte/s";
      description
        "Rate of the bytes of green packets by CAR.";
    }
    leaf car-yellow-packet-rate {
      type uint64;
      units "pps";
      description
        "Rate of yellow packets by CAR.";
    }
    leaf car-yellow-byte-rate {
      type uint64;
      units "Byte/s";
      description
        "Rate of the bytes of yellow packets by CAR.";
    }
    leaf car-red-packet-rate {
      type uint64;
      units "pps";
      description
        "Rate of red packets by CAR.";
    }
    leaf car-red-byte-rate {
      type uint64;
      units "Byte/s";
      description
        "Rate of the bytes of red packets by CAR.";
    }
  }
  grouping multi-policy-classifier-statistics-type {
    description
      "Multiple traffic classifier statistics information.";
    leaf match-packets {
      type uint64;
      units "packet";
      description
        "Number of matched packets.";
    }
    leaf match-bytes {
      type uint64;
      units "Byte";
      description
        "Number of matched bytes.";
    }
    leaf match-packet-rate {
      type uint64;
      units "pps";
      description
        "Rate of matched packets.";
    }
    leaf match-byte-rate {
      type uint64;
      units "Byte/s";
      description
        "Rate of matched bytes.";
    }
    leaf match-pass-packets {
      type uint64;
      units "packet";
      description
        "Number of matched and passed packets.";
    }
    leaf match-pass-bytes {
      type uint64;
      units "Byte";
      description
        "Number of matched and passed bytes.";
    }
    leaf match-drop-packets {
      type uint64;
      units "packet";
      description
        "Number of matched but discarded packets.";
    }
    leaf match-drop-bytes {
      type uint64;
      units "Byte";
      description
        "Number of matched but discarded bytes.";
    }
    leaf match-pass-packet-rate {
      type uint64;
      units "pps";
      description
        "Rate of the packets matching the traffic classifier and passed.";
    }
    leaf match-pass-byte-rate {
      type uint64;
      units "Byte/s";
      description
        "Rate of the bytes matching the traffic classifier and passed.";
    }
    leaf match-drop-packet-rate {
      type uint64;
      units "pps";
      description
        "Rate of the packets matching the traffic classifier but discarded.";
    }
    leaf match-drop-byte-rate {
      type uint64;
      units "Byte/s";
      description
        "Rate of the bytes matching the traffic classifier but discarded.";
    }
    leaf filter-packets {
      type uint64;
      units "packet";
      description
        "Number of filtered packets.";
    }
    leaf filter-bytes {
      type uint64;
      units "Byte";
      description
        "Number of filtered bytes.";
    }
    leaf filter-packet-rate {
      type uint64;
      units "pps";
      description
        "Rate of filtered packets.";
    }
    leaf filter-byte-rate {
      type uint64;
      units "Byte/s";
      description
        "Rate of filtered bytes.";
    }
    leaf car-packets {
      type uint64;
      units "packet";
      description
        "Number of the processed packets by CAR.";
    }
    leaf car-bytes {
      type uint64;
      units "Byte";
      description
        "Number of the processed bytes by CAR.";
    }
    leaf car-packet-rate {
      type uint64;
      units "pps";
      description
        "Rate of the passed packets by CAR.";
    }
    leaf car-byte-rate {
      type uint64;
      units "Byte/s";
      description
        "Rate of the passed bytes by CAR.";
    }
    leaf car-pass-packets {
      type uint64;
      units "packet";
      description
        "Number of the passed packets by CAR.";
    }
    leaf car-pass-bytes {
      type uint64;
       units "Byte";
      description
        "Number of the passed bytes by CAR.";
    }
    leaf car-drop-packets {
    type uint64;
      units "packet";
      description
        "Number of the discarded packets by CAR.";
    }
    leaf car-drop-bytes {
      type uint64;
      units "Byte";
      description
        "Number of the discarded bytes by CAR.";
    }
    leaf car-pass-packet-rate {
      type uint64;
      units "pps";
      description
        "Rate of the passed packets CAR.";
    }
    leaf car-pass-byte-rate {
      type uint64;
      units "Byte/s";
      description
        "Rate of the passed bytes by CAR.";
    }
    leaf car-drop-packet-rate {
      type uint64;
      units "pps";
      description
        "Rate of the discarded packets by CAR.";
    }
    leaf car-drop-byte-rate {
      type uint64;
      units "Byte/s";
      description
        "Rate of the discarded bytes by CAR.";
    }
    leaf car-green-packets {
      type uint64;
      units "packet";
      description
        "Number of green packets by CAR.";
    }
    leaf car-green-bytes {
      type uint64;
      units "Byte";
      description
        "Number of the bytes of green packets by CAR.";
    }
    leaf car-yellow-packets {
      type uint64;
      units "packet";
      description
        "Number of yellow packets by CAR.";
    }
    leaf car-yellow-bytes {
      type uint64;
      units "Byte";
      description
        "Number of the bytes of yellow packets by CAR.";
    }
    leaf car-red-packets {
      type uint64;
      units "packet";
      description
        "Number of red packets by CAR.";
    }
    leaf car-red-bytes {
      type uint64;
      units "Byte";
      description
        "Number of the bytes of red packets by CAR.";
    }
    leaf car-green-packet-rate {
      type uint64;
      units "pps";
      description
        "Rate of green packets by CAR.";
    }
    leaf car-green-byte-rate {
      type uint64;
      units "Byte/s";
      description
        "Rate of the bytes of green packets by CAR.";
    }
    leaf car-yellow-packet-rate {
      type uint64;
      units "pps";
      description
        "Rate of yellow packets by CAR.";
    }
    leaf car-yellow-byte-rate {
      type uint64;
      units "Byte/s";
      description
        "Rate of the bytes of yellow packets by CAR.";
    }
    leaf car-red-packet-rate {
      type uint64;
      units "pps";
      description
        "Rate of red packets by CAR.";
    }
    leaf car-red-byte-rate {
      type uint64;
      units "Byte/s";
      description
        "Rate of the bytes of red packets by CAR.";
    }
  }
  grouping suppression-statistics-type {
    description
      "Suppression statistics information.";
    leaf unknownunisup-pass-packets {
      type uint64;
      units "packet";
      description
        "Number of the passed packets by unknown unicast suppression.";
    }
    leaf unknownunisup-pass-bytes {
      type uint64;
      units "Byte";
      description
        "Number of the passed bytes by unknown unicast suppression.";
    }
    leaf unknownunisup-pass-packet-rate {
      type uint64;
      units "pps";
      description
        "Rate of the passed packets unknown unicast suppression.";
    }
    leaf unknownunisup-pass-byte-rate {
      type uint64;
      units "Byte/s";
      description
        "Rate of the passed bytes by unknown unicast suppression.";
    }
    leaf unknownunisup-drop-packets {
      type uint64;
      units "packet";
      description
        "Number of the discarded packets by unknown unicast suppression.";
    }
    leaf unknownunisup-drop-bytes {
      type uint64;
      units "Byte";
      description
        "Number of the discarded bytes by unknown unicast suppression.";
    }
    leaf unknownunisup-drop-packet-rate {
      type uint64;
      units "pps";
      description
        "Rate of the discarded packets by unknown unicast suppression.";
    }
    leaf unknownunisup-drop-byte-rate {
      type uint64;
      units "Byte/s";
      description
        "Rate of the discarded bytes by unknown unicast suppression.";
    }
    leaf multicastsup-pass-packets {
      type uint64;
      units "packet";
      description
        "Number of the passed packets by multicast suppression.";
    }
    leaf multicastsup-pass-bytes {
      type uint64;
      units "Byte";
      description
        "Number of the passed bytes by multicast suppression.";
    }
    leaf multicastsup-pass-packet-rate {
      type uint64;
      units "pps";
      description
        "Rate of the passed packets multicast suppression.";
    }
    leaf multicastsup-pass-byte-rate {
      type uint64;
      units "Byte/s";
      description
        "Rate of the passed bytes by multicast suppression.";
    }
    leaf multicastsup-drop-packets {
      type uint64;
      units "packet";
      description
        "Number of the discarded packets by multicast suppression.";
    }
    leaf multicastsup-drop-bytes {
      type uint64;
      units "Byte";
      description
        "Number of the discarded bytes by multicast suppression.";
    }
    leaf multicastsup-drop-packet-rate {
      type uint64;
      units "pps";
      description
        "Rate of the discarded packets by multicast suppression.";
    }
    leaf multicastsup-drop-byte-rate {
      type uint64;
      units "Byte/s";
      description
        "Rate of the discarded bytes by multicast suppression.";
    }
    leaf broadcastsup-pass-packets {
      type uint64;
      units "packet";
      description
        "Number of the passed packets by broadcast suppression.";
    }
    leaf broadcastsup-pass-bytes {
      type uint64;
      units "Byte";
      description
        "Number of the passed bytes by broadcast suppression.";
    }
    leaf broadcastsup-pass-packet-rate {
      type uint64;
      units "pps";
      description
        "Rate of the passed packets broadcast suppression.";
    }
    leaf broadcastsup-pass-byte-rate {
      type uint64;
      units "Byte/s";
      description
        "Rate of the passed bytes by broadcast suppression.";
    }
    leaf broadcastsup-drop-packets {
      type uint64;
      units "packet";
      description
        "Number of the discarded packets by broadcast suppression.";
    }
    leaf broadcastsup-drop-bytes {
      type uint64;
      units "Byte";
      description
        "Number of the discarded bytes by broadcast suppression.";
    }
    leaf broadcastsup-drop-packet-rate {
      type uint64;
      units "pps";
      description
        "Rate of the discarded packets by broadcast suppression.";
    }
    leaf broadcastsup-drop-byte-rate {
      type uint64;
      units "Byte/s";
      description
        "Rate of the discarded bytes by broadcast suppression.";
    }
  }
grouping car-statistics-type {
    description
	  "CAR statistics information.";
	  leaf pass-packets {
		type uint64;
		units "packet";
		description
		  "Pass packets.";
	  }
	  leaf pass-bytes {
		type uint64;
		units "Byte";
		description
		  "Pass bytes.";
	  }
	  leaf pass-packet-rate {
		type uint64;
		units "pps";
		description
		  "Pass packet rate.";
	  }
	  leaf pass-byte-rate {
		type uint64;
		units "Byte/s";
		description
		  "Pass byte rate.";
	  }
	  leaf drop-packets {
		type uint64;
		units "packet";
		description
		  "Drop packets.";
	  }
	  leaf drop-bytes {
		type uint64;
		units "Byte";
		description
		  "Drop bytes.";
	  }
	  leaf drop-packet-rate {
		type uint64;
		units "pps";
		description
		  "Drop packet rate.";
	  }
	  leaf drop-byte-rate {
		type uint64;
		units "Byte/s";
		description
		  "Drop byte rate.";
	  }
  }
  ext:task-name "qos";
  container qos {
    description
      "Quality of service.";
    container wred-template {
      description
        "Configure wred template.";
        container flow-wreds {
        description
          "List of configure flow wred.";
        list flow-wred {
          key "name";
          max-elements "6144";
          description
            "Configure flow wred.";
          leaf name {
            type string {
              length "1..31";
            }
            description
              "Flow wred name.";
          }
          choice buffer-size {
            default "value-mode";
            description
              "Specify buffer size.";
            case value-mode {
              description
                "Specify buffer size choice case as value mode.";
              leaf queue-depth {
                type uint32;
                units "kB";
                description
                  "Queue depth.";
              }
            }
            case time-mode {
              description
                "Specify buffer size choice case as time mode.";
              leaf buffer-time {
                type uint32 {
                  range "10..1000000";
                }
                units "us";
                description
                  "Buffer time.";
              }
            }
          }
          container wred-colors {
            description
              "List of configure flow wred color.";
            list wred-color {
              key "color";
              max-elements  "3";
              description
                "Configure flow wred color.";
              ext:generated-by system {
                description "The instances are created and deleted following the flow wred template.";
              }
              ext:operation-exclude create {
                description "The instances cannot be created.";
              }
              leaf color {
                type qos-color;
                description
                  "Color.";
              }
              leaf low-limit-percentage {
                type uint8 {
                  range "0..100";
                }
                units "%";
                default "100";
                description
                  "Low limit percentage.";
              }
              leaf high-limit-percentage {
                type uint8 {
                  range "0..100";
                }
                units "%";
                must "../high-limit-percentage>=../low-limit-percentage";
                default "100";
                description
                  "High limit percentage.";
              }
              leaf discard-percentage {
                type uint8 {
                  range "1..100";
                }
                units "%";
                default "100";
                description
                  "Discarding percentage.";
              }
            }
          }
        }
      }
      container port-wreds {
        description
          "List of configure configure port wred.";
        list port-wred {
          key "name";
          max-elements  "127";
          description
            "Configure port wred.";
          leaf name {
            type string {
              length "1..31";
            }
            description
             "Port WRED name.";
          }
          choice buffer-size {
            default "value-mode";
            description
              "Specify buffer size.";
            case value-mode {
              description
                "Specify buffer size choice case as value mode.";
              leaf queue-depth {
                type uint32 {
                  range "0..4294967295";
                }
                units "kB";
                description
                  "Queue depth.";
              }
            }
            case time-mode {
              description
                "Specify buffer size choice case as time mode.";
              leaf buffer-time {
                type uint32 {
                  range "10..1000000";
                }
                units "us";
                description
                  "Buffer time.";
              }
            }
          }
          container wred-colors {
            description
              "List of configure port wred color. This node has default configurations. The default configuration cannot be created. The current configuration cannot be changed to the default configuration. If no user configuration exists, you can check the default configurations through the wred-colors-states node.";
            list wred-color {
            must "./high-limit-percentage>=./low-limit-percentage";
            key "color";
              max-elements  "3";
              description
                "Configure port wred color.";
              ext:generated-by system {
                description "The instances are created and deleted following the port wred template.";
              }
              ext:operation-exclude create {
                description "The instances cannot be created.";
              }
              leaf color {
                type qos-color;
                description
                  "Color.";
              }
              leaf low-limit-percentage {
                type uint8 {
                  range "0..100";
                }
                units "%";
                mandatory true;
                description
                  "Low limit percentage.";
              }
              leaf high-limit-percentage {
                type uint8 {
                  range "0..100";
                }
                units "%";
                mandatory true;
                description
                  "High limit percentage.";
              }
              leaf discard-percentage {
                type uint8 {
                  range "1..100";
                }
                units "%";
                mandatory true;
                description
                  "Discarding percentage.";
              }
            }
          }
          container wred-color-states {
            config false;
            description
              "List of configure operational state of port wred color.";
            list wred-color-state {
              key "color";
              max-elements  "3";
              description
                "Operational state of port wred color.";
              leaf color {
                type qos-color;
                description
                  "Color.";
              }
              leaf low-limit-percentage {
                type uint8 {
                  range "0..100";
                }
                units "%";
                description
                  "Low limit percentage.";
              }
              leaf high-limit-percentage {
                type uint8 {
                  range "0..100";
                }
                units "%";
                description
                  "High limit percentage.";
              }
              leaf discard-percentage {
                type uint8 {
                  range "1..100";
                }
                units "%";
                description
                  "Discarding percentage.";
              }
            }
          }
        }
      }
      container wreds {
        description
          "List of configure wred.";
        list wred {
          key "name";
          max-elements "8";
          description
            "Configure wred.";
          ext:generated-by system {
            description "The template is generated automatically.";
            ext:filter "name = 'default'";
          }
          leaf name {
            type string {
              length "1..31";
            }
            description
              "Wred name.";
          }
          leaf buffer-size-percentage {
            type uint32 {
              range "1..100";
            }
            units "%";
            description
              "Buffer size percentage.";
          }
          leaf mode {
            type wred-mode-type;
			default "blind";
            description
              "Wred mode.";
          }
          container colors {
            description
              "List of configure wred color.";
            list color {
              key "color";
              max-elements "3";
              description
                "Configure wred color. This node cannot be deleted.";
              ext:generated-by system {
                description "The instances are created and deleted following the wred template.";
              }
              ext:operation-exclude create {
                description "The instances cannot be created.";
              }
              leaf color {
                type qos-color;
                description
                  "Color.";
              }
              leaf low-limit-percentage {
                type uint8 {
                  range "0..100";
                }
                units "%";
                default "100";
                description
                  "Low limit percentage.";
              }
              leaf high-limit-percentage {
                type uint8 {
                  range "0..100";
                }
                units "%";
                must "../high-limit-percentage>=../low-limit-percentage";
                default "100";
                description
                  "High limit percentage.";
              }
              leaf discard-percentage {
                type uint8 {
                  range "1..100";
                }
                units "%";
                default "100";
                description
                  "Discarding percentage.";
              }
            }
          }
          container ecn {
            description
              "Configure the ecn command sets Explicit Congestion Notification (ECN) parameters including the upper and lower drop thresholds in percentage, absolute values of upper and lower drop thresholds, and maximum drop probability.";
            choice discard-threshold {
              description
                "Discard threshold choice.";
              case absolute-value {
                description
                "Discard absolute threshold value.";
                leaf absolute-flag {
                  type buff-alarm-type;
                  description
                    "Enable/disable flag of absolute.";
                }
                leaf lowlimitaslt {
                  when "../absolute-flag='true'";
                  type uint32 {
                    range "0..4294967295";
                  }
                  description
                    "Value of Lowlimit absolute.";
                }
                leaf highlimitaslt {
                  when "../absolute-flag='true'";
                  type uint32 {
                    range "0..4294967295";
                  }
				  must "../highlimitaslt>=../lowlimitaslt";
                  description
                    "Value of Highlimit absolute.";
                }
                leaf cell-flag {
                  type buff-alarm-type;
                  description
                    "Enable/disable flag of Cell.";
                }
                leaf lowlimitcell {
                  when "../cell-flag='true'";
                  type uint32 {
                    range "0..4294967295";
                  }
                  description
                    "Cell of Lowlimit.";
                }
                leaf highlimitcell {
                  when "../cell-flag='true'";
                  type uint32 {
                    range "0..4294967295";
                  }
				  must "../highlimitcell>=../lowlimitcell";
                  description
                    "Cell of Highlimit.";
                }
              }
              case percentage-value {
                description
                  "Discard threshold percentage value.";
                leaf low-limit {
                  type uint8 {
                    range "0..100";
                  }
                  default "100";
                  description
                    "Low threshold percentage dropped by WRED.";
                }
                leaf high-limit {
                  type uint8 {
                    range "0..100";
                  }
				  must "../high-limit>=../low-limit";
                  default "100";
                  description
                    "High threshold percentage dropped by WRED.";
                }
              }
            }
            leaf maximum-probability {
              type uint8 {
                range "1..100";
              }
              default "100";
              description
                "Maximum discard probability.";
            }
          }
          container dscp-wreds {
            when "../mode='dscp'";
            description
              "List of configure the dscp-wred parameters including dscp value, the lower and upper drop thresholds in percentage and maximum drop probability.";
            list dscp-wred {
              ext:generated-by system {
                description
                  "The instances are created and deleted following the wred template.";
              }
              ext:operation-exclude create {
                description
                  "The instances cannot be created.";
              }
              key "dscp";
              description
                "Configure dscp wred parameter.";
              leaf dscp {
                type uint8 {
                  range "0..63";
                }
                description
                  "DSCP.";
              }
              leaf low-limit-percentage {
                type uint8 {
                  range "0..100";
                }
                units "%";
                default "100";
                description
                  "Low limit percentage.";
              }
              leaf high-limit-percentage {
                type uint8 {
                  range "0..100";
                }
                units "%";
                must "../high-limit-percentage>=../low-limit-percentage";
                default "100";
                description
                  "High limit percentage.";
              }
              leaf discard-percentage {
                type uint8 {
                  range "1..100";
                }
                units "%";
                default "100";
                description
                  "Discarding percentage.";
              }
            }
          }
        }
      }//wred
    }//wred-template
    container queue-scheduler-template {
      description
        "Configure queue scheduler template.";
      container flow-queues {
        description
          "List of configure flow queue profile.";
        list flow-queue {
          key "name";
          max-elements  "2048";
          description
            "Configure flow queue profile.";
          leaf name {
            type template-name;
            description
              "Flow queue name.";
          }
          leaf mode {
            type flow-queue-template-type;
            mandatory true;
            description
              "Flow queue template mode.";
            ext:operation-exclude update {
              description "After the flow queue template is created, the node cannot be modified.";
            }
          }
          container normal-mode-queues {
            when "../mode='normal'";
            description
              "List of configure the scheduling parameters of normal mode flow queue.";
            list normal-mode-queue {
              key "service-class";
              max-elements  "8";
              description
                "Configure the scheduling parameters of normal mode flow queue.";
              ext:generated-by system {
                description "The instances are created and deleted following the flow queue template.";
              }
              ext:operation-exclude create {
                description "The instances cannot be created.";
              }
              leaf service-class {
                type qos-service-class;
                description
                  "Class of service.";
              }
              leaf flow-wred-name {
                type leafref {
                  path "../../../../../../wred-template/flow-wreds/flow-wred/name";
                }
                description
                  "Flow wred.";
              }
              choice config-type {
                default "shaping-mode";
                description
                  "Specify config type.";
                case shaping-mode {
                  description
                    "Specify config type choice case as shaping mode.";
                  leaf schedule-mode {
                    type queue-schedule-mode;
                    must "../schedule-mode!='wfq' or (../schedule-mode='wfq' and (../weight))";
                    description
                      "Scheduling strategy of flow queue. Can not be deleted or removed when lowlatency configured or service-class joined to share-shaping.";
                    ext:dynamic-default {
                      ext:default-value "wfq" {
                        when "../service-class='be' or ../service-class='af1' or ../service-class='af2' or ../service-class='af3' or ../service-class='af4'";
                        description "The default value is wfq when service-class is be or af1 or af2 or af3 or af4.";
                      }
                      ext:default-value "pq" {
                        when "../service-class='ef' or ../service-class='cs6' or ../service-class='cs7'";
                        description "The default value is wfq when service-class is ef or cs6 or cs7.";
                      }
                    }
                  }
                  leaf weight {
                    when "../schedule-mode='wfq'";
                    type uint8 {
                      range "1..100";
                    }
                    description
                      "Weight of WFQ scheduling strategy.";
                    ext:dynamic-default {
                      ext:default-value "10" {
                        when "../service-class='be' or ../service-class='af1' or ../service-class='af2'";
                        description "The default value is 10 when service-class is be or af1 or af2.";
                      }
                      ext:default-value "15" {
                        when "../service-class='af3' or ../service-class='af4'";
                        description "The default value is 15 when service-class is af3 or af4.";
                      }
                    }
                  }
                  leaf pbs {
                    type uint32 {
                      range "1..10000000";
                    }
                    units "Byte";
                    description
                      "Peak burst size.";
                  }
                  leaf low-latency {
                    when "../schedule-mode='pq'";
                    type queue-low-latency;
                    description
                      "Low Latency.";
                  }
                  leaf low-jitter {
                    type queue-low-jitter;
                    description
                      "Low Jitter.";
                  }
                  choice shaping-parameters {
                    description
                      "Specify shaping parameters.";
                    case shaping {
                      description
                        "Specify shaping parameters choice case as shaping value.";
                      leaf shaping-value {
                        type uint32 {
                          range "8..4294967294";
                        }
                        units "kbit/s";
                        description
                          "Rate of shaping.";
                      }
                    }
                    case shaping-percent {
                      description
                        "Specify shaping parameters choice case as shaping percentage value.";
                      leaf shaping-percentage {
                        type uint8 {
                          range "0..100";
                        }
                        units "%";
                        description
                          "Percentage of shaping.";
                      }
                    }
                    case car {
                      description
                        "Specify shaping parameters choice case as car value.";
                      leaf car-value {
                        when "../service-class='ef' or ../service-class='cs6' or ../service-class='cs7'";
                        type uint32 {
                          range "8..4294967294";
                        }
                        units "kbit/s";
                        description
                          "Rate of car.";
                      }
                    }
                    case car-percent {
                      description
                        "Specify shaping parameters choice case as car percentage value.";
                      leaf car-percentage {
                        when "../service-class='ef' or ../service-class='cs6' or ../service-class='cs7'";
                        type uint8 {
                          range "0..100";
                        }
                        units "%";
                        description
                          "Percentage of car.";
                      }
                    }
                  }
                }
                case cir-mode {
                  description
                    "Specify config type choice case as cir mode.";
                  leaf cir-schedule-mode {
                    type queue-cir-schedule-mode;
                    mandatory true;
                    description
                      "Scheduling strategy of flow queue.";
                  }
                  leaf pir-schedule-mode {
                    type queue-schedule-mode;
                    mandatory true;
                    description
                      "Scheduling strategy of flow queue.";
                  }
                  leaf pir-weight {
                    when "../pir-schedule-mode='wfq'";
                    type uint8 {
                      range "1..100";
                    }
                    mandatory true;
                    description
                      "Weight of WFQ scheduling strategy.";
                  }
                  leaf cbs {
                    type uint32 {
                      range "1..4194304";
                    }
                    units "Byte";
                    must "(../pir-pbs>=../cbs) or not(../pir-pbs)";
                    description
                      "Committed burst size.";
                  }
                  leaf pir-pbs {
                    type uint32 {
                      range "1..4194304";
                    }
                    units "Byte";
                    must "(../pir-pbs>=../cbs) or not(../cbs)";
                    description
                      "Peak burst size.";
                  }
                  choice cir-parameters {
                    mandatory true;
                    description
                      "Specify cir parameters.";
                    case cir {
                      description
                        "Specify cir parameters choice case as cir value.";
                      leaf cir-value {
                        type uint32 {
                          range "0..4294967294";
                        }
                        units "kbit/s";
                        must "../pir-value>=../cir-value";
                        mandatory true;
                        description
                          "Committed information rate.";
                      }
                      leaf pir-value {
                        type uint32 {
                          range "0..4294967294";
                        }
                        units "kbit/s";
                        must "../pir-value>=../cir-value";
                        mandatory true;
                        description
                          "Peak information rate.";
                      }
                    }
                    case cir-percent {
                      description
                        "Specify cir parameters choice case as cir percentage value.";
                      leaf cir-percentage {
                        type uint8 {
                          range "0..100";
                        }
                        units "%";
                        must "../pir-percentage>=../cir-percentage";
                        mandatory true;
                        description
                          "CIR percentage.";
                      }
                      leaf pir-percentage {
                        type uint8 {
                          range "0..100";
                        }
                        units "%";
                        must "../pir-percentage>=../cir-percentage";
                        mandatory true;
                        description
                          "PIR percentage.";
                      }
                    }
                  }
                }
              }
            }
          }
        container share-shapings {
          description
            "Configure share shaping.";
            container share-shaping {
              when "../../mode='normal'";
              must "not(not(./af1='true') and not(./af2='true') and not(./af3='true') and not(./af4='true') and not(./ef='true') and not(./cs6='true') and not(./cs7='true'))";
              must "not(not(./be='true') and not(./af2='true') and not(./af3='true') and not(./af4='true') and not(./ef='true') and not(./cs6='true') and not(./cs7='true'))";
              must "not(not(./be='true') and not(./af1='true') and not(./af3='true') and not(./af4='true') and not(./ef='true') and not(./cs6='true') and not(./cs7='true'))";
              must "not(not(./be='true') and not(./af1='true') and not(./af2='true') and not(./af4='true') and not(./ef='true') and not(./cs6='true') and not(./cs7='true'))";
              must "not(not(./be='true') and not(./af1='true') and not(./af2='true') and not(./af3='true') and not(./ef='true') and not(./cs6='true') and not(./cs7='true'))";
              must "not(not(./be='true') and not(./af1='true') and not(./af2='true') and not(./af3='true') and not(./af4='true') and not(./cs6='true') and not(./cs7='true'))";
              must "not(not(./be='true') and not(./af1='true') and not(./af2='true') and not(./af3='true') and not(./af4='true') and not(./ef='true') and not(./cs7='true'))";
              must "not(not(./be='true') and not(./af1='true') and not(./af2='true') and not(./af3='true') and not(./af4='true') and not(./ef='true') and not(./cs6='true'))";
              presence "create share-shape";
              description
                "Enable/disable share shaping. The configuration involves at least two queues, and the scheduling mode of the queues must be the same.";
              leaf be {
                type be-type;
                must "not(not(../../../normal-mode-queues/normal-mode-queue[service-class='be']/schedule-mode) and ../be='true')";
                must "../af1='false' or ../be='false' or ../../../normal-mode-queues/normal-mode-queue[service-class='be']/schedule-mode=../../../normal-mode-queues/normal-mode-queue[service-class='af1']/schedule-mode";
                must "../af2='false' or ../be='false' or ../../../normal-mode-queues/normal-mode-queue[service-class='be']/schedule-mode=../../../normal-mode-queues/normal-mode-queue[service-class='af2']/schedule-mode";
                must "../af3='false' or ../be='false' or ../../../normal-mode-queues/normal-mode-queue[service-class='be']/schedule-mode=../../../normal-mode-queues/normal-mode-queue[service-class='af3']/schedule-mode";
                must "../af4='false' or ../be='false' or ../../../normal-mode-queues/normal-mode-queue[service-class='be']/schedule-mode=../../../normal-mode-queues/normal-mode-queue[service-class='af4']/schedule-mode";
                must "../ef='false' or ../be='false' or ../../../normal-mode-queues/normal-mode-queue[service-class='be']/schedule-mode=../../../normal-mode-queues/normal-mode-queue[service-class='ef']/schedule-mode";
                must "../cs6='false' or ../be='false' or ../../../normal-mode-queues/normal-mode-queue[service-class='be']/schedule-mode=../../../normal-mode-queues/normal-mode-queue[service-class='cs6']/schedule-mode";
                must "../cs7='false' or ../be='false' or ../../../normal-mode-queues/normal-mode-queue[service-class='be']/schedule-mode=../../../normal-mode-queues/normal-mode-queue[service-class='cs7']/schedule-mode";
                default "false";
                description
                  "BE.";
              }
              leaf af1 {
                type af1-type;
                must "not(not(../../../normal-mode-queues/normal-mode-queue[service-class='af1']/schedule-mode) and ../af1='true')";
                must "../af2='false' or ../af1='false' or ../../../normal-mode-queues/normal-mode-queue[service-class='af1']/schedule-mode=../../../normal-mode-queues/normal-mode-queue[service-class='af2']/schedule-mode";
                must "../af3='false' or ../af1='false' or ../../../normal-mode-queues/normal-mode-queue[service-class='af1']/schedule-mode=../../../normal-mode-queues/normal-mode-queue[service-class='af3']/schedule-mode";
                must "../af4='false' or ../af1='false' or ../../../normal-mode-queues/normal-mode-queue[service-class='af1']/schedule-mode=../../../normal-mode-queues/normal-mode-queue[service-class='af4']/schedule-mode";
                must "../ef='false' or ../af1='false' or ../../../normal-mode-queues/normal-mode-queue[service-class='af1']/schedule-mode=../../../normal-mode-queues/normal-mode-queue[service-class='ef']/schedule-mode";
                must "../cs6='false' or ../af1='false' or ../../../normal-mode-queues/normal-mode-queue[service-class='af1']/schedule-mode=../../../normal-mode-queues/normal-mode-queue[service-class='cs6']/schedule-mode";
                must "../cs7='false' or ../af1='false' or ../../../normal-mode-queues/normal-mode-queue[service-class='af1']/schedule-mode=../../../normal-mode-queues/normal-mode-queue[service-class='cs7']/schedule-mode";
                default "false";
                description
                  "AF1.";
              }
              leaf af2 {
                type af2-type;
                must "not(not(../../../normal-mode-queues/normal-mode-queue[service-class='af2']/schedule-mode) and ../af2='true')";
                must "../af3='false' or ../af2='false' or ../../../normal-mode-queues/normal-mode-queue[service-class='af2']/schedule-mode=../../../normal-mode-queues/normal-mode-queue[service-class='af3']/schedule-mode";
                must "../af4='false' or ../af2='false' or ../../../normal-mode-queues/normal-mode-queue[service-class='af2']/schedule-mode=../../../normal-mode-queues/normal-mode-queue[service-class='af4']/schedule-mode";
                must "../ef='false' or ../af2='false' or ../../../normal-mode-queues/normal-mode-queue[service-class='af2']/schedule-mode=../../../normal-mode-queues/normal-mode-queue[service-class='ef']/schedule-mode";
                must "../cs6='false' or ../af2='false' or ../../../normal-mode-queues/normal-mode-queue[service-class='af2']/schedule-mode=../../../normal-mode-queues/normal-mode-queue[service-class='cs6']/schedule-mode";
                must "../cs7='false' or ../af2='false' or ../../../normal-mode-queues/normal-mode-queue[service-class='af2']/schedule-mode=../../../normal-mode-queues/normal-mode-queue[service-class='cs7']/schedule-mode";
                default "false";
                description
                  "AF2.";
              }
              leaf af3 {
                type af3-type;
                must "not(not(../../../normal-mode-queues/normal-mode-queue[service-class='af3']/schedule-mode) and ../af3='true')";
                must "../af4='false' or ../af3='false' or ../../../normal-mode-queues/normal-mode-queue[service-class='af3']/schedule-mode=../../../normal-mode-queues/normal-mode-queue[service-class='af4']/schedule-mode";
                must "../ef='false' or ../af3='false' or ../../../normal-mode-queues/normal-mode-queue[service-class='af3']/schedule-mode=../../../normal-mode-queues/normal-mode-queue[service-class='ef']/schedule-mode";
                must "../cs6='false' or ../af3='false' or ../../../normal-mode-queues/normal-mode-queue[service-class='af3']/schedule-mode=../../../normal-mode-queues/normal-mode-queue[service-class='cs6']/schedule-mode";
                must "../cs7='false' or ../af3='false' or ../../../normal-mode-queues/normal-mode-queue[service-class='af3']/schedule-mode=../../../normal-mode-queues/normal-mode-queue[service-class='cs7']/schedule-mode";
                default "false";
                description
                  "AF3.";
              }
              leaf af4 {
                type af4-type;
                must "not(not(../../../normal-mode-queues/normal-mode-queue[service-class='af4']/schedule-mode) and ../af4='true')";
                must "../ef='false' or ../af4='false' or ../../../normal-mode-queues/normal-mode-queue[service-class='af4']/schedule-mode=../../../normal-mode-queues/normal-mode-queue[service-class='ef']/schedule-mode";
                must "../cs6='false' or ../af4='false' or ../../../normal-mode-queues/normal-mode-queue[service-class='af4']/schedule-mode=../../../normal-mode-queues/normal-mode-queue[service-class='cs6']/schedule-mode";
                must "../cs7='false' or ../af4='false' or ../../../normal-mode-queues/normal-mode-queue[service-class='af4']/schedule-mode=../../../normal-mode-queues/normal-mode-queue[service-class='cs7']/schedule-mode";
                default "false";
                description
                  "AF4.";
              }
              leaf ef {
                type ef-type;
                must "not(not(../../../normal-mode-queues/normal-mode-queue[service-class='ef']/schedule-mode) and ../ef='true')";
                must "../cs6='false' or ../ef='false' or ../../../normal-mode-queues/normal-mode-queue[service-class='ef']/schedule-mode=../../../normal-mode-queues/normal-mode-queue[service-class='cs6']/schedule-mode";
                must "../cs7='false' or ../ef='false' or ../../../normal-mode-queues/normal-mode-queue[service-class='ef']/schedule-mode=../../../normal-mode-queues/normal-mode-queue[service-class='cs7']/schedule-mode";
                default "false";
                description
                  "EF.";
              }
              leaf cs6 {
                type cs6-type;
                must "not(not(../../../normal-mode-queues/normal-mode-queue[service-class='cs6']/schedule-mode) and ../cs6='true')";
                must "../cs7='false' or ../cs6='false' or ../../../normal-mode-queues/normal-mode-queue[service-class='cs6']/schedule-mode=../../../normal-mode-queues/normal-mode-queue[service-class='cs7']/schedule-mode";
                default "false";
                description
                  "CS6.";
              }
              leaf cs7 {
                type cs7-type;
                must "not(not(../../../normal-mode-queues/normal-mode-queue[service-class='cs7']/schedule-mode) and ../cs7='true')";
                default "false";
                description
                  "CS7.";
              }
              leaf queue-schedule-mode {
                type share-shape-mode;
                must "(../queue-schedule-mode='wfq' and ../weight) or (../queue-schedule-mode!='wfq' and not(../weight))";
                default "not-config";
                description
                  "Scheduling strategy of flow queue.";
              }
              leaf weight {
                type uint8 {
                  range "1..100";
                }
                must "../queue-schedule-mode='wfq' or (../queue-schedule-mode!='wfq' and not(../weight))";
                description
                  "Weight of WFQ scheduling strategy. Weight must be deleted with queue-schedule-mode 'Wfq'.";
              }
              leaf share-shaping-pir {
                type uint32 {
                  range "1..4294967294";
                }
                units "kbit/s";
                mandatory true;
                description
                  "Rate of shaping.";
              }
              leaf pbs {
                type uint32 {
                  range "1..4194304";
                }
                units "Byte";
                default "131072";
                description
                 "Peak burst size.";
              }
            }
          }
          container share-shaping-ids {
            when "../mode='normal'";
            description
              "List of configure share shaping with shap ID.";
            list share-shaping-id {
              must "not(not(./af1='true') and not(./af2='true') and not(./af3='true') and not(./af4='true') and not(./ef='true') and not(./cs6='true') and not(./cs7='true'))";
              must "not(not(./be='true') and not(./af2='true') and not(./af3='true') and not(./af4='true') and not(./ef='true') and not(./cs6='true') and not(./cs7='true'))";
              must "not(not(./be='true') and not(./af1='true') and not(./af3='true') and not(./af4='true') and not(./ef='true') and not(./cs6='true') and not(./cs7='true'))";
              must "not(not(./be='true') and not(./af1='true') and not(./af2='true') and not(./af4='true') and not(./ef='true') and not(./cs6='true') and not(./cs7='true'))";
              must "not(not(./be='true') and not(./af1='true') and not(./af2='true') and not(./af3='true') and not(./ef='true') and not(./cs6='true') and not(./cs7='true'))";
              must "not(not(./be='true') and not(./af1='true') and not(./af2='true') and not(./af3='true') and not(./af4='true') and not(./cs6='true') and not(./cs7='true'))";
              must "not(not(./be='true') and not(./af1='true') and not(./af2='true') and not(./af3='true') and not(./af4='true') and not(./ef='true') and not(./cs7='true'))";
              must "not(not(./be='true') and not(./af1='true') and not(./af2='true') and not(./af3='true') and not(./af4='true') and not(./ef='true') and not(./cs6='true'))";
              key "shap-id";
              description
                "Configure share shaping with shap ID. The configuration involves at least two queues, and the scheduling mode of the queues must be the same.";
              leaf shap-id {
                type shapid-upritype;
                description
                  "Shap Id.";
              }
              leaf be {
                type be-type;
                must "not(not(../../../normal-mode-queues/normal-mode-queue[service-class='be']/schedule-mode) and ../be='true')";
                must "../af1='false' or ../be='false' or ../../../normal-mode-queues/normal-mode-queue[service-class='be']/schedule-mode=../../../normal-mode-queues/normal-mode-queue[service-class='af1']/schedule-mode";
                must "../af2='false' or ../be='false' or ../../../normal-mode-queues/normal-mode-queue[service-class='be']/schedule-mode=../../../normal-mode-queues/normal-mode-queue[service-class='af2']/schedule-mode";
                must "../af3='false' or ../be='false' or ../../../normal-mode-queues/normal-mode-queue[service-class='be']/schedule-mode=../../../normal-mode-queues/normal-mode-queue[service-class='af3']/schedule-mode";
                must "../af4='false' or ../be='false' or ../../../normal-mode-queues/normal-mode-queue[service-class='be']/schedule-mode=../../../normal-mode-queues/normal-mode-queue[service-class='af4']/schedule-mode";
                must "../ef='false' or ../be='false' or ../../../normal-mode-queues/normal-mode-queue[service-class='be']/schedule-mode=../../../normal-mode-queues/normal-mode-queue[service-class='ef']/schedule-mode";
                must "../cs6='false' or ../be='false' or ../../../normal-mode-queues/normal-mode-queue[service-class='be']/schedule-mode=../../../normal-mode-queues/normal-mode-queue[service-class='cs6']/schedule-mode";
                must "../cs7='false' or ../be='false' or ../../../normal-mode-queues/normal-mode-queue[service-class='be']/schedule-mode=../../../normal-mode-queues/normal-mode-queue[service-class='cs7']/schedule-mode";
                default "false";
                description
                  "BE.";
              }
              leaf af1 {
                type af1-type;
                must "not(not(../../../normal-mode-queues/normal-mode-queue[service-class='af1']/schedule-mode) and ../af1='true')";
                must "../af2='false' or ../af1='false' or ../../../normal-mode-queues/normal-mode-queue[service-class='af1']/schedule-mode=../../../normal-mode-queues/normal-mode-queue[service-class='af2']/schedule-mode";
                must "../af3='false' or ../af1='false' or ../../../normal-mode-queues/normal-mode-queue[service-class='af1']/schedule-mode=../../../normal-mode-queues/normal-mode-queue[service-class='af3']/schedule-mode";
                must "../af4='false' or ../af1='false' or ../../../normal-mode-queues/normal-mode-queue[service-class='af1']/schedule-mode=../../../normal-mode-queues/normal-mode-queue[service-class='af4']/schedule-mode";
                must "../ef='false' or ../af1='false' or ../../../normal-mode-queues/normal-mode-queue[service-class='af1']/schedule-mode=../../../normal-mode-queues/normal-mode-queue[service-class='ef']/schedule-mode";
                must "../cs6='false' or ../af1='false' or ../../../normal-mode-queues/normal-mode-queue[service-class='af1']/schedule-mode=../../../normal-mode-queues/normal-mode-queue[service-class='cs6']/schedule-mode";
                must "../cs7='false' or ../af1='false' or ../../../normal-mode-queues/normal-mode-queue[service-class='af1']/schedule-mode=../../../normal-mode-queues/normal-mode-queue[service-class='cs7']/schedule-mode";
                default "false";
                description
                  "AF1.";
              }
              leaf af2 {
                type af2-type;
                must "not(not(../../../normal-mode-queues/normal-mode-queue[service-class='af2']/schedule-mode) and ../af2='true')";
                must "../af3='false' or ../af2='false' or ../../../normal-mode-queues/normal-mode-queue[service-class='af2']/schedule-mode=../../../normal-mode-queues/normal-mode-queue[service-class='af3']/schedule-mode";
                must "../af4='false' or ../af2='false' or ../../../normal-mode-queues/normal-mode-queue[service-class='af2']/schedule-mode=../../../normal-mode-queues/normal-mode-queue[service-class='af4']/schedule-mode";
                must "../ef='false' or ../af2='false' or ../../../normal-mode-queues/normal-mode-queue[service-class='af2']/schedule-mode=../../../normal-mode-queues/normal-mode-queue[service-class='ef']/schedule-mode";
                must "../cs6='false' or ../af2='false' or ../../../normal-mode-queues/normal-mode-queue[service-class='af2']/schedule-mode=../../../normal-mode-queues/normal-mode-queue[service-class='cs6']/schedule-mode";
                must "../cs7='false' or ../af2='false' or ../../../normal-mode-queues/normal-mode-queue[service-class='af2']/schedule-mode=../../../normal-mode-queues/normal-mode-queue[service-class='cs7']/schedule-mode";
                default "false";
                description
                  "AF2.";
              }
              leaf af3 {
                type af3-type;
                must "not(not(../../../normal-mode-queues/normal-mode-queue[service-class='af3']/schedule-mode) and ../af3='true')";
                must "../af4='false' or ../af3='false' or ../../../normal-mode-queues/normal-mode-queue[service-class='af3']/schedule-mode=../../../normal-mode-queues/normal-mode-queue[service-class='af4']/schedule-mode";
                must "../ef='false' or ../af3='false' or ../../../normal-mode-queues/normal-mode-queue[service-class='af3']/schedule-mode=../../../normal-mode-queues/normal-mode-queue[service-class='ef']/schedule-mode";
                must "../cs6='false' or ../af3='false' or ../../../normal-mode-queues/normal-mode-queue[service-class='af3']/schedule-mode=../../../normal-mode-queues/normal-mode-queue[service-class='cs6']/schedule-mode";
                must "../cs7='false' or ../af3='false' or ../../../normal-mode-queues/normal-mode-queue[service-class='af3']/schedule-mode=../../../normal-mode-queues/normal-mode-queue[service-class='cs7']/schedule-mode";
                default "false";
                description
                  "AF3.";
              }
              leaf af4 {
                type af4-type;
                must "not(not(../../../normal-mode-queues/normal-mode-queue[service-class='af4']/schedule-mode) and ../af4='true')";
                must "../ef='false' or ../af4='false' or ../../../normal-mode-queues/normal-mode-queue[service-class='af4']/schedule-mode=../../../normal-mode-queues/normal-mode-queue[service-class='ef']/schedule-mode";
                must "../cs6='false' or ../af4='false' or ../../../normal-mode-queues/normal-mode-queue[service-class='af4']/schedule-mode=../../../normal-mode-queues/normal-mode-queue[service-class='cs6']/schedule-mode";
                must "../cs7='false' or ../af4='false' or ../../../normal-mode-queues/normal-mode-queue[service-class='af4']/schedule-mode=../../../normal-mode-queues/normal-mode-queue[service-class='cs7']/schedule-mode";
                default "false";
                description
                  "AF4.";
              }
              leaf ef {
                type ef-type;
                must "not(not(../../../normal-mode-queues/normal-mode-queue[service-class='ef']/schedule-mode) and ../ef='true')";
                must "../cs6='false' or ../ef='false' or ../../../normal-mode-queues/normal-mode-queue[service-class='ef']/schedule-mode=../../../normal-mode-queues/normal-mode-queue[service-class='cs6']/schedule-mode";
                must "../cs7='false' or ../ef='false' or ../../../normal-mode-queues/normal-mode-queue[service-class='ef']/schedule-mode=../../../normal-mode-queues/normal-mode-queue[service-class='cs7']/schedule-mode";
                default "false";
                description
                  "EF.";
              }
              leaf cs6 {
                type cs6-type;
                must "not(not(../../../normal-mode-queues/normal-mode-queue[service-class='cs6']/schedule-mode) and ../cs6='true')";
                must "../cs7='false' or ../cs6='false' or ../../../normal-mode-queues/normal-mode-queue[service-class='cs6']/schedule-mode=../../../normal-mode-queues/normal-mode-queue[service-class='cs7']/schedule-mode";
                default "false";
                description
                  "CS6.";
              }
              leaf cs7 {
                type cs7-type;
                must "not(not(../../../normal-mode-queues/normal-mode-queue[service-class='cs7']/schedule-mode) and ../cs7='true')";
                default "false";
                description
                  "CS7.";
              }
              leaf queue-schedule-mode {
                type share-shape-mode;
                must "(../queue-schedule-mode='wfq' and ../weight) or (../queue-schedule-mode!='wfq' and not(../weight))";
                default "not-config";
                description
                  "Scheduling strategy of flow queue.";
              }
              leaf weight {
                type uint8 {
                  range "1..100";
                }
                must "../queue-schedule-mode='wfq'";
                description
                  "Weight of WFQ scheduling strategy. Weight must be deleted with queue-schedule-mode 'Wfq'.";
              }
              leaf share-shaping-pir {
                type uint32 {
                  range "1..4294967294";
                }
                units "kbit/s";
                mandatory true;
                description
                  "Rate of shaping.";
              }
              leaf pbs {
                type uint32 {
                  range "1..4194304";
                }
                units "Byte";
                default "131072";
                description
                  "Peak burst size.";
              }
            }
          }
          container share-shape-random-discards {
            description
            "Configure share shaping random discard.";
            container share-shape-random-discard {
              when "../../mode='normal'";
              must "not(not(./af1='true') and not(./af2='true') and not(./af3='true') and not(./af4='true') and not(./ef='true') and not(./cs6='true') and not(./cs7='true'))";
              must "not(not(./be='true') and not(./af2='true') and not(./af3='true') and not(./af4='true') and not(./ef='true') and not(./cs6='true') and not(./cs7='true'))";
              must "not(not(./be='true') and not(./af1='true') and not(./af3='true') and not(./af4='true') and not(./ef='true') and not(./cs6='true') and not(./cs7='true'))";
              must "not(not(./be='true') and not(./af1='true') and not(./af2='true') and not(./af4='true') and not(./ef='true') and not(./cs6='true') and not(./cs7='true'))";
              must "not(not(./be='true') and not(./af1='true') and not(./af2='true') and not(./af3='true') and not(./ef='true') and not(./cs6='true') and not(./cs7='true'))";
              must "not(not(./be='true') and not(./af1='true') and not(./af2='true') and not(./af3='true') and not(./af4='true') and not(./cs6='true') and not(./cs7='true'))";
              must "not(not(./be='true') and not(./af1='true') and not(./af2='true') and not(./af3='true') and not(./af4='true') and not(./ef='true') and not(./cs7='true'))";
              must "not(not(./be='true') and not(./af1='true') and not(./af2='true') and not(./af3='true') and not(./af4='true') and not(./ef='true') and not(./cs6='true'))";
              presence "create share-shape-rdmdscrd";
              description
                "Enable/disable share shaping random discard. The configuration involves at least two queues.";
              leaf be {
                type be-type;
                must "not(not(../../../normal-mode-queues/normal-mode-queue[service-class='be']/schedule-mode) and ../be='true')";
                must "../af1='false' or ../be='false' or ../../../normal-mode-queues/normal-mode-queue[service-class='be']/schedule-mode=../../../normal-mode-queues/normal-mode-queue[service-class='af1']/schedule-mode";
                must "../af2='false' or ../be='false' or ../../../normal-mode-queues/normal-mode-queue[service-class='be']/schedule-mode=../../../normal-mode-queues/normal-mode-queue[service-class='af2']/schedule-mode";
                must "../af3='false' or ../be='false' or ../../../normal-mode-queues/normal-mode-queue[service-class='be']/schedule-mode=../../../normal-mode-queues/normal-mode-queue[service-class='af3']/schedule-mode";
                must "../af4='false' or ../be='false' or ../../../normal-mode-queues/normal-mode-queue[service-class='be']/schedule-mode=../../../normal-mode-queues/normal-mode-queue[service-class='af4']/schedule-mode";
                must "../ef='false' or ../be='false' or ../../../normal-mode-queues/normal-mode-queue[service-class='be']/schedule-mode=../../../normal-mode-queues/normal-mode-queue[service-class='ef']/schedule-mode";
                must "../cs6='false' or ../be='false' or ../../../normal-mode-queues/normal-mode-queue[service-class='be']/schedule-mode=../../../normal-mode-queues/normal-mode-queue[service-class='cs6']/schedule-mode";
                must "../cs7='false' or ../be='false' or ../../../normal-mode-queues/normal-mode-queue[service-class='be']/schedule-mode=../../../normal-mode-queues/normal-mode-queue[service-class='cs7']/schedule-mode";
                default "false";
                description
                  "BE.";
              }
              leaf af1 {
                type af1-type;
                must "not(not(../../../normal-mode-queues/normal-mode-queue[service-class='af1']/schedule-mode) and ../af1='true')";
                must "../af2='false' or ../af1='false' or ../../../normal-mode-queues/normal-mode-queue[service-class='af1']/schedule-mode=../../../normal-mode-queues/normal-mode-queue[service-class='af2']/schedule-mode";
                must "../af3='false' or ../af1='false' or ../../../normal-mode-queues/normal-mode-queue[service-class='af1']/schedule-mode=../../../normal-mode-queues/normal-mode-queue[service-class='af3']/schedule-mode";
                must "../af4='false' or ../af1='false' or ../../../normal-mode-queues/normal-mode-queue[service-class='af1']/schedule-mode=../../../normal-mode-queues/normal-mode-queue[service-class='af4']/schedule-mode";
                must "../ef='false' or ../af1='false' or ../../../normal-mode-queues/normal-mode-queue[service-class='af1']/schedule-mode=../../../normal-mode-queues/normal-mode-queue[service-class='ef']/schedule-mode";
                must "../cs6='false' or ../af1='false' or ../../../normal-mode-queues/normal-mode-queue[service-class='af1']/schedule-mode=../../../normal-mode-queues/normal-mode-queue[service-class='cs6']/schedule-mode";
                must "../cs7='false' or ../af1='false' or ../../../normal-mode-queues/normal-mode-queue[service-class='af1']/schedule-mode=../../../normal-mode-queues/normal-mode-queue[service-class='cs7']/schedule-mode";
                default "false";
                description
                  "AF1.";
              }
              leaf af2 {
                type af2-type;
                must "not(not(../../../normal-mode-queues/normal-mode-queue[service-class='af2']/schedule-mode) and ../af2='true')";
                must "../af3='false' or ../af2='false' or ../../../normal-mode-queues/normal-mode-queue[service-class='af2']/schedule-mode=../../../normal-mode-queues/normal-mode-queue[service-class='af3']/schedule-mode";
                must "../af4='false' or ../af2='false' or ../../../normal-mode-queues/normal-mode-queue[service-class='af2']/schedule-mode=../../../normal-mode-queues/normal-mode-queue[service-class='af4']/schedule-mode";
                must "../ef='false' or ../af2='false' or ../../../normal-mode-queues/normal-mode-queue[service-class='af2']/schedule-mode=../../../normal-mode-queues/normal-mode-queue[service-class='ef']/schedule-mode";
                must "../cs6='false' or ../af2='false' or ../../../normal-mode-queues/normal-mode-queue[service-class='af2']/schedule-mode=../../../normal-mode-queues/normal-mode-queue[service-class='cs6']/schedule-mode";
                must "../cs7='false' or ../af2='false' or ../../../normal-mode-queues/normal-mode-queue[service-class='af2']/schedule-mode=../../../normal-mode-queues/normal-mode-queue[service-class='cs7']/schedule-mode";
                default "false";
                description
                  "AF2.";
              }
              leaf af3 {
                type af3-type;
                must "not(not(../../../normal-mode-queues/normal-mode-queue[service-class='af3']/schedule-mode) and ../af3='true')";
                must "../af4='false' or ../af3='false' or ../../../normal-mode-queues/normal-mode-queue[service-class='af3']/schedule-mode=../../../normal-mode-queues/normal-mode-queue[service-class='af4']/schedule-mode";
                must "../ef='false' or ../af3='false' or ../../../normal-mode-queues/normal-mode-queue[service-class='af3']/schedule-mode=../../../normal-mode-queues/normal-mode-queue[service-class='ef']/schedule-mode";
                must "../cs6='false' or ../af3='false' or ../../../normal-mode-queues/normal-mode-queue[service-class='af3']/schedule-mode=../../../normal-mode-queues/normal-mode-queue[service-class='cs6']/schedule-mode";
                must "../cs7='false' or ../af3='false' or ../../../normal-mode-queues/normal-mode-queue[service-class='af3']/schedule-mode=../../../normal-mode-queues/normal-mode-queue[service-class='cs7']/schedule-mode";
                default "false";
                description
                  "AF3.";
              }
              leaf af4 {
                type af4-type;
                must "not(not(../../../normal-mode-queues/normal-mode-queue[service-class='af4']/schedule-mode) and ../af4='true')";
                must "../ef='false' or ../af4='false' or ../../../normal-mode-queues/normal-mode-queue[service-class='af4']/schedule-mode=../../../normal-mode-queues/normal-mode-queue[service-class='ef']/schedule-mode";
                must "../cs6='false' or ../af4='false' or ../../../normal-mode-queues/normal-mode-queue[service-class='af4']/schedule-mode=../../../normal-mode-queues/normal-mode-queue[service-class='cs6']/schedule-mode";
                must "../cs7='false' or ../af4='false' or ../../../normal-mode-queues/normal-mode-queue[service-class='af4']/schedule-mode=../../../normal-mode-queues/normal-mode-queue[service-class='cs7']/schedule-mode";
                default "false";
                description
                  "AF4.";
              }
              leaf ef {
                type ef-type;
                must "not(not(../../../normal-mode-queues/normal-mode-queue[service-class='ef']/schedule-mode) and ../ef='true')";
                must "../cs6='false' or ../ef='false' or ../../../normal-mode-queues/normal-mode-queue[service-class='ef']/schedule-mode=../../../normal-mode-queues/normal-mode-queue[service-class='cs6']/schedule-mode";
                must "../cs7='false' or ../ef='false' or ../../../normal-mode-queues/normal-mode-queue[service-class='ef']/schedule-mode=../../../normal-mode-queues/normal-mode-queue[service-class='cs7']/schedule-mode";
                default "false";
                description
                  "EF.";
              }
              leaf cs6 {
                type cs6-type;
                must "not(not(../../../normal-mode-queues/normal-mode-queue[service-class='cs6']/schedule-mode) and ../cs6='true')";
                must "../cs7='false' or ../cs6='false' or ../../../normal-mode-queues/normal-mode-queue[service-class='cs6']/schedule-mode=../../../normal-mode-queues/normal-mode-queue[service-class='cs7']/schedule-mode";
                default "false";
                description
                  "CS6.";
              }
              leaf cs7 {
                type cs7-type;
                must "not(not(../../../normal-mode-queues/normal-mode-queue[service-class='cs7']/schedule-mode) and ../cs7='true')";
                default "false";
                description
                  "CS7.";
              }
              leaf random-discard {
                type string {
                  length "1..3";
                  pattern '(0\.[1-9])|([1-4]\.[0-9])|[1-5]|(5\.0)';
                }
                mandatory true;
                description
                  "Random discard percentage-value between 0.1 to 5 and the accuracy is 0.1.";
              }
            }
          }
          container normal-mode-random-discards {
            when "../mode='normal'";
            description
              "List of configure the random discard value of normal mode flow queue.";
            list normal-mode-random-discard {
              key "service-class";
              max-elements  "8";
              description
                "Configure the random discard value of normal mode flow queue.";
              leaf service-class {
                type qos-service-class;
                description
                  "Class of service.";
              }
              leaf random-discard {
                type string {
                  length "1..3";
                  pattern '(0\.[1-9])|([1-4]\.[0-9])|[1-5]|(5\.0)';
                }
                mandatory true;
                description
                  "Random discard percentage-value between 0.1 to 5 and the accuracy is 0.1.";
              }
            }
          }  
          container four-cos-mode-queues {
            when "../mode='4cos'";
            description
              "List of configure four cos mode flow queue.";
            list four-cos-mode-queue {
              key "cos-value";
              max-elements  "4";
              description
                "Configure four cos mode flow queue.";
              ext:generated-by system {
                description "The instances are created and deleted following the flow queue template.";
              }
              ext:operation-exclude create {
                description "The instances cannot be created.";
              }
              leaf cos-value {
                type qos-cos-value;
                description
                  "Service class.";
              }
              leaf schedule-mode {
                type queue-schedule-mode;
                mandatory true;
                description
                  "Priority.";
              }
              leaf weight {
                when "../schedule-mode='wfq'";
                type uint8 {
                  range "1..100";
                }
                mandatory true;
                description
                  "Weight of scheduling strategy.";
              }
              leaf shaping {
                type uint32 {
                  range "8..4294967294";
                }
                units "kbit/s";
                description
                  "Rate of shaping.";
              }
              leaf shaping-percentage {
                when "not(../shaping)";
                type uint8 {
                  range "0..100";
                }
                units "%";
                description
                  "Percentage of shaping.";
              }
              leaf pbs {
                when "../shaping or ../shaping-percentage";
                type uint32 {
                  range "1..4194304";
                }
                units "Byte";
                description
                  "Peak burst size.";
              }
              leaf flow-wred-name {
                type leafref {
                  path "../../../../../../wred-template/flow-wreds/flow-wred/name";
                }
                description
                  "Wred name.";
              }
            }
          }
          container priority-mode-queues {
            when "../mode='priority'";
            description
              "List of configure priority mode flow queues.";
            list priority-mode-queue {
              key "service-class";
              max-elements  "8";
              description
                "Configure priority mode flow queue.";
              ext:generated-by system {
                description "The instances are created and deleted following the flow queue template.";
              }
              ext:operation-exclude create {
                description "The instances cannot be created.";
              }
              leaf service-class {
                type qos-service-class;
                description
                  "Service class.";
              }
              leaf priority {
                type uint8 {
                  range "0..3";
                }
                mandatory true;
                description
                  "Priority.";
              }
              leaf weight {
                type uint8 {
                  range "1..100";
                }
                mandatory true;
                description
                  "Weight of priority flow queue.";
              }
              leaf shaping {
                type uint32 {
                  range "8..4294967294";
                }
                units "kbit/s";
                description
                  "Rate of priority flow queue shaping.";
              }
              leaf shaping-percentage {
                when "not(../shaping)";
                type uint8 {
                  range "0..100";
                }
                units "%";
                description
                  "Percentage of shaping.";
              }
              leaf pbs {
                when "../shaping or ../shaping-percentage";
                type uint32 {
                  range "1..4194304";
                }
                units "Byte";
                description
                  "Peak burst size.";
              }
              leaf flow-wred-name {
                type leafref {
                  path "../../../../../../wred-template/flow-wreds/flow-wred/name";
                }
                description
                  "Wred name.";
              }
            }
          }
          container priority-mode-schedules {
            when "../mode='priority'";
            description
              "List of configure schedule parameters of priority mode flow queue.";
            list priority-mode-schedule {
              key "priority";
              description
                "Configure schedule parameters of priority mode flow queue.";
              ext:generated-by system {
                description "The instances are created and deleted following the flow queue template.";
              }
              ext:operation-exclude create {
                description "The instances cannot be created.";
              }
              leaf priority {
                type uint8 {
                  range "0..3";
                }
                description
                  "Priority.";
              }
              leaf schedule-mode {
                type priority-flow-queue-schedule-mode;
                mandatory true;
                description
                  "Schedule.";
              }
            }
          }  
          container priority-mode-share-shapings {
            when "../mode='priority'";
            description
              "List of configure priority mode flow queue share shaping.";
            list priority-mode-share-shaping {
              must "not(not(./af1) and not(./af2) and not(./af3) and not(./af4) and not(./ef) and not(./cs6) and not(./cs7))";
              must "not(not(./be) and not(./af2) and not(./af3) and not(./af4) and not(./ef) and not(./cs6) and not(./cs7))";
              must "not(not(./be) and not(./af1) and not(./af3) and not(./af4) and not(./ef) and not(./cs6) and not(./cs7))";
              must "not(not(./be) and not(./af1) and not(./af2) and not(./af4) and not(./ef) and not(./cs6) and not(./cs7))";
              must "not(not(./be) and not(./af1) and not(./af2) and not(./af3) and not(./ef) and not(./cs6) and not(./cs7))";
              must "not(not(./be) and not(./af1) and not(./af2) and not(./af3) and not(./af4) and not(./cs6) and not(./cs7))";
              must "not(not(./be) and not(./af1) and not(./af2) and not(./af3) and not(./af4) and not(./ef) and not(./cs7))";
              must "not(not(./be) and not(./af1) and not(./af2) and not(./af3) and not(./af4) and not(./ef) and not(./cs6))";
              key "shap-id";
              max-elements  "2";
              description
                "Configure priority mode flow queue share shaping.";
              leaf shap-id {
                type shap-id-type;
                description
                  "Shap id.";
              }
              leaf be {
                type queue-select-be-type;
                must "not(../af1) or ../../../priority-mode-queues/priority-mode-queue[service-class='be']/priority=../../../priority-mode-queues/priority-mode-queue[service-class='af1']/priority";
                must "not(../af2) or ../../../priority-mode-queues/priority-mode-queue[service-class='be']/priority=../../../priority-mode-queues/priority-mode-queue[service-class='af2']/priority";
                must "not(../af3) or ../../../priority-mode-queues/priority-mode-queue[service-class='be']/priority=../../../priority-mode-queues/priority-mode-queue[service-class='af3']/priority";
                must "not(../af4) or ../../../priority-mode-queues/priority-mode-queue[service-class='be']/priority=../../../priority-mode-queues/priority-mode-queue[service-class='af4']/priority";
                must "not(../ef) or ../../../priority-mode-queues/priority-mode-queue[service-class='be']/priority=../../../priority-mode-queues/priority-mode-queue[service-class='ef']/priority";
                must "not(../cs6) or ../../../priority-mode-queues/priority-mode-queue[service-class='be']/priority=../../../priority-mode-queues/priority-mode-queue[service-class='cs6']/priority";
                must "not(../cs7) or ../../../priority-mode-queues/priority-mode-queue[service-class='be']/priority=../../../priority-mode-queues/priority-mode-queue[service-class='cs7']/priority";
                must "not(../../priority-mode-share-shaping[shap-id='not-config']/be) or not(../../priority-mode-share-shaping[shap-id='1']/be)";
                description
                  "Queue be.";
              }
              leaf af1 {
                type queue-select-af1-type;
                must "not(../af2) or ../../../priority-mode-queues/priority-mode-queue[service-class='af1']/priority=../../../priority-mode-queues/priority-mode-queue[service-class='af2']/priority";
                must "not(../af3) or ../../../priority-mode-queues/priority-mode-queue[service-class='af1']/priority=../../../priority-mode-queues/priority-mode-queue[service-class='af3']/priority";
                must "not(../af4) or ../../../priority-mode-queues/priority-mode-queue[service-class='af1']/priority=../../../priority-mode-queues/priority-mode-queue[service-class='af4']/priority";
                must "not(../ef) or ../../../priority-mode-queues/priority-mode-queue[service-class='af1']/priority=../../../priority-mode-queues/priority-mode-queue[service-class='ef']/priority";
                must "not(../cs6) or ../../../priority-mode-queues/priority-mode-queue[service-class='af1']/priority=../../../priority-mode-queues/priority-mode-queue[service-class='cs6']/priority";
                must "not(../cs7) or ../../../priority-mode-queues/priority-mode-queue[service-class='af1']/priority=../../../priority-mode-queues/priority-mode-queue[service-class='cs7']/priority";                
                must "not(../../priority-mode-share-shaping[shap-id='not-config']/af1) or not(../../priority-mode-share-shaping[shap-id='1']/af1)";               
                description
                  "Queue af1.";
              }
              leaf af2 {
                type queue-select-af2-type;
                must "not(../af3) or ../../../priority-mode-queues/priority-mode-queue[service-class='af2']/priority=../../../priority-mode-queues/priority-mode-queue[service-class='af3']/priority";
                must "not(../af4) or ../../../priority-mode-queues/priority-mode-queue[service-class='af2']/priority=../../../priority-mode-queues/priority-mode-queue[service-class='af4']/priority";
                must "not(../ef) or ../../../priority-mode-queues/priority-mode-queue[service-class='af2']/priority=../../../priority-mode-queues/priority-mode-queue[service-class='ef']/priority";
                must "not(../cs6) or ../../../priority-mode-queues/priority-mode-queue[service-class='af2']/priority=../../../priority-mode-queues/priority-mode-queue[service-class='cs6']/priority";
                must "not(../cs7) or ../../../priority-mode-queues/priority-mode-queue[service-class='af2']/priority=../../../priority-mode-queues/priority-mode-queue[service-class='cs7']/priority";
                must "not(../../priority-mode-share-shaping[shap-id='not-config']/af2) or not(../../priority-mode-share-shaping[shap-id='1']/af2)";
                description
                  "Queue af2.";
              }
              leaf af3 {
                type queue-select-af3-type;
                must "not(../af4) or ../../../priority-mode-queues/priority-mode-queue[service-class='af3']/priority=../../../priority-mode-queues/priority-mode-queue[service-class='af4']/priority";
                must "not(../ef) or ../../../priority-mode-queues/priority-mode-queue[service-class='af3']/priority=../../../priority-mode-queues/priority-mode-queue[service-class='ef']/priority";
                must "not(../cs6) or ../../../priority-mode-queues/priority-mode-queue[service-class='af3']/priority=../../../priority-mode-queues/priority-mode-queue[service-class='cs6']/priority";
                must "not(../cs7) or ../../../priority-mode-queues/priority-mode-queue[service-class='af3']/priority=../../../priority-mode-queues/priority-mode-queue[service-class='cs7']/priority";
                must "not(../../priority-mode-share-shaping[shap-id='not-config']/af3) or not(../../priority-mode-share-shaping[shap-id='1']/af3)";
                description
                  "Queue af3.";
              }
              leaf af4 {
                type queue-select-af4-type;
                must "not(../ef) or ../../../priority-mode-queues/priority-mode-queue[service-class='af4']/priority=../../../priority-mode-queues/priority-mode-queue[service-class='ef']/priority";
                must "not(../cs6) or ../../../priority-mode-queues/priority-mode-queue[service-class='af4']/priority=../../../priority-mode-queues/priority-mode-queue[service-class='cs6']/priority";
                must "not(../cs7) or ../../../priority-mode-queues/priority-mode-queue[service-class='af4']/priority=../../../priority-mode-queues/priority-mode-queue[service-class='cs7']/priority";
                must "not(../../priority-mode-share-shaping[shap-id='not-config']/af4) or not(../../priority-mode-share-shaping[shap-id='1']/af4)";
                description
                  "Queue af4.";
              }
              leaf ef {
                type queue-select-ef-type;
                must "not(../cs6) or ../../../priority-mode-queues/priority-mode-queue[service-class='ef']/priority=../../../priority-mode-queues/priority-mode-queue[service-class='cs6']/priority";
                must "not(../cs7) or ../../../priority-mode-queues/priority-mode-queue[service-class='ef']/priority=../../../priority-mode-queues/priority-mode-queue[service-class='cs7']/priority";
                must "not(../../priority-mode-share-shaping[shap-id='not-config']/ef) or not(../../priority-mode-share-shaping[shap-id='1']/ef)";
                description
                  "Queue ef.";
              }
              leaf cs6 {
                type queue-select-cs6-type;
                must "not(../cs7) or ../../../priority-mode-queues/priority-mode-queue[service-class='cs6']/priority=../../../priority-mode-queues/priority-mode-queue[service-class='cs7']/priority";
                must "not(../../priority-mode-share-shaping[shap-id='not-config']/cs6) or not(../../priority-mode-share-shaping[shap-id='1']/cs6)";
                description
                  "Queue cs6.";
              }
              leaf cs7 {
                type queue-select-cs7-type;
                must "not(../../priority-mode-share-shaping[shap-id='not-config']/cs7) or not(../../priority-mode-share-shaping[shap-id='1']/cs7)";
                description
                  "Queue cs7.";
              }
              leaf schedule-mode {
                type priority-flow-queue-schedule-mode;
                description
                  "Share shaping schedule mode.";
              }
              leaf weight {
                type uint8 {
                  range "1..100";
                }
                description
                  "Weight scheduling strategy.";
              }
              leaf share-shaping-pir {
                type uint32 {
                  range "1..4294967294";
                }
                units "kbit/s";
                mandatory true;
                description
                  "Rate of share shaping.";
              }
              leaf pbs {
                type uint32 {
                  range "1..4194304";
                }
                units "Byte";
                default "131072";
                description
                  "Peak burst size.";
              }
            }
          }
          container eight-cos-mode-queues {
            when "../mode='8cos-enhance'";
            description
              "List of configure the scheduling parameters of eight cos mode flow queue.";
            list eight-cos-mode-queue {
              key "cos";
              max-elements "8";
              description
                "Configure the scheduling parameters of eight cos mode flow queue.";
              ext:generated-by system {
                description "The instances are created and deleted following the flow queue template.";
              }
              ext:operation-exclude create {
                description "The instances cannot be created.";
              }
              leaf cos {
                type uint8 {
                  range "0..7";
                }
                description
                  "Class of service.";
              }
              container flow-wred {
                description
                  "Configure flow wred.";
                leaf name {
                  type leafref {
                    path "../../../../../../../wred-template/flow-wreds/flow-wred/name";
                  }
                  description
                    "Flow wred name.";
                }
              }
              container car-mode {
                when "../cos=5 or ../cos=6 or ../cos=7";
                presence "create car-mode";
                description
                  "Enable/disable car mode.";
              }
              container remark-color {
                presence "create remark-color";
                description
                  "Enable/disable remark color.";
              }
              container parent-priority {
                must "cir-parent-priority < pir-parent-priority";
                presence "create parent-priority";
                description
                  "Configure parent priority.";
                ext:generated-by system {
                  description "The instances are created and deleted following the parameters of eight cos mode flow queue.";
                }
                ext:operation-exclude create {
                  description "The instances cannot be created.";
                }
                leaf cir-parent-priority {
                  type uint8 {
                    range "0..2";
                  }
                  mandatory true;
                  description
                    "Cir parent priority value.";
                }
                leaf cir-weight {
                  type uint8 {
                    range "1..100";
                  }
                  description
                    "Cir weight.";
                  ext:dynamic-default {
                    ext:default-value 10 {
                      when "../../cos=0 or ../../cos=1 or ../../cos=2";
                      description "The default value is 10 when cos is 0, 1 or 2.";
                    }
                    ext:default-value 15 {
                      when "../../cos=3 or ../../cos=4";
                      description "The default value is 15 when cos is 3 or 4.";
                    }
                    ext:default-value 20 {
                      when "../../cos=5 or ../../cos=6 or ../../cos=7";
                      description "The default value is 20 when cos is 5, 6 or 7.";
                    }
                  }
                }
                leaf pir-parent-priority {
                  type uint8 {
                    range "1..3";
                  }
                  mandatory true;
                  description
                    "Pir parent priority value.";
                }
                leaf pir-weight {
                  type uint8 {
                    range "1..100";
                  }
                  description
                    "Pir weight.";
                  ext:dynamic-default {
                    ext:default-value 10 {
                      when "../../cos=0 or ../../cos=1 or ../../cos=2";
                      description "The default value is 10 when cos is 0, 1 or 2.";
                    }
                    ext:default-value 15 {
                      when "../../cos=3 or ../../cos=4";
                      description "The default value is 15 when cos is 3 or 4.";
                    }
                    ext:default-value 20 {
                      when "../../cos=5 or ../../cos=6 or ../../cos=7";
                      description "The default value is 20 when cos is 5, 6 or 7.";
                    }
                  }
                }
              }
              container pir {
                must "pbs>=cbs or not(pbs) or not(cbs)";
                must "peak-burst-time>=committed-burst-time or not(peak-burst-time) or not(committed-burst-time)";
                presence "create pir";
                description
                  "Configure pir of flow queue.";
                choice parameter {
                  mandatory true;
                  description
                    "Specify parameter.";
                  case value-mode {
                    description
                      "Specify pir parameter choice case as value mode.";
                    leaf pir-value {
                      type uint32 {
                        range "8..4294967294";
                      }
                      units "kbit/s";
                      must "../pir-value>=../cir-value or not(../cir-value)";
                      mandatory true;
                      description
                        "Peak information rate.";
                    }
                    leaf cir-value {
                      type uint32 {
                        range "8..4294967294";
                      }
                      units "kbit/s";
                      must "../pir-value>=../cir-value";
                      description
                        "Committed information rate.";
                    }
                  }
                  case percent-mode {
                    description
                      "Specify pir parameter choice case as percent mode.";
                    leaf pir-percent {
                      type uint8 {
                        range "0..100";
                      }
                      units "%";
                      must "../pir-percent>=../cir-percent or not(../cir-percent)";
                      mandatory true;
                      description
                        "Peak information rate percent.";
                    }
                    leaf cir-percent {
                      type uint8 {
                        range "0..100";
                      }
                      units "%";
                      must "../pir-percent>=../cir-percent";
                      description
                        "Committed information rate percent.";
                    }
                  }
                }
                choice burst-size {
                  description
                    "Specify burst size.";
                  case value-mode {
                    description
                      "Specify burst size choice case as value mode.";
                    leaf pbs {
                      type uint32 {
                        range "1..max";
                      }
                      units "Byte";
                      description
                        "Peak burst size.";
                    }
                    leaf cbs {
                      when "../cir-value or ../cir-percent";
                      type uint32 {
                        range "1..max";
                      }
                      units "Byte";
                      description
                        "Committed burst size.";
                    }
                  }
                  case time-mode {
                    description
                      "Specify burst size choice case as time mode.";
                    leaf peak-burst-time {
                      type uint16 {
                        range "1..5000";
                      }
                      units "ms";
                      description
                        "Peak burst time.";
                    }
                    leaf committed-burst-time {
                      when "../cir-value or ../cir-percent";
                      type uint16 {
                        range "1..5000";
                      }
                      units "ms";
                      description
                        "Committed burst time.";
                    }
                  }
                }
              }
            }
          }
          container traffic-behavior-queues {
            description
              "List of configure the scheduling parameters of flow queue.";
            list traffic-behavior-queue {
              key "name";
              max-elements 32;
              description
                "Configure the scheduling parameters of flow queue.";
              leaf name {
                type string {
                  length "1..31";
                }
                description
                  "Flow queue name.";
              }
              leaf scheduler-mode {
                type user-schedule-mode;
                mandatory true;
                description
                  "Scheduling strategy of flow queue.";
              }
              leaf weight {
                when "../scheduler-mode='drr'";
                type uint8 {
                  range "1..100";
                }
                description
                  "Weight of drr scheduling strategy.";
              }
              choice shaping-config-type {
                mandatory true;
                description
                  "Specify config type.";
                case shaping-mode {
                  description
                    "Specify config type choice case as shaping mode.";
                  leaf shaping {
                    type uint32 {
                      range "64..100000000";
                    }
                    units "kbit/s";
                    description
                      "Shaping value.";
                  }
                }
                case shaping-percent-mode {
                  description
                    "Specify config type choice case as shaping percentage mode.";
                  leaf shaping-percent {
                    type uint8 {
                      range "1..100";
                    }
                    units "%";
                    description
                      "Shaping percentage.";
                  }
                  leaf percent-reference {
                    type qos:percent-reference-type;
                    ext:dynamic-default;
                    description
                      "Shaping percentage reference.";
                  }
                }
              }
              leaf pbs {
                type uint32 {
                  range "0..4194304";
                }
                units "Byte";
                description
                  "Peak burst size.";
              }
              leaf flow-wred-name {
                type leafref {
                  path "/qos:qos/qos:wred-template/qos:wreds/qos:wred/qos:name";
                }
                description
                  "Drop wred profile.";
              }
              leaf packet-number {
                type uint32 {
                  range "1..1024";
                }
                description
                  "Number of packets.";
              }
              leaf queue-depth {
                type uint32 {
                  range "1..4294967295";
                }
                description
                  "Queue depth.";
              }
              leaf weight-fix {
                when "../scheduler-mode='drr'";
                type boolean;
                default "false";
                description
                  "Enable/disable the fixed weight function of the drr queue.";
              }
            }
          }
        }
      }
      container profiles {
        description
          "List of configure QoS profile.";
        list profile {
          key "name";
          max-elements  "4095";
          description
            "Configure QoS profile.";
          leaf name {
            type qos-profile-template-name;
            description
              "Name of qos profile.";
          }
          leaf mode {
            type profile-template-type;
            mandatory true;
            description
              "Profile Template Mode. This node does not support modification.";
            ext:operation-exclude update {
              description "After profile template is created, the node cannot be modified.";
            }
          }
          leaf description {
            type string {
              length "1..63";
            }
            description
              "Profile template description.";
          }
          container user-queues {
            when "../mode!='8cos-enhance'";
            description
              "List of configure user queue.";
            list user-queue {
              key "direction";
              max-elements  "2";
              description
                "Configure user queue.";
              leaf direction {
                type all-direction-type;
                description
                  "Direction.";
              }
              choice config-type {
                mandatory true;
                description
                  "Specify config type.";
                case cir-mode {
                  description
                    "Specify config type choice case as cir mode.";
                  leaf cir {
                    type uint32 {
                      range "0 | 16..4294967294";
                    }
                    units "kbit/s";
                    must "../pir>=../cir";
                    mandatory true;
                    description
                      "Committed information rate.";
                  }
                  leaf pir {
                    type uint32 {
                      range "0 | 16..4294967294";
                    }
                    units "kbit/s";
                    must "../pir>=../cir";
                    mandatory true;
                    description
                      "Peak information rate.";
                  }
                }
                case cir-percent-mode {
                  description
                    "Specify config type choice case as cir percentage mode.";
                  leaf cir-percent {
                    type uint8 {
                      range "0..100";
                    }
                    units "%";
                    must "../pir-percent>=../cir-percent";
                    mandatory true;
                    description
                      "Cir percentage.";
                  }
                  leaf pir-percent {
                    type uint8 {
                      range "0..100";
                    }
                    units "%";
                    must "../pir-percent>=../cir-percent";
                    mandatory true;
                    description
                      "Pir percentage.";
                  }
                }
              }
              leaf cbs {
                type uint32 {
                  range "1..4194304";
                }
                units "Byte";
                description
                  "Committed burst size.";
              }
              leaf pbs {
                type uint32 {
                  range "1..4194304";
                }
                units "Byte";
                must "not(../cbs) or ../pbs>=../cbs";
                description
                  "Peak burst size.";
              }
              leaf priority-level-id {
                type priority-level-type;
                /*must "../pir or ../pir-percent";*/
                default "low";
                description
                  "PIR priority.";
              }
              leaf flow-queue-name {
                type leafref {
                  path "../../../../../flow-queues/flow-queue/name";
                }
                must "../../../../../flow-queues/flow-queue[name=current()]/mode!='8cos-enhance' and not(../../../../../flow-queues/flow-queue[name=current()]/mode='4cos' and ../direction='inbound')";
                description
                  "Flow queue.";
              }
              leaf flow-mapping-name {
                type leafref {
                  path "../../../../../flow-mappings/flow-mapping/name";
                }
                description
                  "Flow mapping.";
              }
              leaf user-group-queue-name {
                type leafref {
                  path "../../../../../user-group-queues/user-group-queue/name";
                }
                must "(../../../../../user-group-queues/user-group-queue[name=current()]/mode!='priority' and ../direction='inbound') or (../direction!='inbound')";
                description
                  "User group queue.";
              }
              leaf service-template-name {
                type leafref {
                  path "../../../../../service-templates/service-template/name";
                }
                description
                  "Service template.";
              }
              leaf queue-4cos-mapping-name {
                when "../flow-queue-name and ../../../../../flow-queues/flow-queue[name=current()/../flow-queue-name]/mode='4cos' and ../../../mode!='time-range'";
                type leafref {
                  path "../../../../../queue-4cos-mappings/queue-4cos-mapping/name";
                }
                description
                  "Queue 4cos mapping.";
              }
              leaf adjust-on-card {
                type adjust-on-card-type;
                default "disable";
                description
                  "Adjust on card flag.";
              }
            }
          }
          container user-queue-weights {
            when "../mode!='8cos-enhance'";
            description
              "List of configure user queue weight.";
            list user-queue-weight {
              key "direction";
              max-elements  "2";
              description
                "Configure user queue weight.";
              ext:generated-by system {
                description "The instance is generated automatically.";
              }
              ext:operation-exclude create {
                description "The instances cannot be created.";
              }
              leaf direction {
                type qos-direction-type;
                description
                  "Direction.";
              }
              leaf weight {
                type uint8 {
                  range "1..63";
                }
                default "10";
                description
                  "SQ Weight.";
              }
            }
          }
          container user-queue-time-ranges {
            when "(../mode='time-range')";
            must "count(./user-queue-time-range[direction = 'inbound']/time-range-name)<=2 and count(./user-queue-time-range[direction = 'outbound']/time-range-name)<=2 and count(./user-queue-time-range[direction = 'all']/time-range-name)<=2";
            description
              "List of configure user queue time range.";
            list user-queue-time-range {
              must "(./direction='all' and not (../user-queue-time-range[direction='inbound']) and not(../user-queue-time-range[direction='outbound']) or (./direction!='all' and not(../user-queue-time-range[direction='all'])))";
              must "./service-template-name or ./adjust-on-card='disable'";
              key "direction time-range-name";
              max-elements  "4";
              description
                "Configure user queue time range.";
              leaf direction {
                type all-direction-type;
                description
                  "Direction.";
              }
              leaf time-range-name {
                type leafref {
                  path "/timerange:time-range/timerange:time-range-instances/timerange:time-range-instance/timerange:name";
                }
                description
                  "Time range name.";
              }
              leaf cir {
                type uint32 {
                  range "0 | 16..4294967294";
                }
                units "kbit/s";
                must "../pir>=../cir";
                mandatory true;
                description
                  "Committed information rate.";
              }
              leaf pir {
                type uint32 {
                  range "0 | 16..4294967294";
                }
                units "kbit/s";
                must "../pir>=../cir";
                mandatory true;
                description
                  "Peak information rate.";
              }
              leaf cbs {
                type uint32 {
                  range "1..4194304";
                }
                units "Byte";
                must "not(../pbs) or ../pbs>=../cbs";
                description
                  "Committed burst size.";
              }
              leaf pbs {
                type uint32 {
                  range "1..4194304";
                }
                units "Byte";
                must "not(../cbs) or ../pbs>=../cbs";
                description
                  "Peak burst size.";
              }
              leaf priority-level-id {
                type priority-level-type;
                /*must "../pir or ../pir-percent";*/
                default "low";
                description
                  "PIR priority.";
              }
              leaf flow-queue-name {
                type leafref {
                  path "../../../../../flow-queues/flow-queue/name";
                }
                must "../../../../../flow-queues/flow-queue[name=current()]/mode='normal'";
                description
                  "Flow queue name.";
              }
              leaf flow-mapping-name {
                type leafref {
                  path "../../../../../flow-mappings/flow-mapping/name";
                }
                description
                  "Flow mapping name.";
              }
              leaf user-group-queue-name {
                type leafref {
                  path "../../../../../user-group-queues/user-group-queue/name";
                }
                must "(../../../../../user-group-queues/user-group-queue[name=current()]/mode!='priority' and ../direction='inbound') or (../direction!='inbound')";
                description
                  "User group queue name.";
              }
              leaf service-template-name {
                type leafref {
                  path "../../../../../service-templates/service-template/name";
                }
                description
                  "Service template name.";
              }
              leaf adjust-on-card {
                type adjust-on-card-type;
                default "disable";
                description
                  "Adjust on card flag.";
              }
            }
          }
          container cars {
            when "../mode='normal' or ../mode='8cos-enhance'";
            description
              "List of configure CAR action.";
            list car {
              must "(./direction='all' and not(../car[direction='inbound']) and not(../car[direction='outbound'])) or (./direction!='all' and not(../car[direction='all']))";
              must "(./cir-value and ./cbs) or not(./cir-value)";              
              key "type direction";
              description
                "Configure CAR action.";
              leaf type {
                type qos-car-type;
                description
                  "Type of a CAR action.";
              }
              leaf direction {
                type car-direction-type;
                description
                  "Direction of a CAR action.";
              }
              choice cir-parameters {
                mandatory true;
                description
                  "Specify cir parameters.";
                case cir {
                  description
                    "Specify cir parameters choice case as cir value.";
                  leaf cir-value {
                    type uint32 {
                      range "0..4294967295";
                    }
                    units "kbit/s";
                    must "../cbs and (not(../pir-value) or ../pir-value>=../cir-value)";
                    mandatory true;
                    description
                      "Committed information rate.";
                  }
                  leaf pir-value {
                    type uint32 {
                      range "1..4294967295";
                    }
                    units "kbit/s";
                    must "../pir-value>=../cir-value";
                    description
                      "Peak information rate.";
                  }
                }
                case cir-percentage {
                  description
                    "Specify cir parameters choice case as cir percentage value.";
                  leaf cir-percent {
                    when "../type='car'";
                    type uint8 {
                      range "0..100";
                    }
                    units "%";
                    must "not(../pir-percent) or ../pir-percent>=../cir-percent";
                    mandatory true;
                    description
                      "Committed information rate percent.";
                  }
                  leaf pir-percent {
                    when "../type='car'";
                    type uint8 {
                      range "0..100";
                    }
                    units "%";
                    must "../pir-percent>=../cir-percent";
                    description
                      "Peak information rate percent.";
                  }
                }
              }
              leaf cbs {
                type uint32 {
                  range "0..4294967295";
                }
                units "Byte";
                description
                  "Committed burst size.";
              }
              leaf pbs {
                type uint32 {
                  range "0..4294967295";
                }
                units "Byte";
                must "../cbs";
                description
                  "Peak burst size.";
              }
              leaf green-action {
                type color-action-type;
                mandatory true;
                description
                  "Action performed to the green packets.";
              }
              leaf green-service-class {
                when "../green-action='pass'";
                type qos-service-class;
                description
                  "Service class marked to the green packets.";
              }
              leaf green-color {
                when "../green-service-class";
                type qos-color;
                mandatory true;
                description
                  "Color marked to the green packets.";
              }
              leaf yellow-action {
                type color-action-type;
                description
                  "Action performed to the yellow packets.";
              }
              leaf yellow-service-class {
                when "../yellow-action='pass'";
                type qos-service-class;
                description
                  "Service class marked to the yellow packets.";
              }
              leaf yellow-color {
                when "../yellow-service-class";
                type qos-color;
                mandatory true;
                description
                  "Color marked to the yellow packets.";
              }
              leaf red-action {
                type color-action-type;
                mandatory true;
                description
                  "Action performed to the red packets.";
              }
              leaf red-service-class {
                when "../red-action='pass'";
                type qos-service-class;
                description
                  "Service class marked to the red packets.";
              }
              leaf red-color {
                when "../red-service-class";
                type qos-color;
                mandatory true;
                description
                  "Color marked to the red packets.";
              }
              leaf color-aware {
                type color-aware-type;
                description
                  "Color Aware.";
              }
            }
          }
          container profile-cars {
            description
              "List of configure CAR action.";
            list profile-car {
              must "(not(./yellow-action) and ./pbs=0) or (./yellow-action and ./pbs>0)";
              key "type direction";
              description
                "Configure CAR action.";
              leaf type {
                type profile-car-type;
                description
                  "Type of a CAR action.";
              }
              leaf direction {
                type profile-car-direction-type;
                description
                  "Direction of a CAR action.";
              }
              leaf cir-value {
                type uint32 {
                  range "0..4294967295";
                }
                units "kbit/s";
                must "../pir-value>=../cir-value";
                mandatory true;
                description
                  "Committed information rate.";
              }
              leaf pir-value {
                type uint32 {
                  range "0..4294967295";
                }
                units "kbit/s";
                must "../pir-value>=../cir-value";
                mandatory true;
                description
                  "Peak information rate.";
              }
              leaf cbs {
                type uint32 {
                  range "0..4294967295";
                }
                units "Byte";
                mandatory true;
                description
                  "Committed burst size.";
              }
              leaf pbs {
                type uint32 {
                  range "0..4294967295";
                }
                units "Byte";
                mandatory true;
                description
                  "Peak burst size.";
              }
              leaf priority-aware {
                when "../../../mode!='8cos-enhance'";
                type priority-aware-type;
                description
                  "Priority aware.";
              }
              leaf priority-template-name {
                when "../priority-aware";
                type leafref {
                  path "../../../../../priority-templates/priority-template/name";
                }
                default "default";
                description
                  "Priority template name.";
              }
              leaf adjust-value {
                type int32 {
                  range "-32..31";
                }
                default "4";
                description
                  "Adjust value.";
              }
              leaf green-action {
                type color-action-type;
                mandatory true;
                description
                  "Action performed to the green packets.";
              }
              leaf green-service-class {
                when "../green-action='pass'";
                type qos-service-class;
                description
                  "Service class marked to the green packets.";
              }
              leaf green-color {
                when "../green-service-class";
                type qos-color;
                mandatory true;
                description
                  "Color marked to the green packets.";
              }
              leaf yellow-action {
                type color-action-type;
                description
                  "Action performed to the yellow packets.";
              }
              leaf yellow-service-class {
                when "../yellow-action='pass'";
                type qos-service-class;
                description
                  "Service class marked to the yellow packets.";
              }
              leaf yellow-color {
                when "../yellow-service-class";
                type qos-color;
                mandatory true;
                description
                  "Color marked to the yellow packets.";
              }
              leaf red-action {
                type color-action-type;
                mandatory true;
                description
                  "Action performed to the red packets.";
              }
              leaf red-service-class {
                when "../red-action='pass'";
                type qos-service-class;
                description
                  "Service class marked to the red packets.";
              }
              leaf red-color {
                when "../red-service-class";
                type qos-color;
                mandatory true;
                description
                  "Color marked to the red packets.";
              }
              leaf color-aware {
                type color-aware-type;
                description
                  "Color Aware.";
              }
            }
          }
          container suppressions {
            when "../mode='normal' or ../mode='8cos-enhance'";
            description
              "List of configure suppression action.";
            list suppression {
              key "type direction";
              description
                "Configure suppression action.";
              leaf type {
                type qos-suppression-type;
                description
                  "Type of a suppression action.";
              }
              leaf direction {
                type suppression-direction-type;
                description
                  "Direction.";
              }
              leaf cir {
                type uint32 {
                  range "0..4294967295";
                }
                units "kbit/s";
                mandatory true;
                description
                  "Committed information rate.";
              }
              leaf cbs {
                type uint32 {
                  range "0..4294967295";
                }
                units "Byte";
                mandatory true;
                description
                  "Committed burst size.";
              }
              leaf adjust-value {
                type int32 {
                  range "-32..31";
                }
                default "4";
                description
                  "Adjust value.";
              }
            }
          }
          container mpls-tunnel-flow-queues {
            description
            "Configure MPLS tunnel flow queue.";
            container mpls-tunnel-flow-queue {
              when "../../mode='normal'";
              presence "Create mpls-tunnel-flow-queue.";
              description
                "Enable/disable MPLS tunnel flow queue.";
              leaf flow-queue-name {
                type leafref {
                  path "../../../../../flow-queues/flow-queue/name";
                }
                must "../../../../../flow-queues/flow-queue[name=current()]/mode='normal'";
                mandatory true;
                description
                  "Flow queue.";
              }
              leaf flow-mapping-name {
                type leafref {
                  path "../../../../../flow-mappings/flow-mapping/name";
                }
                description
                  "Flow mapping.";
              }
              leaf user-group-queue-name {
                type leafref {
                  path "../../../../../user-group-queues/user-group-queue/name";
                }
                must "../../../../../user-group-queues/user-group-queue[name=current()]/mode='normal'";
                description
                  "User group queue.";
              }
              leaf service-template-name {
                type leafref {
                  path "../../../../../service-templates/service-template/name";
                }
                description
                  "Service template.";
              }
            }
          }
          container eight-cos-mode-queues {
            when "../mode='8cos-enhance'";
            description
              "List of configure eight cos mode queue.";
            list eight-cos-mode-queue {
              must "(direction='all' and not(../eight-cos-mode-queue[direction='inbound']) and not(../eight-cos-mode-queue[direction='outbound']) or (direction!='all' and not(../eight-cos-mode-queue[direction='all'])))";
              key "direction";
              max-elements "2";
              description
                "Configure eight cos mode queue.";
              leaf direction {
                type all-direction-type;
                description
                  "Direction.";
              }
              leaf user-queue-name {
                type leafref {
                  path "../../../../../user-queue-templates/user-queue-template/name";
                }
                mandatory true;
                description
                  "User queue.";
              }
              leaf flow-queue-name {
                type leafref {
                  path "../../../../../flow-queues/flow-queue/name";
                }
                must "../../../../../flow-queues/flow-queue[name=current()]/mode='8cos-enhance'";
                description
                  "Flow queue.";
              }
              leaf user-group-queue-name {
                type leafref {
                  path "../../../../../user-group-queues/user-group-queue/name";
                }
                must "not(../../../../../user-group-queues/user-group-queue[name=current()]/mode='priority' and ../direction='inbound')";
                description
                  "User group queue.";
              }
            }
          }
          container traffic-behavior-user-queues {
            description
              "List of configure traffic-behavior-user queue.";
            list traffic-behavior-user-queue {
              key "name";
              max-elements 256;
              description
                "Configure traffic-behavior-user queue.";
              leaf name {
                type string {
                  length "1..31";
                }
                description
                  "User queue name.";
              }
              leaf scheduler-mode {
                type qos:user-schedule-mode;
                mandatory true;
                description
                  "Scheduling strategy of user queue.";
              }
              leaf weight {
                when "../scheduler-mode='drr'";
                type uint8 {
                  range "1..100";
                }
                description
                  "Weight of drr scheduling strategy.";
              }
              choice config-type {
                mandatory true;
                description
                  "Specify config type.";
                case cir-mode {
                  description
                    "Specify config type choice case as cir mode.";
                  leaf cir {
                    type uint32 {
                      range "64..100000000";
                    }
                    units "kbit/s";
                    must "../pir>=../cir";
                    description
                      "Committed information rate.";
                  }
                  leaf pir {
                    type uint32 {
                      range "8..100000000";
                    }
                    units "kbit/s";
                    must "../pir>=../cir";
                    description
                      "Peak information rate.";
                  }
                }
                case cir-percent-mode {
                  description
                    "Specify config type choice case as cir percentage mode.";
                  leaf cir-percent {
                    type uint8 {
                      range "1..100";
                    }
                    units "%";
                    must "../pir-percent>=../cir-percent";
                    description
                      "Cir percentage.";
                  }
                  leaf pir-percent {
                    type uint8 {
                      range "1..100";
                    }
                    units "%";
                    must "../pir-percent>=../cir-percent";
                    description
                      "Pir percentage.";
                  }
                }
              }
              leaf cbs {
                type uint32 {
                  range "0..4194304";
                }
                units "Byte";
                description
                  "Committed burst size.";
              }
              leaf pbs {
                type uint32 {
                  range "0..4194304";
                }
                units "Byte";
                description
                  "Peak burst size.";
              }
            }
          }
        }
      }
      container flow-mappings {
        description
          "List of configure flow mapping.";
        list flow-mapping {
          key "name";
          max-elements  "15";
          description
            "Configure flow mapping. This object has default configurations.";
          leaf name {
            type template-name;
            description
              "Flow mapping name.";
          }
          container parameters {
            description
              "List of configure parameters of flow mapping.";
            list parameter {
              key "flow-queue-service-class";
              max-elements  "8";
              description
                "Configure parameters of flow mapping.";
              ext:generated-by system {
                description "The instances are created and deleted following the flow mapping template.";
              }
              ext:operation-exclude create {
                description "The instances cannot be created.";
              }
              leaf flow-queue-service-class {
                type qos-service-class;
                description
                  "Flow queue service class.";
              }
              leaf port-queue-service-class {
                type qos-service-class;
                mandatory true;
                description
                  "Port queue service class.";
              }
            }
          }
        }
      }
      container queue-4cos-mappings {
        description
          "List of configure queue 4cos mapping.";
        list queue-4cos-mapping{
          key "name";
          max-elements  "8";
          description
            "Configure queue 4cos mapping. This object has default configurations.";
          leaf name {
            type template-name;
            description
              "Queue 4cos mapping name.";
          }
          container parameters {
            description
              "List of configure parameters of queue 4cos mapping.";
            list parameter {
              key "flow-queue-service-class";
              max-elements  "8";
              description
                "Configure parameters of queue 4cos mapping.";
              ext:generated-by system {
                description "The instances are created and deleted following the 4cos mapping template.";
              }
              ext:operation-exclude create {
                description "The instances cannot be created.";
              }
              leaf flow-queue-service-class {
                type qos-service-class;
                description
                  "Flow queue service class.";
              }
              leaf four-queue-service-class {
                type qos-cos-value;
                mandatory true;
                description
                  "Queue 4cos service class.";
              }
            }
          }
        }
      }
      container user-group-queues {
        description
          "List of configure user group queue.";
        list user-group-queue {
          key "name";
          max-elements  "8191";
          description
            "Configure user group queue.";
          leaf name {
            type template-name;
            description
              "User group queue name.";
          }
          leaf mode {
            type gq-template-type;
            mandatory true;
            description
              "User group queue mode. This node does not support modification.";
            ext:operation-exclude update {
              description "After the user group queue template is created, the node cannot be modified.";
            }
          }
          leaf mode-template {
            when "../mode='normal'";
            type mode-template-status;
            description
              "User group queue mode template status. After the user-group-queue is applied, the attribute of this node cannot be changed.";
          }
          container shapings {
            when "../mode='normal'";
            description
              "List of configure user group queue shaping.";
            list shaping {
              key "direction";
              max-elements  "2";
              description
                "Configure user group queue shaping.";
              leaf direction {
                type qos-direction-type;
                description
                  "Direction.";
              }
              leaf pir {
                type uint32 {
                  range "66..4294967294";
                }
                units "kbit/s";
                mandatory true;
                description
                  "Peak information rate.";
              }
              leaf pbs {
                type uint32 {
                  range "64..2097152";
                }
                units "Byte";
                default "524288";
                description
                  "Peak burst size.";
              }
            }
          }
          container shaping-priortys {
            when "../mode='priority'";
            description
              "List of configure priority user group queue shaping.";
            list shaping-priorty {
              key "priority direction";
              max-elements  "4";
              description
                "Configure priority user group queue shaping.";
              leaf priority {
                type priority-shaping-type;
                description
                  "Priority.";
              }
              leaf direction {
                type out-direction-type;
                description
                  "Direction.";
              }
              leaf shaping-value {
                type uint32 {
                  range "66..4294967294";
                }
                units "kbit/s";
                mandatory true;
                description
                  "Shaping value.";
              }
              leaf pbs {
                type uint32 {
                  range "64..2097152";
                }
                units "Byte";
                default "524288";
                description
                  "Peak burst size.";
              }
            }
          }
          container cir-pirs {
            when "../mode='normal'";
            description
              "List of configure user group queue cir pir.";
            list cir-pir {
              key "direction";
              description
                "Configure user group queue cir pir.";
              leaf direction {
                type out-direction-type;
                description
                  "Direction.";
              }
              leaf cir {
                type uint32 {
                  range "66..4294967294";
                }
                units "kbit/s";
                mandatory true;
                description
                  "Committed information rate.";
              }
              leaf cbs {
                type uint32 {
                  range "64..2097152";
                }
                units "Byte";
                mandatory true;
                description
                  "Committed burst size.";
              }
              leaf pir {
                type uint32 {
                  range "66..4294967294";
                }
                units "kbit/s";
                must "(../pir>=../cir)";
                mandatory true;
                description
                  "Peak information rate. During creation, the pir is generated based on the configured cir.";
              }
              leaf pbs {
                type uint32 {
                  range "64..2097152";
                }
                units "Byte";
                mandatory true;
                description
                  "Peak burst size.";
              }
            }
          }
          container weights {
            when "../mode='normal'";
            description
              "List of configure weight.";
            list weight { 
              key "direction";
              description
                "Configure weight.";
              ext:generated-by system {
                description "The instances are created and deleted following the user group queue template.";
              }
              ext:operation-exclude create {
                description "The instances cannot be created.";
              }
              leaf direction {
                type out-direction-type;
                description
                  "Direction.";
              }
              leaf weight-value {
                type uint8 {
                  range "1..63";
                }
                mandatory true;
                description
                 "Weight value.";
              }
            }
          }
          container user-group-queue-statisticss {
            config false;
            description
              "List of user group queue statistics.";
            list user-group-queue-statistics {
              key "slot-id direction service-class";
              description
                "User group queue statistics.";
              leaf slot-id {
                type slot-id;
                description
                  "Slot id.";
              }
              leaf direction {
                type qos-gq-direction-type;
                description
                  "Direction.";
              }
              leaf service-class {
                type qos-service-class-filter;
                description
                  "Class of service.";
              } 
              leaf group-name {
                type group-name;
                description
                  "Group name.";
              }
              leaf pass-packets {
                type uint64;
                units "packet";
                description
                  "Number of passed packets.";
              }
              leaf pass-bytes {
                type uint64;
                units "Byte";
                description
                  "Number of passed bytes.";
              }
              leaf pass-packet-rate {
                type uint64;
                units "pps";
                description
                  "Rate of the packets passed during the latest 30 seconds.";
              }
              leaf pass-byte-rate {
                type uint64;
                units "Byte/s";
                description
                  "Rate of the bytes passed during the latest 30 seconds.";
              }
              leaf drop-packets {
                type uint64;
                units "packet";
                description
                  "Number of dropped packets.";
              }
              leaf drop-bytes {
                type uint64;
                units "Byte";
                description
                  "Number of dropped bytes.";
              }
              leaf drop-packet-rate {
                type uint64;
                units "pps";
                description
                  "Number of dropped bytes.";
              }
              leaf drop-byte-rate {
                type uint64;
                units "Byte/s";
                description
                  "Rate of the bytes dropped during the latest 30 seconds.";
              }
            }
          }
        }
      }
      container service-templates {
        description
          "List of configure service template. Some products have default templates. The default templates cannot be modified or deleted. The parameters of some default templates can be modified.";
        list service-template {
          key "name";
          description
            "Configure service template.";
          leaf name {
            type template-name;
            description
              "Service template name.";
          }
          leaf slot-id {
            type slot-id;
            description
              "Slot id.";
          }
          container service-lengths {
            description
              "List of configure length of network header.";
            list service-length {
              key "direction";
              max-elements  "2";
              description
                "Configure length of network header. This node cannot be deleted.";
              ext:generated-by "system" {
                description
                  "The template is generated automatically.";
              }
              ext:operation-exclude create {
                description
                  "The template cannot be created.";
              }
              leaf direction {
                type qos-direction-type;
                description
                  "Direction.";
              }
              leaf value {
                type int32 {
                  range "-63..63";
                }
                units "Byte";
                mandatory true;
                description
                  "Length value of network header.";
              }
            }
          }
          container service-length-on-etm {
            description
              "Configure length of network header on ETM.";
            leaf value {
              type int32 {
                range "-63..63";
              }
              units "Byte";
              description
                "Length value of network header on ETM.";
            }
          }
        }
      }
      container port-queue-templates {
        description
          "List of configure port queue template.";
        list port-queue-template {
          key "name";
          max-elements  "1024";
          description
            "Configure port queue template.";
          leaf name {
            type template-name;
            description
              "Port queue template name.";
          }
          container queues {
            description
              "List of configure port queue template parameter.";
            list queue {
              key "service-class";
              max-elements  "8";
              description
                "Configure port queue template parameter.";
              ext:generated-by system {
                description "The instances are created and deleted following the port-queue template.";
              }
              ext:operation-exclude create {
                description "The instances cannot be created.";
              }
              leaf service-class {
                type qos-service-class;
                description
                  "Service class.";
              }
              leaf port-wred-name {
                type leafref {
                  path "../../../../../../wred-template/port-wreds/port-wred/name";
                }
                description
                  "Port wred name.";
              }
              choice config-type {
                mandatory true;
                description
                  "Specify config type.";
                case shaping-mode {
                  description
                    "Specify config type choice case as shaping mode.";
                  leaf queue-schedule-mode {
                    type queue-schedule-mode;
                    mandatory true;
                    description
                      "Schedule Mode.";
                  }
                  leaf weight {
                    when "../queue-schedule-mode='wfq'";
                    type uint8 {
                      range "1..100";
                    }
                    mandatory true;
                    description
                      "Weight of wfq scheduling strategy.";
                  }
                  leaf pbs {
                    when "../shaping-value or ../shaping-percentage";
                    type uint32 {
                      range "1..10000000";
                    }
                    units "Byte";
                    description
                      "Peak burst size.";
                  }
                  leaf low-latency {
                    when "../queue-schedule-mode='pq'";
                    type queue-low-latency;
                    description
                      "Low latency. Some boards do not support this object.";
                  }
                  choice shaping-parameters {
                    description
                      "Specify shaping parameters.";
                    case shaping {
                      description
                        "Specify shaping parameters choice case as shaping value.";
                      leaf shaping-value {
                        type uint32 {
                          range "0..4294967294";
                        }
                        units "Mbit/s";
                        description
                          "Shaping value.";
                      }
                    }
                    case shaping-percent {
                      description
                        "Specify shaping parameters choice case as shaping percentage value.";
                      leaf shaping-percentage {
                        type uint8 {
                          range "0..100";
                        }
                        units "%";
                        description
                          "Shaping percentage.";
                      }
                    }
                  }
                }
                case cir-mode {
                  description
                    "Specify config type choice case as cir mode. Some boards do not support this object.";
                  leaf cir-schedule-mode {
                    type queue-cir-schedule-mode;
                    mandatory true;
                    description
                      "Scheduling strategy of cir.";
                  }
                  leaf pir-schedule-mode {
                    type queue-schedule-mode;
                    mandatory true;
                    description
                      "Scheduling strategy of pir.";
                  }
                  leaf pir-weight {
                    when "../pir-schedule-mode='wfq'";
                    type uint8 {
                      range "1..100";
                    }
                    mandatory true;
                    description
                      "Weight of wfq scheduling strategy.";
                  }
                  leaf cbs {
                    type uint32 {
                      range "1..10000000";
                    }
                    units "Byte";
                    must "../pir-pbs>=../cbs or not(../pir-pbs)";
                    description
                      "Committed burst size.";
                  }
                  leaf pir-pbs {
                   type uint32 {
                     range "1..10000000";
                   }
                   units "Byte";
                   must "../pir-pbs>=../cbs or not(../cbs)";
                   description
                     "Peak burst size.";
                  }
                  choice cir-parameters {
                   mandatory true;
                   description
                     "Specify cir parameters.";
                   case cir {
                     description
                     "Specify cir parameters choice case as cir value.";
                     leaf cir-value {
                       type uint32 {
                         range "0..4294967294";
                       }
                       units "Mbit/s";
                       must "../pir-value>=../cir-value";
                       mandatory true;
                       description
                         "Specify cir value.";
                     }
                     leaf pir-value {
                       type uint32 {
                         range "0..4294967294";
                       }
                       units "Mbit/s";
                       must "../pir-value>=../cir-value";
                       mandatory true;
                       description
                         "Peak information rate.";
                       }
                    }
                    case cir-percent {
                      description
                        "Specify cir parameters choice case as cir percentage value.";
                      leaf cir-percentage {
                        type uint8 {
                          range "0..100";
                        }
                        units "%";
                        must "../pir-percentage>=../cir-percentage";
                        mandatory true;
                        description
                          "Cir percentage.";
                      }
                      leaf pir-percentage {
                        type uint8 {
                          range "0..100";
                        }
                        units "%";
                        must "../pir-percentage>=../cir-percentage";
                        mandatory true;
                        description
                          "Pir percentage.";
                      }
                    }
                  }
                }
              }
            }
          }
          container queue-states {
            config false;
            description
              "List of operational state of port queue template parameter.";
            list queue-state {
              key "service-class";
              description
                "Operational state of port queue template parameter.";
              leaf service-class {
                type qos-service-class;
                description
                  "Service class.";
              }
              leaf port-wred-name {
                type leafref {
                  path "../../../../../../wred-template/port-wreds/port-wred/name";
                }
                description
                  "Port wred name.";
              }
              choice config-type {
                description
                  "Specify config type.";
                case shaping-mode {
                  description
                    "Specify config type choice case as shaping mode.";
                  leaf queue-schedule-mode {
                    type queue-schedule-mode;
                    description
                      "Schedule Mode.";
                  }
                  leaf weight {
                    when "../queue-schedule-mode='wfq'";
                    type uint8 {
                      range "1..100";
                    }
                    description
                      "Weight of wfq scheduling strategy.";
                  }
                  leaf pbs {
                    when "../shaping-value or ../shaping-percentage";
                    type uint32 {
                      range "1..10000000";
                    }
                    units "Byte";
                    description
                      "Peak burst size.";
                  }
                  leaf low-latency {
                    when "../queue-schedule-mode='pq'";
                    type queue-low-latency;
                    description
                      "Low latency. Some boards do not support this object.";
                  }
                  choice shaping-parameters {
                    description
                      "Specify shaping parameters.";
                    case shaping {
                      description
                        "Specify shaping parameters choice case as shaping value.";
                      leaf shaping-value {
                        type uint32 {
                          range "0..4294967294";
                        }
                        units "Mbit/s";
                        description
                          "Shaping value.";
                      }
                    }
                    case shaping-percent {
                      description
                        "Specify shaping parameters choice case as shaping percentage value.";
                      leaf shaping-percentage {
                        type uint8 {
                          range "0..100";
                        }
                        units "%";
                        description
                          "Shaping percentage.";
                      }
                    }
                  }
                }
                case cir-mode {
                  description
                    "Specify config type choice case as cir mode. Some boards do not support this object.";
                  leaf cir-schedule-mode {
                    type queue-cir-schedule-mode;
                    description
                      "Scheduling strategy of cir.";
                  }
                  leaf pir-schedule-mode {
                    type queue-schedule-mode;
                    description
                      "Scheduling strategy of pir.";
                  }
                  leaf pir-weight {
                    when "../pir-schedule-mode='wfq'";
                    type uint8 {
                      range "1..100";
                    }
                    description
                      "Weight of wfq scheduling strategy.";
                  }
                  leaf cbs {
                    type uint32 {
                      range "1..10000000";
                    }
                    units "Byte";
                    description
                      "Committed burst size.";
                  }
                  leaf pir-pbs {
                   type uint32 {
                     range "1..10000000";
                   }
                   units "Byte";
                   description
                     "Peak burst size.";
                  }
                  choice cir-parameters {
                   description
                     "Specify cir parameters.";
                   case cir {
                     description
                     "Specify cir parameters choice case as cir value.";
                     leaf cir-value {
                       type uint32 {
                         range "0..4294967294";
                       }
                       units "Mbit/s";
                       description
                         "Specify cir value.";
                     }
                     leaf pir-value {
                       type uint32 {
                         range "0..4294967294";
                       }
                       units "Mbit/s";
                       description
                         "Peak information rate.";
                       }
                    }
                    case cir-percent {
                      description
                        "Specify cir parameters choice case as cir percentage value.";
                      leaf cir-percentage {
                        type uint8 {
                          range "0..100";
                        }
                        units "%";
                        description
                          "Cir percentage.";
                      }
                      leaf pir-percentage {
                        type uint8 {
                          range "0..100";
                        }
                        units "%";
                        description
                          "Pir percentage.";
                      }
                    }
                  }
                }
              }
            }
          }
          container share-shapes {
            description
              "Configure port queue share shaping.";
            container share-shape {
              must "not(not(./af1='true') and not(./af2='true') and not(./af3='true') and not(./af4='true') and not(./ef='true') and not(./cs6='true') and not(./cs7='true'))";
              must "not(not(./be='true') and not(./af2='true') and not(./af3='true') and not(./af4='true') and not(./ef='true') and not(./cs6='true') and not(./cs7='true'))";
              must "not(not(./be='true') and not(./af1='true') and not(./af3='true') and not(./af4='true') and not(./ef='true') and not(./cs6='true') and not(./cs7='true'))";
              must "not(not(./be='true') and not(./af1='true') and not(./af2='true') and not(./af4='true') and not(./ef='true') and not(./cs6='true') and not(./cs7='true'))";
              must "not(not(./be='true') and not(./af1='true') and not(./af2='true') and not(./af3='true') and not(./ef='true') and not(./cs6='true') and not(./cs7='true'))";
              must "not(not(./be='true') and not(./af1='true') and not(./af2='true') and not(./af3='true') and not(./af4='true') and not(./cs6='true') and not(./cs7='true'))";
              must "not(not(./be='true') and not(./af1='true') and not(./af2='true') and not(./af3='true') and not(./af4='true') and not(./ef='true') and not(./cs7='true'))";
              must "not(not(./be='true') and not(./af1='true') and not(./af2='true') and not(./af3='true') and not(./af4='true') and not(./ef='true') and not(./cs6='true'))";
              presence "Create share-shape.";
              description
                "Enable/disable port queue share shaping. The configuration involves at least two queues, and the scheduling mode of the queues must be the same.";
              leaf be {
                type be-type;
                must "not(not(../../../queues/queue[service-class='be']/queue-schedule-mode) and ../be='true')";
                must "../af1='false' or ../be='false' or ../../../queues/queue[service-class='be']/queue-schedule-mode=../../../queues/queue[service-class='af1']/queue-schedule-mode";
                must "../af2='false' or ../be='false' or ../../../queues/queue[service-class='be']/queue-schedule-mode=../../../queues/queue[service-class='af2']/queue-schedule-mode";
                must "../af3='false' or ../be='false' or ../../../queues/queue[service-class='be']/queue-schedule-mode=../../../queues/queue[service-class='af3']/queue-schedule-mode";
                must "../af4='false' or ../be='false' or ../../../queues/queue[service-class='be']/queue-schedule-mode=../../../queues/queue[service-class='af4']/queue-schedule-mode";
                must "../ef='false' or ../be='false' or ../../../queues/queue[service-class='be']/queue-schedule-mode=../../../queues/queue[service-class='ef']/queue-schedule-mode";
                must "../cs6='false' or ../be='false' or ../../../queues/queue[service-class='be']/queue-schedule-mode=../../../queues/queue[service-class='cs6']/queue-schedule-mode";
                must "../cs7='false' or ../be='false' or ../../../queues/queue[service-class='be']/queue-schedule-mode=../../../queues/queue[service-class='cs7']/queue-schedule-mode";
                default "false";
                description
                  "BE.";
                
              }
              leaf af1 {
                type af1-type;
                must "not(not(../../../queues/queue[service-class='af1']/queue-schedule-mode) and ../af1='true')";
                must "../af2='false' or ../af1='false' or ../../../queues/queue[service-class='af1']/queue-schedule-mode=../../../queues/queue[service-class='af2']/queue-schedule-mode";
                must "../af3='false' or ../af1='false' or ../../../queues/queue[service-class='af1']/queue-schedule-mode=../../../queues/queue[service-class='af3']/queue-schedule-mode";
                must "../af4='false' or ../af1='false' or ../../../queues/queue[service-class='af1']/queue-schedule-mode=../../../queues/queue[service-class='af4']/queue-schedule-mode";
                must "../ef='false' or ../af1='false' or ../../../queues/queue[service-class='af1']/queue-schedule-mode=../../../queues/queue[service-class='ef']/queue-schedule-mode";
                must "../cs6='false' or ../af1='false' or ../../../queues/queue[service-class='af1']/queue-schedule-mode=../../../queues/queue[service-class='cs6']/queue-schedule-mode";
                must "../cs7='false' or ../af1='false' or ../../../queues/queue[service-class='af1']/queue-schedule-mode=../../../queues/queue[service-class='cs7']/queue-schedule-mode";
                default "false";
                description
                  "AF1.";
                
              }
              leaf af2 {
                type af2-type;
                must "not(not(../../../queues/queue[service-class='af2']/queue-schedule-mode) and ../af2='true')";
                must "../af3='false' or ../af2='false' or ../../../queues/queue[service-class='af2']/queue-schedule-mode=../../../queues/queue[service-class='af3']/queue-schedule-mode";
                must "../af4='false' or ../af2='false' or ../../../queues/queue[service-class='af2']/queue-schedule-mode=../../../queues/queue[service-class='af4']/queue-schedule-mode";
                must "../ef='false' or ../af2='false' or ../../../queues/queue[service-class='af2']/queue-schedule-mode=../../../queues/queue[service-class='ef']/queue-schedule-mode";
                must "../cs6='false' or ../af2='false' or ../../../queues/queue[service-class='af2']/queue-schedule-mode=../../../queues/queue[service-class='cs6']/queue-schedule-mode";
                must "../cs7='false' or ../af2='false' or ../../../queues/queue[service-class='af2']/queue-schedule-mode=../../../queues/queue[service-class='cs7']/queue-schedule-mode";
                default "false";
                description
                  "AF2.";
                
              }
              leaf af3 {
                type af3-type;
                must "not(not(../../../queues/queue[service-class='af3']/queue-schedule-mode) and ../af3='true')";
                must "../af4='false' or ../af3='false' or ../../../queues/queue[service-class='af3']/queue-schedule-mode=../../../queues/queue[service-class='af4']/queue-schedule-mode";
                must "../ef='false' or ../af3='false' or ../../../queues/queue[service-class='af3']/queue-schedule-mode=../../../queues/queue[service-class='ef']/queue-schedule-mode";
                must "../cs6='false' or ../af3='false' or ../../../queues/queue[service-class='af3']/queue-schedule-mode=../../../queues/queue[service-class='cs6']/queue-schedule-mode";
                must "../cs7='false' or ../af3='false' or ../../../queues/queue[service-class='af3']/queue-schedule-mode=../../../queues/queue[service-class='cs7']/queue-schedule-mode";
                default "false";
                description
                  "AF3.";
                
              }
              leaf af4 {
                type af4-type;
                must "not(not(../../../queues/queue[service-class='af4']/queue-schedule-mode) and ../af4='true')";
                must "../ef='false' or ../af4='false' or ../../../queues/queue[service-class='af4']/queue-schedule-mode=../../../queues/queue[service-class='ef']/queue-schedule-mode";
                must "../cs6='false' or ../af4='false' or ../../../queues/queue[service-class='af4']/queue-schedule-mode=../../../queues/queue[service-class='cs6']/queue-schedule-mode";
                must "../cs7='false' or ../af4='false' or ../../../queues/queue[service-class='af4']/queue-schedule-mode=../../../queues/queue[service-class='cs7']/queue-schedule-mode";
                default "false";
                description
                  "AF4.";
                
              }
              leaf ef {
                type ef-type;
                must "not(not(../../../queues/queue[service-class='ef']/queue-schedule-mode) and ../ef='true')";
                must "../cs6='false' or ../ef='false' or ../../../queues/queue[service-class='ef']/queue-schedule-mode=../../../queues/queue[service-class='cs6']/queue-schedule-mode";
                must "../cs7='false' or ../ef='false' or ../../../queues/queue[service-class='ef']/queue-schedule-mode=../../../queues/queue[service-class='cs7']/queue-schedule-mode";
                default "false";
                description
                  "EF.";
                
              }
              leaf cs6 {
                type cs6-type;
                must "not(not(../../../queues/queue[service-class='cs6']/queue-schedule-mode) and ../cs6='true')";
                must "../cs7='false' or ../cs6='false' or ../../../queues/queue[service-class='cs6']/queue-schedule-mode=../../../queues/queue[service-class='cs7']/queue-schedule-mode";
                default "false";
                description
                  "CS6.";
                
              }
              leaf cs7 {
                type cs7-type;
                must "not(not(../../../queues/queue[service-class='cs7']/queue-schedule-mode) and ../cs7='true')";
                default "false";
                description
                  "CS7.";
                
              }
              leaf queue-schedule-mode {
                type queue-schedule-mode;
                must "(../queue-schedule-mode='wfq' and ../weight) or (../queue-schedule-mode!='wfq' and not(../weight))";
                description
                  "Scheduling strategy of port queue.";
                
              }
              leaf weight {
                when "../queue-schedule-mode='wfq'";
                type uint8 {
                  range "1..100";
                }
                description
                  "Weight of wfq scheduling strategy.";
                
              }
              choice shaping-parameters {
                mandatory true;
                description
                  "Specify shaping parameters.";
                case shaping {
                  description
                    "Specify shaping parameters choice case as shaping value.";
                  leaf shaping-value {
                    when "../be='true' or ../af1='true' or ../af2='true' or ../af3='true' or ../af4='true' or ../ef='true' or ../cs6='true' or ../cs7='true'";
                    type uint32 {
                      range "1..4294967294";
                    }
                    units "kbit/s";
                    description
                      "Shaping value.";
                  }
                }
                case shaping-percent {
                  description
                    "Specify shaping parameters choice case as shaping percentage value.";
                  leaf shaping-percentage {
                    when "../be='true' or ../af1='true' or ../af2='true' or ../af3='true' or ../af4='true' or ../ef='true' or ../cs6='true' or ../cs7='true'";
                    type uint8 {
                      range "0..100";
                    }
                    units "%";
                    description
                      "Shaping percentage.";
                  }
                }
              }
              leaf pbs {
                type uint32 {
                  range "1..4194304";
                }
                units "Byte";
                description
                  "Peak burst size.";
                
              }
            }
          }
        }
      }
      container channel-profiles {
        description
          "List of configure channel Profile.";
        list channel-profile {
          key "name";
          max-elements "16";
          description
            "Configure channel Profile.";
          leaf name {
            type template-name;
            description
              "Name of qos channel profile.";
          }
          container channel-paras {
            description
              "List of configure channel parameters.";
            list channel-para {
              key "channel-id";
              description
                "Configure channel parameters.";
              leaf channel-id {
                type uint32 {
                  range "0..15";
                }
                description
                  "Channel id.";
              }
              leaf bandwidth {
                type uint32 {
                  range "1..100000";
                }
                units "kbit/s";
                mandatory true;
                description
                  "Channel bandwidth.";
              }
              leaf quantity {
                type uint32 {
                  range "1..16000";
                }
                must "../quantity mod 8 = 0";
                mandatory true;
                description
                  "Quantity of channel bandwidth.";
              }
            }
          }
        }
      }
      container buffer-policys {
        description
          "List of configure buffer policy template.";
        list buffer-policy {
          key "name";
          description
            "Configure buffer policy template.";
          leaf name {
            type template-name;
            description
              "Buffer-policy name.";
          }
          container buffer-mode-slots {
            description
              "List of configure buffer mode on slot.";
            list buffer-mode-slot {
              key "slot-id";
              description
                "Configure buffer mode on slot.";
              ext:generated-by system {
                description "The instances are created and deleted following the buffer policy template.";
              }
              ext:operation-exclude create {
                description "The instances cannot be created.";
              }
              leaf slot-id {
                type slot-id;
                description
                  "Slot ID.";
              }
              leaf buffer-mode-ge {
                type buffer-mode-type;
                ext:dynamic-default;
                description
                  "GE buffer mode.";
              }
              leaf buffer-mode-10ge {
                type buffer-mode-type;
                ext:dynamic-default;
                description
                  "10GE buffer mode.";
              }
            }
          }
          container buffer-mode-interfaces {
            description
              "List of configure buffer mode on interface.";
            list buffer-mode-interface {
              key "ifname";
              description
                "Configure buffer mode on interface.";
              ext:generated-by system {
                description "The instances are created and deleted following the buffer policy template.";
              }
              ext:operation-exclude create {
                description "The instances cannot be created.";
              }
              leaf ifname {
                type pub-type:if-name;
                description
                  "IfName.";
              }
              leaf buffer-mode {
                type buffer-mode-type;
                mandatory true;
                description
                  "Buffer mode.";
              }
            }
          }
        }
      }
      container qos-queue-templates {
        description
         "List of configure qos queue template.";
          list qos-queue-template {
            key "name";
            max-elements "1024";
            description
             "Configure qos queue template.";
            leaf name {
              type template-name;
              description
                "QoS queue template name.";
            }
            container queue-parameterss {
              must "./queue-parameters[service-class='be']/cir-percent + ./queue-parameters[service-class='af1']/cir-percent + ./queue-parameters[service-class='af2']/cir-percent + ./queue-parameters[service-class='af3']/cir-percent + ./queue-parameters[service-class='af4']/cir-percent + ./queue-parameters[service-class='ef']/cir-percent + ./queue-parameters[service-class='cs6']/cir-percent + ./queue-parameters[service-class='cs7']/cir-percent <= 100";
              description
                "List of configure parameters of qos queue template.";
              list queue-parameters {
                key "service-class";
                description
                "Configure parameters of qos queue template. This node cannot be deleted.";
                ext:generated-by system {
                  description "The instances are created and deleted following the qos queue template.";
                }
                ext:operation-exclude create {
                  description "The instances cannot be created.";
                }
                leaf service-class {
                  type qos-service-class;
                  description
                   "Service class.";
                }
                leaf cir-percent {
                 type uint8 {
                   range "0..100";
                }
                units "%";
                mandatory true;
                description
                 "CIR percentage.";
              }
              leaf pir-percent {
               type uint8 {
                 range "0..100";
               }
               units "%";
               must "(../pir-percent>=../cir-percent)";
               mandatory true;
               description
                 "PIR percentage.";
              }
              leaf priority {
                type queue-schedule-mode;
                mandatory true;
                description
                   "Priority.";
              }
            }
          }
        }
      }
      container sub-port-queues {
        description
          "List of configure sub port queue.";
        list sub-port-queue {
          key "name";
          max-elements "100";
          description
            "Configure sub port queue.";
          leaf name {
            type template-name;
            description
              "Sub port queue name.";
          }
          container shaping {
            presence "create shaping";
            description
              "Enable/disable rate of shaping.";
            leaf shaping-value {
              type uint32 {
                range "66..4294967294";
              }
              mandatory true;
              description
                "Rate of shaping.";
            }
            leaf pbs {
              type uint32 {
                range "64..2097152";
              }
              units "Byte";
              default "524288";
              description
                "Peak burst size.";
            }
          }
          container weight {
            description
              "Configure weight of WFQ scheduling strategy.";
            leaf weight-value {
              type uint8 {
                range "1..63";
              }
              default "10";
              description
                "Weight of WFQ scheduling strategy.";
            }
          }
        }
      }      
      container priority-templates {
        description
          "List of configure priority templates.";
        list priority-template {
          key "name";
          max-elements "9";
          description
            "Configure priority templates.";
          ext:generated-by system {
            ext:filter "name='default'";
            description "The instances whose name is 'default' are generated automatically.";
          }
          ext:operation-exclude create|update {
            ext:filter "name='default'";
            description "The instances whose name is 'default' cannot be created or updated.";
          }
          leaf name {
            type string {
              length "1..48";
            }
            description
              "Name of priority template.";
          }
          container queues {
            description
              "List of configure the mapping between the CoS, color, and CAR priority.";
            list queue {
              key "service-class color";
              description
                "Configure the mapping between the CoS, color, and CAR priority.";
              ext:generated-by system {
                description "The all instances are generated automatically.";
              }
              ext:operation-exclude create {
                description "The all instances cannot be created.";
              }
              leaf service-class {
                type qos-service-class;
                description
                  "Class of service.";
              }
              leaf color {
                type qos-color;
                description
                  "Color.";
              }
              leaf priority {
                type uint8 {
                  range "0..7";
                }
                mandatory true;
                description
                  "Priority.";
              }
            }
          }
        }
      }
      container user-queue-templates {
        description
          "List of configure user queue template.";
        list user-queue-template {
          key "name";
          max-elements "4095";
          description
            "Configure user queue template.";
          leaf name {
            type string {
              length "1..63";
            }
            description
              "User queue template name.";
          }
          leaf mode {
            type user-queue-template-type;
            mandatory true;
            description
              "User queue template mode.";
            ext:operation-exclude update {
              description "After the user queue template is created, the node cannot be modified.";
            }
          }
          container shaping {
            must "pbs>=cbs or not(pbs) or not(cbs)";
            must "peak-burst-time>=committed-burst-time or not(peak-burst-time) or not(committed-burst-time)";
            presence "create shaping";
            description
              "Configure shaping of user queue template.";
            choice parameter {
              mandatory true;
              description
                "Specify parameter.";
              case value-mode {
                description
                  "Specify shaping parameter choice case as value mode.";
                leaf pir-value {
                  type uint32 {
                    range "0 | 16..4294967294";
                  }
                  units "kbit/s";
                  must "../pir-value>=../cir-value or not(../cir-value)";
                  mandatory true;
                  description
                    "Peak information rate.";
                }
                leaf cir-value {
                  type uint32 {
                    range "0 | 16..4294967294";
                  }
                  units "kbit/s";
                  must "../pir-value>=../cir-value";
                  description
                    "Committed information rate.";
                }
              }
              case percent-mode {
                description
                  "Specify shaping parameter choice case as percent mode.";
                leaf pir-percent {
                  type uint8 {
                    range "0..100";
                  }
                  units "%";
                  must "../pir-percent>=../cir-percent or not(../cir-percent)";
                  mandatory true;
                  description
                    "Peak information rate percent.";
                }
                leaf cir-percent {
                  type uint8 {
                    range "0..100";
                  }
                  units "%";
                  must "../pir-percent>=../cir-percent";
                  description
                    "Committed information rate percent.";
                }
              }
            }
            choice burst-size {
              description
                "Specify burst size.";
              case value-mode {
                description
                  "Specify burst size choice case as value mode.";
                leaf pbs {
                  type uint32 {
                    range "1..4194304";
                  }
                  units "Byte";
                  description
                    "Peak burst size.";
                }
                leaf cbs {
                  when "../cir-value or ../cir-percent";
                  type uint32 {
                    range "1..4194304";
                  }
                  units "Byte";
                  description
                    "Committed burst size.";
                }
              }
              case time-mode {
                description
                  "Specify burst size choice case as time mode.";
                leaf peak-burst-time {
                  type uint16 {
                    range "1..5000";
                  }
                  units "ms";
                  description
                    "Peak burst time.";
                }
                leaf committed-burst-time {
                  when "../cir-value or ../cir-percent";
                  type uint16 {
                    range "1..5000";
                  }
                  units "ms";
                  description
                    "Committed burst time.";
                }
              }
            }
          }
          container service-template {
            description
              "Configure service template name.";
            leaf name {
              type leafref {
                path "../../../../service-templates/service-template/name";
              }
              description
                "Service template.";
            }
          }
          container priority-sheduler-modes {
            when "../mode='4-priority'";
            description
              "List of configure schedule parameters of four priority mode user queue.";
            list priority-sheduler-mode {
              key "priority";
              description
                "Configure schedule parameters of four priority mode user queue.";
              ext:generated-by system {
                description "The instances are created and deleted following the user queue template.";
              }
              ext:operation-exclude create {
                description "The instances cannot be created.";
              }
              leaf priority {
                type uint8 {
                  range "0..3";
                }
                description
                  "Priority.";
              }
              leaf schedule-mode {
                type priority-schedule-mode;
                mandatory true;
                description
                  "Schedule mode.";
              }
            }
          }
          container parent-priority-weights {
            when "../mode='4-priority'";
            description
              "List of configure weight parameters of four priority mode user queue.";
            list parent-priority-weight {
              key "priority";
              description
                "Configure weight parameters of four priority mode user queue.";
              ext:generated-by system {
                description "The instances are created and deleted following the user queue template.";
              }
              ext:operation-exclude create {
                description "The instances cannot be created.";
              }
              leaf priority {
                type uint8 {
                  range "0..3";
                }
                description
                  "Priority.";
              }
              leaf weight {
                type uint8 {
                  range "1..100";
                }
                mandatory true;
                description
                  "Weight.";
              }
            }
          }
          container parent-prioritys {
            when "../mode='4-priority'";
            description
              "List of configure parent priority of four priority mode user queue.";
            list parent-priority {
              must "cir-parent-priority <= pir-parent-priority";
              key "priority";
              description
                "Configure parent priority of four priority mode user queue.";
              ext:generated-by system {
                description "The instances are created and deleted following the user queue template.";
              }
              ext:operation-exclude create {
                description "The instances cannot be created.";
              }
              leaf priority {
                type uint8 {
                  range "0..3";
                }
                description
                  "Priority.";
              }
              leaf cir-parent-priority {
                type uint8 {
                  range "0..3";
                }
                mandatory true;
                description
                  "Cir parent priority.";
              }
              leaf pir-parent-priority {
                type uint8 {
                  range "0..3";
                }
                mandatory true;
                description
                  "Pir parent priority.";
              }
            }
          }
          container priority-shapings {
            when "../mode='4-priority'";
            description
              "List of configure shaping parameters of four priority mode user queue.";
            list priority-shaping {
              key "priority";
              description
                "Configure shaping parameters of four priority mode user queue.";
              leaf priority {
                type uint8 {
                  range "0..2";
                }
                description
                  "Priority.";
              }
              leaf pir {
                type uint32;
                units "kbit/s";
                mandatory true;
                description
                  "Peak information rate.";
              }
              leaf pbs {
                type uint32 {
                  range "1..max";
                }
                units "Byte";
                description
                  "Peak burst size.";
              }
            }
          }
        }
      }
      container schedule-profiles {
        description
          "List of configure schedule profile.";
        list schedule-profile {
          key "name";
          description
            "Configure schedule profile.";
          ext:generated-by system {
            description "The template is generated automatically.";
            ext:filter "name = 'default'";
          }
          leaf name {
            type string {
              length "1..31";
              pattern '[^"\s?]*';
            }
            description
              "Schedule profile name.";
          }
          container queue-schedules {
            description
              "List of queue schedule.";
            list queue-schedule {
             key "queue-index";
              max-elements 8;
              description
                "Configure queue schedule of schedule profile.";
              ext:generated-by system {
                description "The instances are created and deleted following the schedule profile.";
              }
              leaf queue-index {
                type uint8 {
                  range "0..7";
                }
                description
                  "Configure the index of the queue.";
              }
              leaf schedule-mode {
                type schedule-type;
                mandatory true;
                description
                  "Configure the mode of schedule.";
              }
              leaf weight {
                when "../schedule-mode='drr'";
                type uint8 {
                  range "1..100";
                }
                default "1";
                description
                  "Configure the DRR weight.";
              }
            }
          }
        }
      }
    }
    container classifier-template {
      description
        "Configure classifier template.";
      container diffserv-domains {
        description
          "List of configure diffserv domain.";
        list diffserv-domain {
          key "name";
          description
            "Configure diffserv domain.";
          ext:generated-by system {
            description "The template is generated automatically.";
            ext:filter "name = 'default'";
          }
          ext:operation-exclude create {
            description "The template cannot be created.";
            ext:filter "name = 'default'";
          }
          leaf name {
            type string {
              length "1..48";
              pattern '[^"\s?]*';
            }
            description
              "Name of a diffserv domain.";
          }
          container behavior-aggregations {
            description
              "List of configure mapping between the outbound and inbound priorities for inbound traffic.";
            list behavior-aggregation {
              key "type value";
              description
                "Configure mapping between the outbound and inbound priorities for inbound traffic.";
              ext:generated-by "system" {
                ext:filter "type!='ipv4-dscp' and type!='ipv6-dscp'";
                description
                  "The template is generated automatically.";
              }
              ext:operation-exclude create {
                ext:filter "type!='ipv4-dscp' and type!='ipv6-dscp'";
                description
                  "The template cannot be created.";
              }
              leaf type {
                ext:dynamic-default;
                type qos-ba-type;
                description
                  "Priority type.";
              }
              leaf value {
                ext:dynamic-default;
                type uint8 {
                  range "0..63";
                }
                must "(../type='ip-dscp' and ../value>=0 and ../value<=63) or (../value>=0 and ../value<=7)";
                description
                  "Priority value.";
              }
              leaf service-class {
                ext:dynamic-default;
                type qos-service-class;
                mandatory true;
                description
                  "Class of service.";
              }
              leaf color {
                ext:dynamic-default;
                type qos-color;
                mandatory true;
                description
                  "Color marked to the data flows after measurement.";
              }
            }
          }
          container per-hop-behaviors {
            description
              "List of configure mapping between the outbound and inbound priorities for outbound traffic.";
            list per-hop-behavior {
              key "type service-class color";
              description
                "Configure mapping between the outbound and inbound priorities for outbound traffic.";
              ext:generated-by "system" {
                ext:filter "type!='ipv4-dscp' and type!='ipv6-dscp'";
                description
                  "The template is generated automatically.";
              }
              ext:operation-exclude create {
                ext:filter "type!='ipv4-dscp' and type!='ipv6-dscp'";
                description
                  "The template cannot be created.";
              }
              leaf type {
                ext:dynamic-default;
                type qos-phb-type;
                description
                  "Priority type.";
              }
              leaf service-class {
                ext:dynamic-default;
                type qos-service-class;
                description
                  "Class of service.";
              }
              leaf color {
                ext:dynamic-default;
                type qos-color;
                description
                  "Color marked to the data flows after measurement.";
              }
              leaf value {
                ext:dynamic-default;
                type uint8 {
                  range "0..63";
                }
                must "(../type='ip-dscp' and ../value>=0 and ../value<=63) or (../value>=0 and ../value<=7)";
                mandatory true;
                description
                  "Priority value. When Priority type is DSCP priority the Priority Value is 0~63, otherwise is 0~7.";
              }
            }
          }
          container diffserv-domain-applications {
            config false;
            description
              "List of operational state of diffserv domain applications on the interface.";
            list diffserv-domain-application {
              key "interface-name direction";
              description
                "Operational state of diffserv domain applications on the interface.";
              leaf interface-name {
                type string {
                  length "1..127";
                }
                description
                  "Interface name.";
              }
              leaf direction {
                type trust-direction-type ;
                description
                  "Direction.";
              }
            }
          }
        }
      }
      container traffic-classifiers {
        description
          "List of configure traffic classifiers.";
        list traffic-classifier {
          key "name";
          description
            "Configure traffic classifier.";
          leaf name {
            type string {
              length "1..127";
            }
            description
              "Name of a traffic classifier.";
          }
          leaf operator {
            type class-operator;
            default "or";
            description
              "Logical operator of a rule. This node does not support modification.";
            ext:operation-exclude update {
              description "After the configuration is created, the node cannot be modified.";
            }
          }
          leaf description {
            type string {
              length "1..127";
            }
            description
              "Description.";
          }
          leaf precedence {
            type uint16;
            description
              "Priority of classifier.";
          }
          leaf id {
            type uint32;
            config false;
            description
              "Classifier ID.";
          }
          container tcp-flag {
            description
              "Configure the TCP flag value.";
            leaf tcp-flag-value {
              type bits{
                bit fin {
                  position 0;
                }
                bit syn {
                  position 1;
                }
                bit rst {
                  position 2;
                }
                bit psh {
                  position 3;
                }
                bit ack {
                  position 4;
                }
                bit urg {
                  position 5;
                }
            } 
              description
                "TCP flag value.ack(0x010000),fin(0x000001),psh(0x001000),rst(0x000100),syn(0x000010),urg(0x100000).";
            }
          }
          container rule-acls {
            must "../operator='or' or (../operator='and' and count(./rule-acl)<=1)";
            description
              "List of configure rule matching IPv4 acl.";
            list rule-acl {
              key "acl-name";
              max-elements  "16";
              description
                "Configure rule matching IPv4 acl.";
              leaf acl-name {
                type leafref {
                  path "/acl:acl/acl:groups/acl:group/acl:identity";
                }
                must "/acl:acl/acl:groups/acl:group[acl:identity=current()]/acl:type!='interface' and /acl:acl/acl:groups/acl:group[acl:identity=current()]/acl:type!='UCL'";
                description
                  "Acl number or name.";
              }
            }
          }
          container rule-acl-ipv6s {
            must "../operator='or' or (../operator='and' and count(./rule-acl-ipv6)<=1)";
            description
              "List of configure rule matching IPv6 acl. This node is deprecated and rule-acl-ipv6-prioritys is recommended.";
            list rule-acl-ipv6 {
              key "acl-name";
              max-elements  "16";
              description
                "Configure rule matching IPv6 acl.";
              leaf acl-name {
                type leafref {
                  path "/acl:acl/acl:group6s/acl:group6/acl:identity";
                }
                must "/acl:acl/acl:group6s/acl:group6[acl:identity=current()]/acl:type='basic' or /acl:acl/acl:group6s/acl:group6[acl:identity=current()]/acl:type='advance'";
                description
                  "Acl number or name.";
              }
              leaf loose-mode {
                type qos:ipv6-prefix-mode;
				default "default-mode";
                description
                  "IPv6 prefix mode. Loose mode (prefix 64) or strict mode (prefix 128).";
              }
            }
          }
          container rule-acl-prioritys {
            must "../operator='or' or (../operator='and' and count(./rule-acl-priority)<=1)";
            description
              "List of configure rule matching IPv4 ACL.";
            list rule-acl-priority {
              key "acl-name";
              unique "priority";
              max-elements "16";
              description
                "Configure rule matching IPv4 ACL.";
              leaf acl-name {
                type leafref {
                  path "/acl:acl/acl:groups/acl:group/acl:identity";
                }
                must "/acl:acl/acl:groups/acl:group[acl:identity=current()]/acl:type!='interface'";
                description
                  "ACL number or name.";
              }
              leaf priority {
                when "../../../operator='or'";
                type uint16 {
                  range "1..65535";
                }
                mandatory true;
                description
                  "Specify the precedence of ACL.";
              }
            }
          }
          container rule-acl-ipv6-prioritys {
            must "../operator='or' or (../operator='and' and count(./rule-acl-ipv6-priority)<=1)";
            description
              "List of configure rule matching IPv6 ACL.";
            list rule-acl-ipv6-priority {
              key "acl-name";
              unique "priority";
              max-elements "16";
              description
                "Configure rule matching IPv6 ACL.";
              leaf acl-name {
                type leafref {
                  path "/acl:acl/acl:group6s/acl:group6/acl:identity";
                }
                must "/acl:acl/acl:group6s/acl:group6[acl:identity=current()]/acl:type!='interface'";
                description
                  "ACL number or name.";
              }
              leaf priority {
                when "../../../operator='or'";
                type uint16 {
                  range "1..65535";
                }
                mandatory true;
                description
                  "Specify the precedence of IPv6 ACL.";
              }
            }
          }
          container rule-anys {
            description
              "List of configure rule matching all packets.";
            list rule-any {
              key "protocol-family";
              max-elements  "2";
              description
                "Configure rule matching all packets.";
              leaf protocol-family {
                type ip-family;
                description
                  "IP protocol version.";
              }
            }
          }
          container rule-prioritys {
            description
              "List of configure rule matching precedence.";
            list rule-priority {
              key "type value";
              max-elements "16";
              description
                "Configure rule matching precedence.";
              leaf type {
                type priority-type;
                description
                  "Priority type.";
              }
              leaf value {
                type uint8 {
                  range "0..63";
                }
                must "(((../type='dscp' or ../type='ipv6-dscp') and ../value<=63) or ../value<=7)";
                description
                  "Priority value.";
              }
            }
          }
          container rule-service-classs {
            description
              "List of configure rule matching service classes.";
            list rule-service-class {
              key "service-class";
              max-elements "8";
              description
                "Configure rule matching service class.";
              leaf service-class {
                type qos-service-class;
                description
                  "Service class.";
              }
            }
          }
          container local-ids {
            description
              "List of configure rule matching local id.";
            list local-id {
              key "value";
              max-elements "16";
              description
                "Configure rule matching local id.";
              leaf value {
                type uint32 {
                  range "1..255";
                }
                description
                  "Local id value.";
              }
            }
          }
          container local-id-ipv6s {
            description
              "List of configure rule matching IPv6 local id.";
            list local-id-ipv6 {
              key "value";
              max-elements "16";
              description
                "Configure rule matching IPv6 local id.";
              leaf value {
                type uint32 {
                  range "1..255";
                }
                description
                  "IPv6 local id value.";
              }
            }
          }
          container rule-eth-types {
            must "../operator='or' or (../operator='and' and count(./rule-eth-type)<=1)";
            description
              "List of configure rule type value.";
            list rule-eth-type {
              key "value";
              max-elements  "16";
              description
                "Configure rule type value.";
              leaf value {
                type pub-type:hex-binary {
                  length "3..6";
                }
                description
                  "Type value.";
              }
            }
          }
          container rule-address-ipv6s {
            description
              "List of configure rule matching IPv6 addresses.";
            list rule-address-ipv6 {
              key "address-type address-value prefix-length";
              max-elements  "16";
              description
                "Configure rule matching IPv6 addresses.";
              leaf address-type {
                type qos-address-type;
                description
                  "Type of an IPv6 address.";
              }
              leaf address-value {
                type inet:ipv6-address-no-zone;
                description
                  "IPv6 address.";
              }
              leaf prefix-length {
                type uint8 {
                  range "0..128";
                }
                description
                  "Length of the IPv6 address prefix.";
              }
            }
          }
          container rule-mac-and-masks {
            must "../operator='or' or (../operator='and' and count(./rule-mac-and-mask[mac-type = 'source'])<=1 and count(./rule-mac-and-mask[mac-type = 'destination'])<=1)";
            description
              "List of configure rule matching mac and mask addresses.";
            list rule-mac-and-mask {
              key "mac-type mac-address mac-address-mask";
              max-elements  "16";
              description
                "Configure rule matching mac and mask addresses.";
              leaf mac-type {
                type qos-mac-type;
                description
                  "Type of a MAC address.";
              }
              leaf mac-address {
                type pub-type:mac-address;
                description
                  "Mac address.";
              }
              leaf mac-address-mask {
                type pub-type:mac-address;
                description
                  "Mac address mask.";
              }
            }
          }
          container rule-mac-addresss {
            description
              "List of configure rule matching mac addresses.";
            list rule-mac-address {
              key "type address";
              max-elements  "16";
              description
                "Configure rule matching mac addresses.";
              leaf type {
                type qos-mac-type;
                description
                  "Type of a MAC address.";
              }
              leaf address {
                type pub-type:mac-address;
                description
                  "Mac address.";
              }
            }
          }
          container rule-offsets {
            description
              "Configure rule offset values.";
            container rule-offset {
              presence "create rule-offset";
              description
                "Enable/disable rule offset values.";
              leaf offset-value1 {
                type uint32 {
                  range "0..156";
                }
                mandatory true;
                description
                  "Offset Value.";
              }
              leaf match-value1 {
                type pub-type:hex-binary;
                mandatory true;
                description
                  "Match Value.";
              }
              leaf match-mask1 {
                type pub-type:hex-binary;
                mandatory true;
                description
                  "Match Mask.";
              }
              leaf offset-value2 {
                type uint32 {
                  range "0..156";
                }
                description
                  "Offset Value.";
              }
              leaf match-value2 {
                when "../offset-value2";
                type pub-type:hex-binary;
                mandatory true;
                description
                  "Match Value.";
              }
              leaf match-mask2 {
                when "../offset-value2";
                type pub-type:hex-binary;
                mandatory true;
                description
                  "Match Mask.";
              }
              leaf offset-value3 {
                when "../offset-value2";
                type uint32 {
                  range "0..156";
                }
                description
                  "Offset Value.";
              }
              leaf match-value3 {
                when "../offset-value3";
                type pub-type:hex-binary;
                mandatory true;
                description
                  "Match Value.";
              }
              leaf match-mask3 {
                when "../offset-value3";
                type pub-type:hex-binary;
                mandatory true;
                description
                  "Match Mask.";
              }
              leaf offset-value4 {
                when "../offset-value3";
                type uint32 {
                  range "0..156";
                }
                description
                  "Offset Value.";
              }
              leaf match-value4 {
                when "../offset-value4";
                type pub-type:hex-binary;
                mandatory true;
                description
                  "Match Value.";
              }
              leaf match-mask4 {
                when "../offset-value4";
                type pub-type:hex-binary;
                mandatory true;
                description
                  "Match Mask.";
              }
            }
          }
          container rule-protocol-ipv6s {
            description
              "List of configure rule matching IPv6 extended headers.";
            list rule-protocol-ipv6 {
              key "family number";
              max-elements "16";
              description
                "Configure rule matching IPv6 extended headers.";
              leaf family {
                type qos-ipv6-family;
                description
                  "Protocol family.";
              }
              leaf number {
                type uint8;
                description
                  "Protocol number.";
              }
            }
          }
          container rule-tcp-flags {
            description
              "List of configure rule matching TCP flags.";
            list rule-tcp-flag {
              must "((./bit-match-type='not-config') or (./bit-match-type='established' and ./tcp-flag='20' and ./tcp-flag-mask='20') or (./bit-match-type='fin' and ./tcp-flag='1' and ./tcp-flag-mask='1') or (./bit-match-type='syn' and ./tcp-flag='2' and ./tcp-flag-mask='2') or (./bit-match-type='rst' and ./tcp-flag='4' and ./tcp-flag-mask='4') or (./bit-match-type='psh' and ./tcp-flag='8' and ./tcp-flag-mask='8') or (./bit-match-type='ack' and ./tcp-flag='16' and ./tcp-flag-mask='16') or (./bit-match-type='urg' and ./tcp-flag='32' and ./tcp-flag-mask='32') or (./bit-match-type='ece' and ./tcp-flag='64' and ./tcp-flag-mask='64') or (./bit-match-type='cwr' and ./tcp-flag='128' and ./tcp-flag-mask='128') or (./bit-match-type='ns' and ./tcp-flag='256' and ./tcp-flag-mask='256'))";
              key "bit-match-type tcp-flag tcp-flag-mask";
              max-elements  "16";
              description
                "Configure rule matching TCP flags.";
              leaf bit-match-type {
                type qos-tcp-bit-match;
                description
                  "TCP bit match type.";
              }
              leaf tcp-flag {
                type uint16 {
                  range "0..511";
                }
                description
                  "TCP flag value.";
              }
              leaf tcp-flag-mask {
                type uint16 {
                  range "0..511|65535";
                }
                description
                  "TCP flag mask value;please input 65535 when not config.";
              }
            }
          }
          container rule-tcp-flag-ipv6s {
            description
              "List of configure rule matching IPv6 TCP flags.";
            list rule-tcp-flag-ipv6 {
              must "((./bit-match-type='not-config') or (./bit-match-type='established' and ./tcp-flag='20' and ./tcp-flag-mask='20') or (./bit-match-type='fin' and ./tcp-flag='1' and ./tcp-flag-mask='1') or (./bit-match-type='syn' and ./tcp-flag='2' and ./tcp-flag-mask='2') or (./bit-match-type='rst' and ./tcp-flag='4' and ./tcp-flag-mask='4') or (./bit-match-type='psh' and ./tcp-flag='8' and ./tcp-flag-mask='8') or (./bit-match-type='ack' and ./tcp-flag='16' and ./tcp-flag-mask='16') or (./bit-match-type='urg' and ./tcp-flag='32' and ./tcp-flag-mask='32'))";
              key "bit-match-type tcp-flag tcp-flag-mask";
              max-elements  "16";
              description
                "Configure rule matching IPv6 TCP flags.";
              leaf bit-match-type {
                type qos-tcp-bit-match-ipv6;
                description
                  "IPv6 TCP bit match type.";
              }
              leaf tcp-flag {
                type uint16 {
                  range "0..63";
                }
                description
                  "IPv6 TCP flag value.";
              }
              leaf tcp-flag-mask {
                type uint16 {
                  range "0..63|65535";
                }
                description
                  "IPv6 TCP flag mask value;please input 65535 when not config.";
              }
            }
          }
          container rule-vlans {
            description
              "List of configure VLAN value.";
            list rule-vlan {
              key "vlan-id ce-vlan-id";
              max-elements  "16";
              description
                "Configure VLAN value.";
              leaf vlan-id {
                type uint16 {
                  range "1..4094";
                }
                description
                  "VLAN id.";
              }
              leaf ce-vlan-id {
                type uint16 {
                  range "0..4094";
                }
                description
                  "Ce VLAN id.";
              }
            }
          }
          container src-dest-local-ids {
            description
              "List of configure rule matching source and destination local id.";
            list src-dest-local-id {
              key "source destination";
              max-elements  "16";
              description
                "Configure rule matching source and destination local id.";
              leaf source {
                type uint32 {
                  range "1..255";
                }
                description
                  "Source local id.";
              }
              leaf destination {
                type uint32 {
                  range "1..255";
                }
                description
                  "Source local id.";
              }
            }
          }
          container rule-pevlans {
            description
              "List of configure pe VLAN.";
            list rule-pevlan {
			  must "./end-vlan-id>=./start-vlan-id";
              key "start-vlan-id end-vlan-id";
              description
              "Configure pe VLAN.";
            leaf start-vlan-id {
              type uint16 {
                range "1..4094";
              }
              description
                "Start VLAN id.";
            }
            leaf end-vlan-id {
              type uint16 {
                range "1..4094";
              }
              description
                "End VLAN id.";
             }
            }
          }
          container rule-cevlans {
            must "../operator='or' or (../operator='and' and count(./rule-cevlan)<=1)";
            description
              "List of configure ce VLAN.";
            list rule-cevlan {
              must "./end-vlan-id>=./start-vlan-id";
              key "start-vlan-id end-vlan-id";
              description
              "Configure ce VLAN.";
              leaf start-vlan-id {
                type uint16 {
                  range "1..4094";
                }
                description
                  "Start VLAN id.";
              }
              leaf end-vlan-id {
                type uint16 {
                  range "1..4094";
                }
                description
                  "End VLAN id.";
              }
            }
          }
          container rule-pe-cevlans {
            description
              "List of configure pe VLAN and ce VLAN.";
            list rule-pe-cevlan {
			  must "./rule-end-pevlan-id>=./rule-start-pevlan-id";
			  must "./rule-end-cevlan-id>=./rule-start-cevlan-id";
			  must "not((./rule-end-cevlan-id!=./rule-start-cevlan-id) and (./rule-start-pevlan-id!=./rule-end-pevlan-id))";
              key "rule-start-pevlan-id rule-end-pevlan-id rule-start-cevlan-id rule-end-cevlan-id";
              description
              "Configure pe VLAN and ce VLAN.";
            leaf rule-start-pevlan-id {
              type uint16 {
                range "1..4094";
              }
              description
                "Start pe VLAN id.";
            }
            leaf rule-end-pevlan-id {
              type uint16 {
                range "1..4094";
              }
              description
                "End pe VLAN id.";
            }
            leaf rule-start-cevlan-id {
              type uint16 {
                range "1..4094";
              }
              description
                "Start ce VLAN id.";
            }
            leaf rule-end-cevlan-id {
              type uint16 {
                range "1..4094";
              }
              description
                "End ce VLAN id.";
              }
            }
          }
          container rule-any-packets {
            description
              "Configure match any packets.";
            leaf rule-any-packet {
              type empty;
              description
                "Match any packets.";
            }
          }
          container rule-interfaces {
            description
              "List of match interface.";
            list rule-interface {
              key "direction interface";
              max-elements 4;
              description
                "Configure match interface.";
              leaf direction {
                type qos:qos-direction-type;
                description
                  "Direction.";
              }
              leaf interface {
                type leafref {
                  path "/ifm:ifm/ifm:interfaces/ifm:interface/ifm:name";
                }
                description
                  "Interface.";
              }
            }
          }
          container rule-double-tags {
            description
              "Configure double tags.";
            leaf double-tag {
              type empty;
              description
                "Double tags.";
            }
          }
          container rule-discards {
            description
              "Configure discard.";
            leaf rule-discard-label {
              type empty;
              description
                "Discard.";
            }
          }
          container rule-ip-identifications {
            description
              "List of configure match ip identification id.";
            list rule-ip-identification {
              key "identification-id";
              description
                "Configure match ip identification id.";
              leaf identification-id {
                type uint16 {
                  range "0..65535";
                }
                description
                  "Ip identification id.";
              }
              leaf identification-mask {
                type pub-type:hex-binary;
                default "0XFFFF";
                description
                  "Ip identification mask.";
              }
            }
          }
          container rule-nexthops {
            description
              "List of configure nexthop.";
            list rule-nexthop {
              key "ip-address interface";
              description
                "Configure nexthop.";
              leaf ip-address {
                type inet:ipv4-address-no-zone;
                description
                  "Nexthop IPv4 address.";
              }
              leaf interface {
                type leafref {
                  path "/ifm:ifm/ifm:interfaces/ifm:interface/ifm:name";
                }
                description
                  "Nexthop interface.";
              }
            }
          }
          container rule-nexthop-ipv6s {
            description
              "List of configure match nexthop of IPv6.";
            list rule-nexthop-ipv6 {
              key "ipv6-address interface";
              description
                "Configure match nexthop of IPv6.";
              leaf ipv6-address {
                type inet:ipv6-address-no-zone;
                description
                  "Nexthop IPv6 address.";
              }
              leaf interface {
                type leafref {
                  path "/ifm:ifm/ifm:interfaces/ifm:interface/ifm:name";
                }
                description
                  "Nexthop interface.";
              }
            }
          }
          container rule-packet-types {
            description
              "Configure packet type.";
            leaf rule-packet-type {
              type enumeration {
                enum "unicast" {
                  value 1;
                  description
                    "Unicast type.";
                }
                enum "unknown-unicast" {
                  value 2;
                  description
                    "Unknown unicast type.";
                }
              }
              description
                "Packet type.";
            }
          }
          container rule-ecns {
            description
              "List of configure match of ecn.";
            list rule-ecn {
              key "ip-family ecn-value";
              description
                "Configure match of ecn.";
              leaf ip-family {
                type qos:ip-family;
                description
                  "Ip family.";
              }
              leaf ecn-value {
                type uint8 {
                  range "0..3";
                }
                description
                  "Ecn.";
              }
            }
          }
          container rule-gre-inner {
            description
              "Configure gre inner ip fields.";
              leaf source-port-num {
                type inet:port-number;
                description
                  "Source port number.";
              }
              leaf dest-port-num {
                type inet:port-number;
                description
                  "Destination port number.";
              }
              leaf source-ip {
                type inet:ipv4-address-no-zone;
                description
                  "Source IPv4 address.";
              }
              leaf source-ip-mask {
                type inet:ipv4-address-no-zone;
                description
                  "Source IPv4 address mask.";
              }
              leaf destination-ip {
                type inet:ipv4-address-no-zone;
                description
                  "Destination IPv4 address.";
              }
              leaf destination-ip-mask {
                type inet:ipv4-address-no-zone;
                description
                  "Destiantion IPv4 address mask.";
              }
	      leaf protocol {
		type uint8;
		description
		  "Protocol type value (1: icmp; 2: igmp; 6: tcp; 17: udp; 47: gre; 50: IPv6-esp; 51: IPv6-ah; 58: icmpv6; 89: ospf).";
	      }
          }
          container rule-vxlan-acls {
            description
              "List of configure of vxlan tunnel fields and inner packet fields.";
            list rule-vxlan-acl {
              key "vxlan-acl";
              description
                "Configure vxlan acl.";
              leaf vxlan-acl {
                type leafref {
                  path "/acl:acl/acl:groups/acl:group/acl:identity";
                }
                must "/acl:acl/acl:groups/acl:group[acl:identity=current()]/acl:type='basic' or /acl:acl/acl:groups/acl:group[acl:identity=current()]/acl:type='advance' or /acl:acl/acl:groups/acl:group[acl:identity=current()]/acl:type='link'";
                description
                  "Acl number or name.";
              }
              leaf tag-format {
                type qos:tag-format;
                description
                  "Qos tag format.";
              }
              leaf transit {
                type empty;
                description
                  "Transit.";
              }
            }
          }
          container rule-vxlan-infos {
            description
              "List of configure vxlan header info.";
            list rule-vxlan-info {
              key "vxlan-field-type field-value";
              description
                "Configure vxlan fields.";
              leaf vxlan-field-type {
                type qos:vxlan-field-type;
                description
                  "Vxlan field type.";
              }
              leaf field-value {
                type pub-type:hex-binary;
                description
                  "Field value.";
              }
              leaf transit {
                type empty;
                description
                  "Transit.";
              }
            }
          }
          container rule-mpls-acls {
            description
              "List of configure MPLS acl.";
            list rule-mpls-acl {
              key "adv-acl";
              description
                "Configure MPLS acl.";
              leaf adv-acl {
                type leafref {
                  path "/acl:acl/acl:groups/acl:group/acl:identity";
                }
                must "/acl:acl/acl:groups/acl:group[acl:identity=current()]/acl:type='basic' or /acl:acl/acl:groups/acl:group[acl:identity=current()]/acl:type='advance' or /acl:acl/acl:groups/acl:group[acl:identity=current()]/acl:type='link'";
                description
                  "Advanced acl.";
              }
              leaf transit {
                type empty;
                description
                  "Transit.";
              }
            }
          }
          container rule-mpls-ipv6acls {
            description
              "List of comfigure MPLS IPv6 acl.";
            list rule-mpls-ipv6acl {
              key "ipv6-acl";
              description
                "Configure MPLS IPv6 acl.";
              leaf ipv6-acl {
                type leafref {
                  path "/acl:acl/acl:group6s/acl:group6/acl:identity";
                }
                must "/acl:acl/acl:group6s/acl:group6[acl:identity=current()]/acl:type='basic' or /acl:acl/acl:group6s/acl:group6[acl:identity=current()]/acl:type='advance'";
                description
                  "IPv6 acl.";
              }
              leaf transit {
                type empty;
                description
                  "Transit.";
              }
            }
          }
          container rule-rocev2 {
            presence "Configure rocev2.";
            description
              "Configure rocev2.";
              leaf ip-family {
                type qos:ip-family;
                mandatory true;
                description
                  "Ip family.";
              }
              leaf opcode {
                type uint8 {
                  range "0..255";
                }
                description
                  "Opcode.";
              }
              leaf qpair {
                type uint32;
                description
                  "Qpair.";
              }
              leaf nack {
                type uint8;
                description
                  "Nack.";
              }
              container udf-l4-head-offs {
                description
                  "List of configure udf l4 head offset.";
                list udf-l4-head-off {
                  key "rule-string rule-mask offset";
                  description
                    "Configure udf l4 head offset.";
                  leaf rule-string {
                    type pub-type:hex-binary {
                      length "3..10";
                    }
                    description
                      "Match value.";
                  }
                  leaf rule-mask {
                    type pub-type:hex-binary {
                      length "3..10";
                    }
                    description
                      "Value mask.";
                  }
                  leaf offset {
                    type uint8 {
                      range "8..20";
                    }
                    description
                      "Offset.";
                  }
                }
              }
          }
          container rule-vxlan-ipv6acls {
            description
              "List of configure match vxlan inner IPv6 packets.";
            list rule-vxlan-ipv6acl {
              key "vxlan-ipv6acl";
              description
                "Configure match vxlan inner IPv6 packets.";
              leaf vxlan-ipv6acl {
                type leafref {
                  path "/acl:acl/acl:group6s/acl:group6/acl:identity";
                }
                must "/acl:acl/acl:group6s/acl:group6[acl:identity=current()]/acl:type='basic' or /acl:acl/acl:group6s/acl:group6[acl:identity=current()]/acl:type='advance'";
                description
                  "Vxlan IPv6 acl.";
              }
              leaf ipv6-rule-mode {
                type qos:ipv6-prefix-mode;
                description
                  "Match mode.";
              }
              leaf tag-format {
                type qos:tag-format;
                description
                  "Tag format.";
              }
              leaf transit {
                type empty;
                description
                  "Configure vxlan IPv6 Transit.";
              }
            }
          }
          container rule-qppb {
            description
              "Configure qppb rule.";
            leaf local-id {
              type uint32 {
                range "1..255";
              }
              description
                "Qppb local-id value.";
            }
          }
          container rule-gtp {
            description
              "Configure GTP (GPRS Tunneling Protocol) rule.";
            leaf gtp-teid-value {
              type uint32;
              description
                "GTP teid value.";
            }
          }
          container vxlan-local-ids {
            description
              "List of configure rule matching vxlan local ID.";
            list vxlan-local-id {
              must "(../../operator='or') or (../../operator='and' and not(../../local-ids/local-id) and not(../../local-id-ipv6s/local-id-ipv6))";
              key "value";
              max-elements  "7";
              description
                "Configure rule matching vxlan local ID.";
              leaf value {
                type uint32 {
                  range "1..7";
                }
                description
                  "Vxlan local ID.";
              }
            }
          }
          container vxlan-local-id-ipv6s {
            description
              "List of configure rule matching IPv6 vxlan local ID.";
            list vxlan-local-id-ipv6 {
              must "(../../operator='or') or (../../operator='and' and not(../../local-ids/local-id) and not(../../local-id-ipv6s/local-id-ipv6))";
              key "value";
              max-elements  "7";
              description
                "Configure rule matching IPv6 vxlan local ID.";
              leaf value {
                type uint32 {
                  range "1..7";
                }
                description
                  "IPv6 vxlan local ID.";
              }
            }
          }
        }
      }
      container traffic-behaviors {
        description
          "List of configure traffic behaviors.";
        list traffic-behavior {
          key "name";
          description
            "Configure traffic behavior.";
          leaf name {
            type string {
              length "1..127";
            }
            description
              "Name of a traffic behavior.";
          }
          leaf description {
            type string {
              length "1..127";
            }
            description
              "Description.";            
          }
          container filter-action {
              description
                "Configure filter action.";
              leaf filter {
                type filter-flag;
                default "permit";
                description
                  "Filter type.";
              }
            }
          container service-class-actions {
            description
              "List of configure service class actions.";
            list service-class-action {
              key "action-type";
              max-elements  "3";
              description
                "Configure service class action.";
              leaf action-type {
                type service-class-action;
                description
                  "Type of a service class action.";
              }
              leaf service-class {
                type qos-service-class;
                mandatory true;
                description
                  "Class of service.";
              }
              leaf color {
                type qos-color;
                mandatory true;
                description
                  "Color.";
              }
              leaf remark-switch {
                type remark-type;
                must "../action-type='service-class' or not(../remark-switch='disable')";
                default "enable";
                description
                  "Remark switch.";
              }
              leaf bfd-session-name {
                when "../action-type!='service-class'";
                type leafref {
                  path "/bfd:bfd/bfd:sessions/bfd:session/bfd:name";
                }
                mandatory true;
                description
                  "Bfd Session Name.";
              }
            }
          }
          container remark-actions {
            description
              "List of configure remark actions.";
            list remark-action {
              key "action-type";
              max-elements "8";
              description
                "Configure remark action.";
              leaf action-type {
                type action-remark;
                description
                  "Type of a remark action. The 8021p includes inner-8021p and outer-8021p.";
              }
              leaf remark-value {
                type uint32 {
                  range "0..255";
                }
                must "((../action-type='ip-df' and ../remark-value<=1) or ((../action-type='8021p' or ../action-type='ip-precedence' or ../action-type='mpls-exp' or ../action-type='inner-8021p' or ../action-type='outer-8021p') and ../remark-value<=7) or (../action-type='tos' and ../remark-value<=15) or ((../action-type='ipv4-dscp' or ../action-type='ipv6-dscp') and ../remark-value<=63) or (../action-type='ttl' and ../remark-value>0 and ../remark-value<=255) or (../action-type='remark-local-id' and ../remark-value>0 and ../remark-value<=7))";
                mandatory true;
                description
                  "Remark priority value.";
              }
              leaf after-trust {
                when "../action-type='8021p'";
                type switch-type;
                description
                  "Remark take effect after trust.";
              }
            }
          }
          container acl-log-action {
            description
              "Configure log first packet action.";
            leaf action-type {
              type acl-log-action-type;
              description
                "Type of the log first-packet action.";
            }            
          }
          container car-actions {
            description
              "List of configure CAR actions.";
            list car-action {
              key "action-type";
              description
                "Configure CAR action.";
              leaf action-type {
                type action-car;
                description
                  "Type of a car action.";
              }
              choice cir-parameters {
                mandatory true;
                description
                  "Specify cir parameters.";
                case cir-mode {
                  description
                  "Specify cir parameters choice case as cir value.";
                  leaf cir {
                    type uint32 {
                      range "0..4294967295";
                    }
                    units "kbit/s";
                    mandatory true;
                    description
                      "Specify cir value.";
                  }
                  leaf pir {
                    type uint32 {
                      range "0..4294967295";
                    }
                    units "kbit/s";
                    must "../pir>=../cir";
                    description
                      "Peak information rate.";
                    }
                }
                case cir-percent-mode {
                  description
                    "Specify cir parameters choice case as cir percentage value.";
                  leaf cir-percentage {
                    type uint8 {
                      range "0..100";
                    }
                    units "%";
                    mandatory true;
                    description
                      "Cir percentage.";
                  }
                  leaf percent-src {
                    type percent-source;
                    must "(../percent-src='bandwidth') or (../percent-src='car' and ../share-mode='enable' and ../color-aware='enable') ";
                    mandatory true;
                    description
                      "Percentage source of cir and pir.";
                  }  
                  leaf pir-percentage {
                    type uint8 {
                      range "0..100";
                    }
                    units "%";
                    must "../pir-percentage>=../cir-percentage";
                    description
                      "Pir percentage.";
                  }			  
                }
              }
              leaf cbs {
                type uint32 {
                  range "0..4294967295";
                }
                units "Byte";
                must "../cir";
                description
                  "Committed burst size.";
              }
              leaf pbs {
                type uint32 {
                  range "0..4294967295";
                }
                units "Byte";
                must "../cbs";
                description
                  "Peak burst size.";
              }
              leaf adjust {
                type int32 {
                  range "-32..-1 | 1..31";
                }
                description
                  "Adjust value.";
              }
              leaf green-action {
                type color-action-type;
                mandatory true;
                description
                  "Action performed to the green packets.";
              }
              choice green-action-parameters {
                description
                  "Specify green action parameters.";
                case green-service-class {
                  description
                    "Specify green action parameters choice case as service clase.";
                  leaf green-service-class {
                    when "../green-action='pass'";
                    type qos-service-class;
                    description
                      "Service class marked to the green packets.";
                  }
                  leaf green-color {
                    when "../green-service-class";
                    type qos-color;
                    mandatory true;
                    description
                      "Color marked to the green packets.";
                  }
                }
                case green-remark-dscp {
                  description
                    "Specify green action parameters choice case as remark dscp.";
                  leaf green-remark-dscp {
                    when "../green-action='pass'";
                    type uint8 {
                      range "0..63";
                    }
                    description
                      "DSCP priority marked to the green packets.";
                  }
                }
                case green-remark-8021p {
                  description  "Specify green action parameters choice case as remark 8021p.";
                  leaf green-remark-8021p {
                    when "../green-action='pass'";
                    type uint8 {  
                      range "0..7";
                    }
                    description
                      "8021p priority marked to the green packets.";
                  }
                }
              }
              leaf yellow-action {
                type color-action-type;
                must "../pbs>0 or (../pir-percentage and not(../pbs))";
                ext:dynamic-default;
                description
                  "Action performed to the yellow packets.";
              }
              choice yellow-action-parameters {
                description
                  "Specify red action parameters.";
                case yellow-service-class {
                  description
                    "Specify yellow action parameters choice case as service clase.";
                  leaf yellow-service-class {
                    when "../yellow-action='pass'";
                    type qos-service-class;
                    description
                      "Service class marked to the yellow packets.";
                  }
                  leaf yellow-color {
                    when "../yellow-service-class";
                    type qos-color;
                    mandatory true;
                    description
                      "Color marked to the yellow packets.";
                  }
                }
                case yellow-remark-dscp {
                  description
                    "Specify yellow action parameters choice case as remark dscp.";
                  leaf yellow-remark-dscp {
                    when "../yellow-action='pass'";
                    type uint8 {
                      range "0..63";
                    }
                    description
                      "DSCP priority marked to the yellow packets.";
                  }
                }
                case yellow-remark-8021p {
                  description  "Specify yellow action parameters choice case as remark 8021p.";
                  leaf yellow-remark-8021p {
                    when "../yellow-action='pass'";
                    type uint8 {  
                      range "0..7";
                    }
                    description
                      "8021p priority marked to the yellow packets.";
                  }
                }
              }
              leaf red-action {
                type color-action-type;
                mandatory true;
                description
                  "Action performed to the red packets.";
              }
              choice red-action-parameters {
                description
                  "Specify red action parameters.";
                case red-service-class {
                  description
                    "Specify red action parameters choice case as service clase.";
                  leaf red-service-class {
                    when "../red-action='pass'";
                    type qos-service-class;
                    description
                      "Service class marked to the red packets.";
                  }
                  leaf red-color {
                    when "../red-service-class";
                    type qos-color;
                    mandatory true;
                    description
                      "Color marked to the red packets.";
                  }
                }
                case red-remark-dscp {
                  description
                    "Specify red action parameters choice case as remark dscp.";
                  leaf red-remark-dscp {
                    when "../red-action='pass'";
                    type uint8 {
                      range "0..63";
                    }
                    description
                      "DSCP priority marked to the red packets.";
                  }
                }
                case red-remark-8021p {
                  description  "Specify red action parameters choice case as remark 8021p.";
                  leaf red-remark-8021p {
                    when "../red-action='pass'";
                    type uint8 {  
                      range "0..7";
                    }
                    description
                      "8021p priority marked to the red packets.";
                  }
                }
              }
              leaf color-aware {
                type switch-type;
                description
                  "Color aware.";
              }
              leaf limit-type {
                when "not(../adjust) and (../cir)";
                type car-limit-type;
                description
                  "Car limit type.";
              }
              leaf share-mode {
                type enumeration {
                  enum "enable" {
                    value 1;
                    description
                      "Enable.";
                  }
                }
                description
                  "Aggregation car.";
              }
              leaf cir-unit {
                type qos:queue-rate;
                default "kbps";
                description
                  "Committed information rate uints.";
              }
              leaf pir-unit {
                type qos:queue-rate;
                default "kbps";
                description
                  "Peak information rate uints.";
              }
              leaf cbs-unit {
                type qos:queue-burst-size;
                default "bytes";
                description
                  "Committed burst size uints.";
              }
              leaf pbs-unit {
                type qos:queue-burst-size;
                default "bytes";
                description
                  "Peak burst size uints.";
              }
            }
          }
          container car-shares {
            description
              "Configure car share.";
            leaf car-name-share {
              type qos:priority-aware-type;
              description
                "Car share name.";
            }
          }
          container car-action-with-eirs {
            description
              "List of configure CAR actions with eir.";
            list car-action-with-eir {
              must "not(../../car-actions/car-action)";
              must "eir >= cir";
              key "action-type";
              description
                "Configure CAR action with eir.";
              leaf action-type {
                type action-car;
                description
                  "Type of a car action.";
              }
              leaf cir {
                type uint32;
                units "kbit/s";
                mandatory true;
                description
                  "Committed information rate.";
              }
              leaf eir {
                type uint32;
                units "kbit/s";
                mandatory true;
                description
                  "Excess information rate.";
              }
              leaf cbs {
                type uint32;
                units "Byte";
                mandatory true;
                description
                  "Committed burst size.";
              }
              leaf ebs {
                type uint32;
                units "Byte";
                mandatory true;
                description
                  "Excess burst size.";
              }
              leaf coupling {
                type switch-flag;
                default "disable";
                description
                  "Enable/disable coupling.";
              }
              leaf adjust {
                type int32 {
                  range "-32..-1 | 1..31";
                }
                description
                  "Adjust value.";
              }
              leaf green-action {
                type color-action-type;
                mandatory true;
                description
                  "Action performed to the green packets.";
              }
              choice green-action-parameters {
                description
                  "Specify green action parameters.";
                case green-service-class {
                  description
                    "Specify green action parameters choice case as service clase.";
                  leaf green-service-class {
                    when "../green-action='pass'";
                    type qos-service-class;
                    description
                      "Service class marked to the green packets.";
                  }
                  leaf green-color {
                    when "../green-service-class";
                    type qos-color;
                    mandatory true;
                    description
                      "Color marked to the green packets.";
                  }
                }
                case green-remark-dscp {
                  description
                    "Specify green action parameters choice case as remark dscp.";
                  leaf green-remark-dscp {
                    when "../green-action='pass'";
                    type uint8 {
                      range "0..63";
                    }
                    description
                      "DSCP priority marked to the green packets.";
                  }
                }
              }
              leaf yellow-action {
                type color-action-type;
                mandatory true;
                description
                  "Action performed to the yellow packets.";
              }
              choice yellow-action-parameters {
                description
                  "Specify red action parameters.";
                case yellow-service-class {
                  description
                    "Specify yellow action parameters choice case as service clase.";
                  leaf yellow-service-class {
                    when "../yellow-action='pass'";
                    type qos-service-class;
                    description
                      "Service class marked to the yellow packets.";
                  }
                  leaf yellow-color {
                    when "../yellow-service-class";
                    type qos-color;
                    mandatory true;
                    description
                      "Color marked to the yellow packets.";
                  }
                }
                case yellow-remark-dscp {
                  description
                    "Specify yellow action parameters choice case as remark dscp.";
                  leaf yellow-remark-dscp {
                    when "../yellow-action='pass'";
                    type uint8 {
                      range "0..63";
                    }
                    description
                      "DSCP priority marked to the yellow packets.";
                  }
                }
              }
              leaf red-action {
                type color-action-type;
                mandatory true;
                description
                  "Action performed to the red packets.";
              }
              choice red-action-parameters {
                description
                  "Specify red action parameters.";
                case red-service-class {
                  description
                    "Specify red action parameters choice case as service clase.";
                  leaf red-service-class {
                    when "../red-action='pass'";
                    type qos-service-class;
                    description
                      "Service class marked to the red packets.";
                  }
                  leaf red-color {
                    when "../red-service-class";
                    type qos-color;
                    mandatory true;
                    description
                      "Color marked to the red packets.";
                  }
                }
                case red-remark-dscp {
                  description
                    "Specify red action parameters choice case as remark dscp.";
                  leaf red-remark-dscp {
                    when "../red-action='pass'";
                    type uint8 {
                      range "0..63";
                    }
                    description
                      "DSCP priority marked to the red packets.";
                  }
                }
              }
              leaf color-aware {
                type switch-type;
                description
                  "Color aware.";
              }
              leaf limit-type {
                when "not(../adjust)";
                type car-limit-type;
                description
                  "Car limit type.";
              }              
            }
          }
          container flow-car-actions {
            description
              "Configure microflow CAR actions.";
            container flow-car-action {
              presence "create flow-car-action";
              description
                "Enable/disable microflow CAR actions.";
              leaf cir {
                type uint32 {
                  range "0..4294967295";
                }
                units "kbit/s";
                mandatory true;
                description
                  "Committed information rate.";
              }
              leaf pir {
                type uint32 {
                  range "0..4294967295";
                }
                units "kbit/s";
                must "(../pir>=../cir)";
                description
                  "Peak information rate.";
              }
              leaf cbs {
                type uint32 {
                  range "0..4294967295";
                }
                units "Byte";
                mandatory true;
                description
                  "Committed burst size.";
              }
              leaf pbs {
                type uint32 {
                  range "0..4294967295";
                }
                units "Byte";
                description
                  "Peak burst size.";
              }
              leaf ip-type {
                type qos-flow-type;
                mandatory true;
                description
                  "Type of an address.";
              }
              leaf ip-family {
                type qos-ip-family;
                default "ipv4";
                description
                  "Type of ip family.";
              }
            }
          }
          container increase-priority-action {
            description
              "Configure actions of increase priority.";
            leaf priority {
              type increase-priority;
              description
                "Action type.";
            }            
          }
         container policy-actions {
            description
              "Configure traffic policy action.";
            container policy-action {
              presence "create policy-actions";
              description
                "Enable/disable traffic policy action.";
              leaf policy-name {
                type leafref {
                  path "../../../../../qos:traffic-policys/qos:traffic-policy/qos:name";
                }
                mandatory true;
                description
                  "Policy name.";
              }
              leaf hierarchical-car {
                type enable-type;
                description
                  "Hierarchical car.";
              }
              leaf layer {
                type qos-policy-layer;
                description
                  "Layer.";
              }
            }
          } 
          container suppression-actions {
            description
              "List of L2 suppression.";
            list suppression-action {
              must "(./green-service-class and ./green-color) or (not(./green-service-class) and not(./green-color))";
              must "(./red-service-class and ./red-color) or (not(./red-service-class) and not(./red-color))";
              key "suppress-type";
              max-elements  "3";
              description
                "Configure L2 suppression.";
              leaf suppress-type {
                type suppress-type;
                description
                  "Suppression type.";
              }
              leaf cir {
                type uint32 {
                  range "0..4294967295";
                }
                units "kbit/s";
                mandatory true;
                description
                  "Committed information rate.";
              }
              leaf cbs {
                type uint32 {
                  range "0..4294967295";
                }
                units "Byte";
                mandatory true;
                description
                  "Committed burst size.";
              }
              leaf green-action {
                type color-action-type;
                mandatory true;
                description
                  "Action performed to the green packets.";
              }
              leaf green-service-class  {
                when "not(../green-action='discard') or ../green-action='pass'";
                type qos-service-class;
                must "../green-color";
                description
                  "Service class marked to the green packets.";
              }
              leaf green-color {
                when "../green-service-class";
                type qos-color;
                description
                  "Color marked to the green packets.";
              }
              leaf red-action {
                type color-action-type;
                mandatory true;
                description
                  "Action performed to the red packets.";
              }
              leaf red-service-class {
                when "not(../red-action='discard') or ../red-action='pass'";
                type qos-service-class;
                must "../red-color";
                description
                  "Service class marked to the red packets.";
              }
              leaf red-color {
                when "../red-service-class";
                type qos-color;
                description
                  "Color marked to the red packets.";
              }
            }
          }
          container load-action {
            description
              "Configure load balancing action.";
            leaf balance-type {
              type load-balance-type;
              description
                "Load balancing type.";
            }
          }      
          container match-term-action {
            description
              "Configure match termination action.";
            leaf match-term {
              type priority-aware-type;
              description
                "Match termination type.";
            }
          }
          container netstream-sampler-actions {
            description
              "List of netstream sampling action.";
            list netstream-sampler-action {
              must "count(../netstream-sampler-action[sample-type=current()/sample-type])=count(../netstream-sampler-action)";
              key "flow-type";
              max-elements  "2";
              description
                "Configure netstream sampling action.";
              leaf flow-type {
                type ip-type;
                description
                  "Flow type.";
              }
              leaf sample-type {
                type sample-type;
                mandatory true;
                description
                  "Sampling type.";
              }
              leaf sample-value {
                type uint16 {
                  range "1..65535";
                }
                must "(../sample-type='fix-time' and ../sample-value>=5 and ../sample-value<=30000) or not(../sample-type='fix-time')";
                mandatory true;
                description
                  "Sampling parameter. When sampling type is netstream fix packets sampler feature or netstream random packets sampler feature the sampling parameter is 1~65535, when sampling type is netstream fix time sampler feature the sampling parameter is 5~30000.";
              }
            }
          }
          container urpf-action {
            presence "create urpf-action";
            description
              "Enable/disable urpf action.";
            leaf check-type {
              type check-type;
              mandatory true;
              description
                "Type of the urpf check.";
            }
            leaf allow-default {
              type priority-aware-type;
              description
                "To check the default route.";
            }
            leaf ignore-default {
              type ignore-default-type;
              description
                "Indicates a mode in which the default route is excluded.";
            }
          }
          container except-deny-action {
            description
              "Configure IP netstream sampler except deny-action.";
            leaf deny-action {
              type priority-aware-type;
              description
                "DenyAction type.";
            }
          }
          container user-queue-action {
            presence "create user-queue-action";
            description
              "Enable/disable user queue action.";
            leaf cir {
              type uint32 {
                range "0 | 16..4294967294";
              }
              units "kbit/s";
              mandatory true;
              description
                "Committed information rate.";
            }
            leaf pir {
              type uint32 {
                range "0 | 16..4294967294";
              }
              units "kbit/s";
              must "../pir>=../cir";
              mandatory true;
              description
                "Peak information rate.";
            }
            leaf flow-queue-name {
              type leafref {
                path "../../../../../queue-scheduler-template/flow-queues/flow-queue/name";
              }
              must "../../../../../qos:queue-scheduler-template/qos:flow-queues/qos:flow-queue[qos:name=current()]/qos:mode='normal'";
              description
                "Flow queue.";
            }
            leaf flow-mapping-name {
              type leafref {
                path "../../../../../queue-scheduler-template/flow-mappings/flow-mapping/name";
              }
              description
                "Flow mapping.";
            }
            leaf user-group-queue-name {
              type leafref {
                path "../../../../../queue-scheduler-template/user-group-queues/user-group-queue/name";
              }
              must "/qos:qos/qos:queue-scheduler-template/qos:user-group-queues/qos:user-group-queue[qos:name=current()]/qos:mode='normal'";
              description
                "User group queue.";
            }
            leaf service-template-name {
              type leafref {
                path "../../../../../queue-scheduler-template/service-templates/service-template/name";
              }
              description
                "Service template.";
            }
          }
          container system-log-action {
            presence "create system-log-action";
            description
              "Enable/disable system log.";
            leaf threshold {
              type uint32 {
                range "1..4294967295";
              }
              mandatory true;
              description
                "Log threshold.";
            }
            leaf statistics-type {
              type statistics-type;
              mandatory true;
              description
                "Statistics type.";
            }
          }
          container remark-local-precedence {
            description
              "Configure remark local precedence.";
            leaf precedence-value {
              type uint8 {
                range "0..7";
              }
              description
                "Local precedence value.";
            }
            leaf color {
              type qos:qos-color;
              description
                "Color: green, yellow, red.";
            }
          }
          container vlan-oper-actions {
            description
              "Configure VLAN operation.";
            choice vlan-oper {
              description
                "VLAN operation type.";
              case vlan-mapping {
                description
                  "VLAN mapping.";
                leaf outer-vlanid {
                  type uint16 {
                    range "1..4094";
                  }
                  description
                    "Outer VLAN id.";
                }
                leaf inner-vlanid {
                  type uint16 {
                    range "1..4094";
                  }
                  description
                    "Inner VLAN id.";
                }
              }
              case vlan-stacking {
                description
                  "VLAN stacking.";
                leaf vlanid {
                  type uint16 {
                    range "1..4094";
                  }
                  description
                    "Stacking VLAN id.";
                }
              }
            }
          }
          container mac-learning-disable {
            description
              "Configure mac learning disable.";
            leaf mac-learning-disable {
              type empty;
              description
                "Disable mac address learning.";
            }
          }
          container statistic-action {
            description
              "Configure statistic.";
            leaf statistic-enable {
              type empty;
              description
                "Statistic enable.";
            }
          }
          container remark-action-colors {
            must "not(./remark-action-color[remark-type='8021p'] and ./remark-action-color[remark-type='qos-local-precedence'])";
            description
              "List of configure remark actions.";
            list remark-action-color {
	      must "(./remark-type='8021p' and ./remark-value<=7) or (./remark-type='dscp' and ./remark-value<=63) or (./remark-type='qos-local-id' and ./remark-value>=1 and ./remark-value<=255) or (./remark-type='qos-local-precedence' and ./remark-value>=0 and ./remark-value<=7)";
	      key "remark-type";
              description
               "Configure remark actions.";
              leaf remark-type {
                type remark-action-type;
                description
                  "Type of a remark action. Includes remark 8021p, remark vxlan, remark qos-local-id, remark qos-local-precedence, remark dscp.";
              }
              leaf remark-value {
                type uint32 {
                  range "0..16777215";
                }
                description
                  "Remark value.";
              }
              leaf color {
                when "../remark-type='qos-local-precedence'";
                type qos:remark-color;
                description
                  "Color of qos-local-precedence. Includes: green, yellow, red.";
              }
            }
          }
          container global-config {
            description
              "Configure traffic behavior global configuration.";
            leaf anyflow-enable {
              type qos:switch-flag;
              description
                "Anyflow enable.";
            }
            leaf traffic-analysis-enable {
              type qos:switch-flag;
              description
                "Traffic-analysis enable.";
            }
          }
          container flow-queue-action {
            description
              "Configure service queue action.";
            leaf flow-queue-name {
              type leafref {
                path "/qos:qos/qos:queue-scheduler-template/qos:flow-queues/qos:flow-queue/qos:name";
              }
              mandatory true;
              description
                "Flow queue profile name.";
            }
            leaf queue-name {
              type leafref {
                path "/qos:qos/qos:queue-scheduler-template/qos:flow-queues/qos:flow-queue/qos:traffic-behavior-queues/qos:traffic-behavior-queue/qos:name";
              }
              mandatory true;
              description
                "Queue name.";
            }
          }
          container qos-profile-action {
            description
              "Configure user queue action.";
            leaf qos-profile-name {
              type leafref {
                path "/qos:qos/qos:queue-scheduler-template/qos:profiles/qos:profile/qos:name";
              }
              description
                "User queue profile name.";
            }
            leaf user-queue-name {
              type leafref {
                path "/qos:qos/qos:queue-scheduler-template/qos:profiles/qos:profile/qos:traffic-behavior-user-queues/qos:traffic-behavior-user-queue/qos:name";
              }
              description
                "User queue name.";
            }
          }
        }
      }
      container traffic-policys {
        description
          "List of traffic policies.";
        list traffic-policy {
          key "name";
          description
            "Configure the traffic policy.";
          leaf name {
            type string {
              length "1..127";
            }
            description
              "Policy name.";
          }
          leaf description {
            type string {
              length "1..127";
            }
            description
              "Description.";            
          }
          leaf step {
            type uint16 {
              range "1..20";
            }
            default "1";
            description
              "Step.";
          }
          leaf share-mode {
            type switch-flag;
            default "enable";
            description
              "Sharing mode. After the policy is applied, the attribute of this node cannot be changed.";
          }
          leaf stat-flag {
            type switch-flag;
            default "disable";
            description
              "Flag for enabling statistics.";
          }
          leaf link-exclude {
            type switch-flag;
            default "disable";
            description
              "QoS link-adjustment link-layer-exclude.";
          }
          leaf id {
            type uint32;
            config false;
            description
              "Policy ID.";
          }
          container policy-nodes {
            description
              "List of the mappings between classifiers and behaviors.";
            list policy-node {
              key "classifier-name";
              description
                "Configure the mapping between classifier and behavior.";
              leaf classifier-name {
                type leafref {
                  path "../../../../../traffic-classifiers/traffic-classifier/name";
                }
                description
                  "Name of a traffic classifier.";
              }
              leaf behavior-name {
                type leafref {
                  path "../../../../../traffic-behaviors/traffic-behavior/name";
                }
                mandatory true;
                description
                  "Name of a traffic behavior.";
              }
              leaf priority {
                type uint16 {
                  range "0..65535";
                }
                ext:dynamic-default;
                description
                  "Priority of a classifier behavior.";
              }
            }
          }
          container group-mode-policy-nodes {
            when "../share-mode='disable'";
            description
              "List of the mappings between classifiers and behaviors for group mode.";
            list group-mode-policy-node {
              must "not(../../policy-nodes/policy-node)";
              key "classifier-name direction group-type group-name";
              unique "priority";
              description
                "Configure classifier and behavior for group mode.";
              leaf classifier-name {
                type leafref {
                  path "../../../../../traffic-classifiers/traffic-classifier/name";
                }
                description
                  "Name of a traffic classifier.";
              }
              leaf direction {
                type stream-direction-type;
                description
                  "Stream direction.";
              }
              leaf group-type {
                type group-type;
                description
                  "Group type.";
              }
              leaf group-name {
                type string {
                  length "1..33";
                }
                description
                  "Group name.";
              }
              leaf behavior-name {
                type leafref {
                  path "../../../../../traffic-behaviors/traffic-behavior/name";
                }
                mandatory true;
                description
                  "Name of a traffic behavior.";
              }
              leaf priority {
                type uint16 {
                  range "1..5119";
                }
                mandatory true;
                description
                  "Priority of a classifier behavior. This node does not support modification or deletion.";                
              }
            }
          }
          container ipv6-local-id-switch {
            description
              "Configure IPv6 local id enable.";
            leaf enable {
              type switch-type;
              description
                "Enable local id. After the classifer is configured, the state of this node cannot be changed.";
            }
          }
          leaf match-extended {
            type boolean;
            description
              "Enable/disable searching next classifier when the action of matched rule is deny.";
          }
          container vxlan-local-id-switch {
            must "enable='true' and not(../ipv6-local-id-switch/enable) or enable='false'";
            description
              "Configure vxlan local ID enable.";
            leaf enable {
              type boolean;
              default "false";
              description
                "Enable/disable vxlan local ID.";
            }
          }
          container ipv6-fragment-inner-protocol-switch {
            description
              "Configure IPv6 protocol fragment enable.";
            leaf enable {
              type boolean;
              default "false";
              description
                "Enable/disable IPv6 protocol fragment.";
            }
          }
        }
      }
      container qos-groups {
        description
          "List of qos group.";
        list qos-group {
          key "group-name";
          description
            "Configure qos group.";
          leaf group-name {
            type string {
              length "1..31";
              pattern '[a-zA-Z][!-~]{0,30}';
            }
            description
              "Group name.";
          }
          container group-interfaces {
            description
              "List of configure interface of qos group.";
            list group-interface {
              key "interface";
              description
                "Configure interface of qos group.";
              leaf interface {
                type leafref {
                  path "/ifm:ifm/ifm:interfaces/ifm:interface/ifm:name";
                }
                description
                  "Interface.";
              }
            }
          }
          container group-vlans {
            description
              "List of VLAN member in qos group.";
             list group-vlan {
              key "begin-vlan end-vlan";
              description
                "Configure VLAN of qos group.";
              leaf begin-vlan {
                type vlan:vlan-id;
                description
                  "Begin VLAN id. Begin-vlan must be smaller than end-vlan. If not, the system automatically corrects the VLAN ID.";
              }
              leaf end-vlan {
                type vlan:vlan-id;
                description
                  "End VLAN id.";
              }
            }
          }
          container group-ips {
            description
              "List of group ip.";
            list group-ip {
              key "source-ipv4 source-ip-mask";
              description
                "Configure group ip.";
              leaf source-ipv4 {
                type inet:ipv4-address-no-zone;
                description
                  "Source IPv4 address.";
              }
              leaf source-ip-mask {
                type inet:ipv4-address-no-zone;
                description
                  "IPv4 mask.";
              }
            }
          }
          container group-policy-applys {
            description
              "List of configure application of group traffic policy.";
            list group-policy-apply {
              key "policy-name direction";
              description
                "Configure application of group traffic policy.";
              leaf policy-name {
                type leafref {
                  path "/qos:qos/qos:classifier-template/qos:traffic-policys/qos:traffic-policy/qos:name";
                }
                description
                  "Policy name.";
              }
              leaf direction {
                type qos-direction-type;
                description
                  "Direction.";
              }
            }
          }
        }
      }
    }
    container car-template {
	  description
        "Configure qos car template.";
      container templates {
        description
          "List of QoS CAR profile and sets parameters in the QoS CAR profile.";
        list template {
          key "name";
          description
            "Configure the car template.";
          leaf name {
            type string {
              length "1..31";
              pattern '[^"\s?]*';
            }
            description
              "Car template name.";
          }
          choice cir-parameters {
            description
              "Specify cir parameters.";
            case cir {
              description
                "Specify cir parameters choice case as cir value.";
              leaf cir-value {
                type uint32 {
                  range "1..800000000";
                }
				mandatory true;
                description
                  "Cir rate.";
              }
              leaf pir-value {
                type uint32 {
                  range "1..800000000";
                }
                description
                  "Pir rate value.";
              }
              leaf cbs-value {
                type uint32 {
                  range "1..536870912";
                }
                description
                  "Committed burst size.";
              }
              leaf pbs-value {
                type uint32 {
                  range "1..536870912";
                }
                description
                  "Peak burst size.";
              }
              leaf cir-unit {
                type qos:queue-rate;
                default "kbps";
                description
                  "Specify the rate unit for car cir.";
              }
              leaf pir-unit {
                type qos:queue-rate;
                must '../pir-value';
                default "kbps";
                description
                  "Specify the rate unit for car pir.";
              }
              leaf cbs-unit {
                type qos:queue-burst-size;
                must '../cbs-value';
                default "bytes";
                description
                  "Specify the burst size unit for car cbs.";
              }
              leaf pbs-unit {
                type qos:queue-burst-size;
                must '../pbs-value';
                default "bytes";
                description
                  "Specify the burst size unit for car pbs.";
              }
            }
            case cir-percentage {
              description
                "Specify cir parameters choice case as cir percentage value.";
              leaf cir-percent {
                type uint32 {
                  range "1..100";
                }
				mandatory true;
                description
                  "Cir rate percent.";
              }
            }
          }
        }
      }
    }
    container integration-template {
      description
        "Configure integration template.";
      container profiles {
        description
          "List of configure profile.";
        list profile {
          key "name";
          max-elements 64;
          description
            "Configure profile.";
          leaf name {
            type string {
              length "1..64";
              pattern '[^"\s?]*';
            }
            description
              "Profile name.";
          }
          container cars {
            description
              "List of car.";
            list car {
              key "direction";
              description
                "Configure car of qos profile.";
              leaf direction {
                type qos:qos-direction-type;
                description
                  "Direction.";
              }
              leaf cir {
                type uint32;
                units "kbit/s";
                mandatory true;
                description
                  "Committed information rate.";
              }
              leaf pir {
                type uint32;
                units "kbit/s";
                must '../pir>=../cir';
                ext:dynamic-default {
                  ext:default-value "../cir";
                }
                description
                  "Peak information rate.";
              }
              leaf cbs {
                type uint32;
                units "Byte";
                ext:dynamic-default {
                  ext:default-value "../cir*188" {
                    when "not(../pir)";
                  }
                  ext:default-value "../pir*125" {
                    when "../pir";
                  }
                }
                description
                  "Committed burst size.";
              }
              leaf pbs {
                type uint32;
                units "Byte";
                ext:dynamic-default {
                  ext:default-value "../cir*313" {
                    when "not(../pir)";
                  }
                  ext:default-value "../pir*125" {
                    when "../pir";
                  }
                }
                description
                  "Peak burst size.";
              }
            }
          }
          container remark-dscps {
            description
              "List of remark dscp.";
            list remark-dscp {
              key "direction";
              description
                "Configure remark dscp of qos profile.";
              leaf direction {
                type qos:qos-direction-type;
                description
                  "Direction.";
              }
              leaf remark-value {
                type uint32 {
                  range "0..63";
                }
                mandatory true;
                description
                  "Value of remark dscp.";
              }
            }
          }
          container remark-8021ps {
            description
              "List of remark 8021p..";
            list remark-8021p {
              key "direction";
              description
                "Configure remark 8021p of qos profile.";
              leaf direction {
                type qos:qos-direction-type;
                description
                  "Direction.";
              }
              leaf remark-value {
                type uint32 {
                  range "0..7";
                }
                mandatory true;
                description
                  "Value of remark 8021p.";
              }
            }
          }
        }
      }
    }
    container global-config {
      description
        "Configure QoS global configuration.";
      container global-policys {
        description
          "List of traffic policy applications.";
        list global-policy {
          key "direction policy-name up-id";
          description
            "Configure the application of a traffic policy.";
          leaf direction {
            type qos-direction-type;
            description
              "Direction.";
          }
          leaf policy-name {
            type leafref {
              path "../../../../classifier-template/traffic-policys/traffic-policy/name";
            }
            must "../ucl-type='acl' or ../../../../qos:classifier-template/qos:traffic-policys/qos:traffic-policy[qos:name=current()]/qos:ipv6-fragment-inner-protocol-switch/qos:enable='false'";
            description
              "Policy name.";
          }
          leaf up-id {
            type uint32 {
              range "0 | 1024..2023 | 2048..3047 | 3072..4071 | 4096..5095";
            }
            description
              "ID of the UP connected to a vBRAS-CP. If the device is not a vBRAS-CP or no UP is specified, the value of this object is set to 0.";
          }
          leaf ucl-type {
            type qos-traffic-type;
            mandatory true;
            description
              "Policy apply based on ucl or global-acl.";
            ext:operation-exclude update {
              description "After the configuration is created, the node cannot be modified.";
            }
	  }
          leaf slot-id {
            type qos:slot-id;
            description
              "Apply slot id.";
          }
          container global-policy-statisticss {
            config false;
            description
              "List of traffic policy statistics.";
            list global-policy-statistics {
              key "slot-id";
              description
                "Traffic policy statistics.";
              leaf slot-id {
                type slot-id;
                description
                  "Slot id. The chassis ID must also be specified when have multi chassis, such as 3, clc1/3 or ccc1/3.";
              }
              leaf apply-time {
                type yang:date-and-time;
                description
                  "Time of applying a policy.";
              }
              leaf enable-time {
                type yang:date-and-time;
                description
                  "Time of enabling/disabling statistics.";
              }
              leaf clear-time {
                type yang:date-and-time;
                description
                  "Time of clearing statistics.";
              }
              leaf clear-flag {
                type boolean;
                description
                  "Enable/disable clearing statistics.";
              }
              uses policy-statistics-type;
              container classifier-statisticss {
                description
                  "List of traffic classifier statistics.";
                list classifier-statistics {
                  key "classifier-name";
                  description
                    "Traffic classifier statistics.";
                  leaf classifier-name {
                    type string {
                      length "1..127";
                    }
                    description
                      "Name of a traffic classifier.";
                  }
                  leaf stream-direction {
                    type template-name;
                    description
                      "Stream direction.";
                  }
                  leaf group-type {
                    type template-name;
                    description
                       "Bras group type.";
                  }
                  leaf group-name {
                    type template-name;
                    description
                      "Bras group name.";
                  }
                  leaf match-packets {
                    type uint64;
                    units "packet";
                    description
                      "Number of matched packets.";
                  }
                  leaf match-bytes {
                    type uint64;
                    units "Byte";
                    description
                      "Number of matched bytes.";
                  }
                  leaf match-packet-rate {
                    type uint64;
                    units "pps";
                    description
                      "Rate of matched packets.";
                  }
                  leaf match-byte-rate {
                    type uint64;
                    units "Byte/s";
                    description
                      "Rate of matched bytes.";
                  }
                  leaf match-pass-packets {
                    type uint64;
                    units "packet";
                    description
                      "Number of matched and passed packets.";
                  }
                  leaf match-pass-bytes {
                    type uint64;
                    units "Byte";
                    description
                      "Number of matched and passed bytes.";
                  }
                  leaf match-drop-packets {
                    type uint64;
                    units "packet";
                    description
                      "Number of matched but discarded packets.";
                  }
                  leaf match-drop-bytes {
                    type uint64;
                    units "Byte";
                    description
                      "Number of matched but discarded bytes.";
                  }
                  leaf match-pass-packet-rate {
                    type uint64;
                    units "pps";
                    description
                      "Rate of the packets matching the traffic classifier and passed.";
                  }
                  leaf match-pass-byte-rate {
                    type uint64;
                    units "Byte/s";
                    description
                      "Rate of the bytes matching the traffic classifier and passed.";
                  }
                  leaf match-drop-packet-rate {
                    type uint64;
                    units "pps";
                    description
                      "Rate of the packets matching the traffic classifier but discarded.";
                  }
                  leaf match-drop-byte-rate {
                    type uint64;
                    units "Byte/s";
                    description
                      "Rate of the bytes matching the traffic classifier but discarded.";
                  }
                  leaf filter-packets {
                    type uint64;
                    units "packet";
                    description
                      "Number of filtered packets.";
                  }
                  leaf filter-bytes {
                    type uint64;
                    units "Byte";
                    description
                      "Number of filtered bytes.";
                  }
                  leaf filter-paket-rate {
                    type uint64;
                    units "pps";
                    description
                      "Rate of filtered packets.";
                  }
                  leaf filter-byte-rate {
                    type uint64;
                    units "Byte/s";
                    description
                      "Rate of filtered bytes.";
                  }
                  leaf urpf-drop-packets {
                    type uint64;
                    units "packet";
                    description
                      "Number of the discarded packets by URPF check.";
                  }
                  leaf urpf-drop-bytes {
                    type uint64;
                    units "Byte";
                    description
                      "Number of the discarded bytes by URPF check.";
                  }
                  leaf urpf-drop-packet-rate {
                    type uint64;
                    units "pps";
                    description
                      "Rate of the discarded packets by URPF check.";
                  }
                  leaf urpf-drop-byte-rate {
                    type uint64;
                    units "Byte/s";
                    description
                      "Rate of the discarded bytes by URPF check.";
                  }
                  leaf car-packets {
                    type uint64;
                    units "packet";
                    description
                      "Number of the processed packets by CAR.";
                  }
                  leaf car-bytes {
                    type uint64;
                    units "Byte";
                    description
                      "Number of the processed bytes by CAR.";
                  }
                  leaf car-packet-rate {
                    type uint64;
                    units "pps";
                    description
                      "Rate of the passed packets by CAR.";
                  }
                  leaf car-byte-rate {
                    type uint64;
                    units "Byte/s";
                    description
                      "Rate of the passed bytes by CAR.";
                  }
                  leaf car-pass-packets {
                    type uint64;
                    units "packet";
                    description
                      "Number of the passed packets by CAR.";
                  }
                  leaf car-pass-bytes {
                    type uint64;
                    units "Byte";
                    description
                      "Number of the passed bytes by CAR.";
                  }
                  leaf car-drop-packets {
                    type uint64;
                    units "packet";
                    description
                      "Number of the discarded packets by CAR.";
                  }
                  leaf car-drop-bytes {
                    type uint64;
                    units "Byte";
                    description
                      "Number of the discarded bytes by CAR.";
                  }
                  leaf car-pass-packet-rate {
                    type uint64;
                    units "pps";
                    description
                      "Rate of the passed packets CAR.";
                  }
                  leaf car-pass-byte-rate {
                    type uint64;
                    units "Byte/s";
                    description
                      "Rate of the passed bytes by CAR.";
                  }
                  leaf car-drop-packet-rate {
                    type uint64;
                    units "pps";
                    description
                      "Rate of the discarded packets by CAR.";
                  }
                  leaf car-drop-byte-rate {
                    type uint64;
                    units "Byte/s";
                    description
                      "Rate of the discarded bytes by CAR.";
                  }
                  leaf car-green-packets {
                    type uint64;
                    units "packet";
                    description
                      "Number of green packets by CAR.";
                  }
                  leaf car-green-bytes {
                    type uint64;
                    units "Byte";
                    description
                      "Number of the bytes of green packets by CAR.";
                  }
                  leaf car-yellow-packets {
                    type uint64;
                    units "packet";
                    description
                      "Number of yellow packets by CAR.";
                  }
                  leaf car-yellow-bytes {
                    type uint64;
                    units "Byte";
                    description
                      "Number of the bytes of yellow packets by CAR.";
                  }
                  leaf car-red-packets {
                    type uint64;
                    units "packet";
                    description
                      "Number of red packets by CAR.";
                  }
                  leaf car-red-bytes {
                    type uint64;
                    units "Byte";
                    description
                      "Number of the bytes of red packets by CAR.";
                  }
                  leaf car-green-packet-rate {
                    type uint64;
                    units "pps";
                    description
                      "Rate of green packets by CAR.";
                  }
                  leaf car-green-byte-rate {
                    type uint64;
                    units "Byte/s";
                    description
                      "Rate of the bytes of green packets by CAR.";
                  }
                  leaf car-yellow-packet-rate {
                    type uint64;
                    units "pps";
                    description
                      "Rate of yellow packets by CAR.";
                  }
                  leaf car-yellow-byte-rate {
                    type uint64;
                    units "Byte/s";
                    description
                      "Rate of the bytes of yellow packets by CAR.";
                  }
                  leaf car-red-packet-rate {
                    type uint64;
                    units "pps";
                    description
                      "Rate of red packets by CAR.";
                  }
                  leaf car-red-byte-rate {
                    type uint64;
                    units "Byte/s";
                    description
                      "Rate of the bytes of red packets by CAR.";
                  }
                }
              }
              container rule-based-statisticss {
                description
                  "List of traffic rule classifier statistics.";
                list rule-based-statistics {
                  key "classifier-name traffic-policy-name ifmatch-id";
                  description
                    "Traffic classifier statistics.";
                  leaf classifier-name {
                    type leafref {
                      path "/qos/classifier-template/traffic-classifiers/traffic-classifier/name";
                    }
                    description
                      "Name of a traffic classifier.";
                  }
                  leaf traffic-policy-name {
                    type leafref {
                      path "/qos/classifier-template/traffic-policys/traffic-policy/name";
                    }
                    description
                      "Name of a traffic policy.";
                  }
                  leaf ifmatch-id {
                    type uint32 {
                      range "1..4294967295";
                    }
                    description
                      "Ifmatch-id of a traffic classifier.";
                  }
                  leaf acl-name {
                    type string {
                      length "1..63";
                    }
                    description
                      "Acl number or name.";
                  }
                  leaf rule-id {
                    type uint32 {
                      range "1..4294967295";
                    }
                    description
                      "Rule-id.";
                  }
                  leaf match-pass-packets {
                    type uint64;
                    units "packet";
                    description
                      "Number of matched and passed packets.";
                  }
                  leaf match-pass-bytes {
                    type uint64;
                    units "Byte";
                    description
                      "Number of matched and passed bytes.";
                  }
                  leaf match-drop-packets {
                    type uint64;
                    units "packet";
                    description
                      "Number of matched but discarded packets.";
                  }
                  leaf match-drop-bytes {
                    type uint64;
                    units "Byte";
                    description
                      "Number of matched but discarded bytes.";
                  }
                  leaf match-pass-patket-rate {
                    type uint64;
                    units "pps";
                    description
                      "Rate of the packets that match the policy rule and passed.";
                  }
                  leaf match-pass-byte-rate {
                    type uint64;
                    units "Byte/s";
                    description
                      "Rate of the bytes that match the policy rule and passed.";
                  }
                  leaf match-drop-patket-rate {
                    type uint64;
                    units "pps";
                    description
                      "Rate of the patkets that match the policy rule and passed.";
                  }
                  leaf match-drop-byte-rate {
                    type uint64;
                    units "Byte/s";
                    description
                      "Rate of the rates that match the policy rule and passed.";
                  }
                }
              }
            }
          }
        }
      }
      container traffic-policys {
        description
          "List of traffic policy applications.";
        list traffic-policy {
          key "direction policy-name";
          description
            "Configure the application of a traffic policy.";
          leaf direction {
            type trust-direction-type;
            description
              "Direction.";
          }
          leaf policy-name {
            type leafref {
              path "../../../../classifier-template/traffic-policys/traffic-policy/name";
            }
            description
              "Policy name.";
          }
          leaf slot-id {
            type qos:slot-id;
            description
              "Apply slot id.";
          }
        }
      }
      container traffic-policy-matchs {
        description
          "List of traffic policy match.";
        list traffic-policy-match {
          must "(((type='ip-layer-push' or type='ip-layer-pop' or type='rule-packet') and not(../traffic-policy-match[type='mpls-layer-push']) and not(../traffic-policy-match[type='mpls-layer-pop'])) or ((type='mpls-layer-push' or type='mpls-layer-pop') and not(../traffic-policy-match[type='ip-layer-push']) and not(../traffic-policy-match[type='ip-layer-pop']) and not(../traffic-policy-match[type='rule-packet'])) or (type='mpls-layer-l2-inbound' or type='protocol-mc-reserved'))";
          key "type";
          max-elements  "5";
          description
            "Configure traffic policy match.";
          leaf type {
            type policy-match-type;
            description
              "Traffic policy match type.";
          }
        }
      }
      container remark-vxlan-local-id {
        description
          "Configure remark qos vxlan-local-id enable.";
        leaf enable {
          type boolean;
          default "false";
          description
            "Enable/disable remark qos vxlan-local-id.";
        }
      }
      container diffserv-mode {
        description
          "Configure service-class mapping 8021p in diffserv mode.";
        leaf-list mapping-8021p-in-pipe-mode {
          type enumeration {
            enum "mpls-pop" {
            value 0;
            description
              "MPLS pop.";
            }
          }
          description
            "Configure service-class mapping 8021p in pipe mode.";
        }
      }
      container acl-log {
        description
          "Configure ACL log parameter. This node has default configuration.";
        leaf entry-num {
          type uint16 {
            range "1..8191";
          }
          default "256";
          description
            "Maximum of logs.";
        }
        leaf agging-time {
          type uint8 {
            range "1..60";
          }
          units "min";
          default "5";
          description
            "Statistical interval.";
        }
      }
      container global-set-queue-stat {
        description
          "Configure queue-stat interval.";
        leaf interval {
          type interval-value;
          default "5s";
          description
            "Specify the value of interval (Unit: s).";
        }
      }
      container buffer-policy-applys {
        description
          "List of buffer-policy application.";
        list buffer-policy-apply {
          key "name";
          max-elements "1";
          description
            "Configure buffer-policy application.";
          leaf name {
            type leafref {
              path "../../../../queue-scheduler-template/buffer-policys/buffer-policy/name";
            }
            description
              "Buffer-policy name.";
          }
        }
      }
      container queue-wreds {
        description
          "List of queues applying wred.";
        list queue-wred {
          must "(./speed-type='both-speed' and not (../queue-wred[service-class=current()/service-class][speed-type='low-speed']) and not(../queue-wred[service-class=current()/service-class][speed-type='high-speed'])) or (./speed-type!='both-speed' and not(../queue-wred[service-class=current()/service-class][speed-type='both-speed']))";
          key "service-class speed-type";
          max-elements  "16";
          description
            "Configure queue applying wred.";
          leaf service-class {
            type qos-service-class;
            description
              "Class of service.";
          }
          leaf speed-type {
            type speed-type;
            description
              "Speed type. The available options are high-speed, low-speed and both-speed.";
          }
          leaf wred-name {
            type leafref {
              path "../../../../wred-template/wreds/wred/name";
            }
            mandatory true;
            description
              "Wred name.";
          }
        }
      }//queue-wreds
      container low-latency-enables {
        description
          "List of low latency enable.";
        list low-latency-enable {
          key "enable-type";
          description
            "Configure low latency enable.";
          leaf enable-type {
            type low-latency-enable-type;
            description
              "Business type.";
          }
          leaf enable-value {
            type low-latency-enable-value;
            mandatory true;
            description
              "Enable type.";
          }
        }
      }
      container scheduling-modes {
        description
          "List of scheduling mode. This node has default configuration.";
        list scheduling-mode {
          key "slot-id";
          description
            "Configure scheduling mode.";
          ext:generated-by system {
            description "The configuration is generated automatically..";
          }
          ext:operation-exclude create {
            description "The configuration cannot be created.";
          }
          leaf slot-id {
            type slot-id;
            description
              "Slot id. The chassis ID must also be specified when have multi chassis, such as 3, clc1/3 or ccc1/3.";
          }
          leaf mode-type {
            type scheduling-mode-type;
            mandatory true;
            description
              "Mode type.";
          }
        }
      }
      container convergence-schedule {
        description
          "Configure convergence schedule mode.";
        leaf mode {
          type convergence-schedule-mode;
          description
            "Convergence schedule. The mode can only change once in one minute.";
        }
      }
      container port-convergence-schedule {
        description
          "Configure port schedule convergence mode.";
        leaf mode {
          type port-convergence-schedule-mode;
          description
            "Port Schedule Convergence.";
        }
      }
      container traffic-policy-untag {
        description
          "Configure policy rule match VLAN.";
        leaf untag-type {
          type traffic-policy-untag-type;
          description
            "Match type.";
        }
      }
      container host-packets {
        description
          "List of host packet.";
        list host-packet {
          key "dscp";
          description
            "Configure host packet.";
          leaf dscp {
            type uint32 {
              range "0..63";
            }
            description
              "Priority value.";
          }
          leaf service-class {
            type qos-service-class;
            mandatory true;
            description
              "Class of service.";
          }
          leaf color {
            type qos-color;
            mandatory true;
            description
              "Color marked to the data flows after measurement.";
          }
        }
      }
      container exp-phb-disable {
        description
          "Configure to disable the private network tag priority in a DS domain from being marked for the downstream traffic on the PW interface in the VLL networking.";
        leaf forward-type {
          type forward-type;
          description
            "Forward type.";
        }
      }
      container packs {
        description
          "List of packaging function.";
        list pack {
          key "slot-id";
          description
            "Configure packaging function.";
          leaf slot-id {
            type slot-id;
            description
              "Slot id.";
          }
          leaf switch-flag {
            type switch-flag;
            mandatory true;
            description
              "Switch flag.";
          }
        }
      }
      container packet-block-threshold-all {
        description
          "Configure the packet block threshold size for all queues.";
        leaf size {
          type uint8 {
            range "0..5";
          }
          units "kB";
          description
            "The packet block threshold size.";
        }
      }
      container burst-sizes {
        description
          "List of the burst size of a chip.";
        list burst-size {
          key "service-class";
          max-elements  "8";
          description
            "Configure the burst size of a chip.";
          leaf service-class {
            type qos-service-class;
            description
              "Class of service.";
          }
          leaf value {
            type uint8 {
              range "0..64";
            }
            mandatory true;
            description
              "Burst size.";
          }
        }
      }
      container tm-schedule-traffic-statistics-enables {
        description
          "List of configuration which enables to collect packet statistics based on accuracy compensated lengths.";
        list tm-schedule-traffic-statistics-enable {
          key "slot-id card-id";
          description
            "Configure collecting packet statistics based on accuracy compensated lengths.";
          leaf slot-id {
            type slot-id;
            description
              "Slot id.";
          }
          leaf card-id {
            type string {
              length "1..32";
            }
            description
              "Card id.";
          }
        }
      }
      container redback-packet-adjustment {
        presence "create redback-packet-adjustment";
        description
          "Enable/disable redback packet adjustment on the device.";
        leaf user-type {
          type user-type;
          mandatory true;
          description
            "User type.";
        }
      }
      container redback-packet-adjustment-slots {
        description
          "List of redback packet adjustment on the slot.";
        list redback-packet-adjustment-slot {
          key "slot-id";
          description
            "Configure redback packet adjustment on the slot.";
          leaf slot-id {
            type slot-id;
            description
              "Slot id.";
          }
          leaf user-type {
            type user-type;
            mandatory true;
            description
              "User type.";
          }
        }
      }
      container link-layer-excludes {
        description
          "List of configuration which enables CAR and statistics for Layer 3 packets on the device.";
        list link-layer-exclude {
          key "access-type";
          description
            "Configure enabling CAR and statistics for Layer 3 packets on the device.";
          leaf access-type {
            type access-type;
            description
              "Access type.";
          }
        }
      }
      container link-layer-exclude-slots {
        description
          "List of configuration which enables CAR and statistics for Layer 3 packets on the slot.";
        list link-layer-exclude-slot {
          key "slot-id access-type";
          description
            "Configure enabling CAR and statistics for Layer 3 packets on the slot.";
          leaf slot-id {
            type slot-id;
            description
              "Slot ID.";
          }
          leaf access-type {
            type access-type;
            description
              "Access type.";
          }
        }
      }
      container l2tp-layer-exclude {
        presence "create l2tp-layer-exclude";
        description
          "Enable/disable CAR and statistics for Layer 3 packets on the device only for L2TP users.";
        leaf l2tp-user {
          type l2tp-user;
          mandatory true;
          description
            "L2TP user.";
        }
      }
      container l2tp-layer-exclude-slots {
        description
          "List of configuration which enables CAR and statistics for Layer 3 packets on the slot only for L2TP users.";
        list l2tp-layer-exclude-slot {
          key "slot-id";
          description
            "Configure enabling CAR and statistics for Layer 3 packets on the slot only for L2TP users.";
          leaf slot-id {
            type slot-id;
            description
              "Slot ID.";
          }
        }
      }
      container burst-modes {
        description
          "List of configure the burst traffic buffer mode on a switch.";
        list burst-mode {
          key "slot-id";
          description
            "Configure burst mode.";          
          leaf slot-id {
            type slot-id {
              pattern "[0-9]|[1-4][0-9]";
            }
            description
              "Slot ID. If the burst traffic buffer mode can only be configured globally on the device, the slot ID must be 0.";
          }
          leaf mode {
            type qos:burst-mode-type;
            mandatory true;
            description
              "Mode type.";
          }
        }
      }
      container multicast-burst-modes {
        description
          "List of configure the burst multicast traffic buffer mode on a switch.";
        list multicast-burst-mode {
          key "slot-id";
          description
            "Configure multicast burst mode.";          
          leaf slot-id {
            type slot-id {
              pattern "[0-9]|[1-4][0-9]";
            }
            description
              "Slot ID. If the burst traffic buffer mode can only be configured globally on the device, the slot ID must be 0.";
          }
          leaf mode {
            type qos:burst-mode-type;
            mandatory true;
            description
              "Mode type.";
          }
        }
      }
      container traffic-class {
        description
          "Configure the protocol packets sent by local device.";
        leaf priority {
          type uint8 {
            range "0..7";
          }
          description
            "Configure the internal priority of protocol packets sent by local device.";
        }
      }
      container queue-buffer-alarms-enable {
        description
          "Configure the device to generate an alarm when the queue buffer exceeds the threshold.";
        leaf enable {
          type buff-alarm-type;
		  default "false";
          description
            "Enables/Disables.";
        }
      }
      container queue-buffer-overrun-threshold {
        description
          "Configure the threshold for the percentage of device traffic to the maximum queue buffer.";
        leaf overrun-limit {
          type uint32 {
            range "1..100";
          }
          units "%";
          default "90";
          description
            "The threshold for the percentage of device traffic to the maximum queue buffer.";
        }
      }
	  container car-ifg {
        description
          "Configure the device not to count the inter-frame gap and preamble of packets when the device calculates and statistics the traffic policing rate or rate limit of an interface.";
        leaf mode {
		    type switch-flag;
			default "enable";
			description
			  "Enables/Disables.";
        }
      }
      container user-queue-resource-8cos-enhances {
        description
          "List of 8 CoS enhance size configuration.";
        list user-queue-resource-8cos-enhance {
          key "direction";
          max-elements "2";
          description
            "Configure 8 CoS enhance size.";
          leaf direction {
            type qos-direction-type;
            description
              "Direction.";
          }
          leaf cos-value {
            type uint32 {
              range "4..1000";
            }
            must "../cos-value mod 4 = 0";
            mandatory true;
            description
              "CoS value.";
          }
        }
      }
      container user-queue-pir-exhaust-alarm {
        description
          "Configure user-queue PIR exhaust alarm.";
        leaf enable {
          type boolean;
          default "false";
          description
            "Enable/disable user-queue PIR exhaust alarm.";
        }
      }
      container queue-discard-alarms {
        description "List of queue discard alarm.";
        list queue-discard-alarm {
          key "service-class";
          max-elements "8";
          description
            "Configure queue discard alarm.";
          leaf service-class {
            type qos:qos-service-class;
            description
              "Class of service.";
          }
          choice discard-type {
            mandatory true;
            description
               "Specify discard type.";
            case bytes {
              description
                "Specify discard type choice case as discard-byte.";
              leaf bytes {
                type uint32 {
                  range "1..4294967295";
                }
                units "Byte";
                mandatory true;
                description
                  "The discarded bytes.";
              }
            }
            case packets {
              description
                "Specify discard type choice case as discard packet.";
              leaf packets {
                type uint32 {
                  range "1..4294967295";
                }
                units "packet";
                mandatory true;
                description
                  "The discarded packets.";
              }
            }
            case packet-ratio {
              description
                "Specify discard type choice case as discard packet ratio.";
              leaf packet-coefficient {
                type uint8 {
                  range "1..9";
                }
                mandatory true;
                description
                  "Ratio coefficient of the discard packets.";
              }
              leaf packet-exponent {
                type uint8 {
                  range "1..5";
                }
                mandatory true;
                description
                  "Ratio exponent of the discard packets.";
              }
            }
          }
          leaf interval-time {
            type uint16 {
              range "15..3600";
            }
            units "s";
            default "30";
            description
              "Monitoring time of the queue discard alarm.";
          }
          leaf repeat-count {
            type uint32 {
              range "2..10";
            }
            description
              "Repeat count of alarm threshold reached.";
          }
        }
      }
      container rate-limiting-overhead {
        description
          "Configure the method for calculating the packet length during traffic policing or traffic shaping.";
        leaf shaping-car-layer {
          type encapsulation-layer;
          must "../../car-ifg/mode!='disable'";
          default "physic";
          description
            "Encapsulation layer:support link or physic.";
        }
      }
      container traffic-policy-protocol-protects {
        description
          "List of acl protocol protect.";
        list traffic-policy-protocol-protect {
          key "protocol-family";
          description
            "Configure acl protocol protect.";
          leaf protocol-family {
            type enumeration {
              enum ipv4 {
                value 0;
                description
                  "Protocol IPv4.";
              }
              enum ipv6 {
                value 1;
                description
                  "Protocol IPv6.";
              }
            }
            description
              "Protocol family.";
          }
        }
      }
      container network-slice {
        description
          "Configure network slice.";
        leaf bandwidth-mode {
          type qos:bandwidth-mode-type;
          default "exclusive";
          description
            "Configure network slice bandwidth mode.";
        }
      }
      container traffic-policy {
        description
          "Configure traffic policy global configuration.";
        leaf large-acl-mode {
          type empty;
          description
            "Enable/disable traffic large acl mode.";
        }
      }
      container auto-buffer {
        description
          "Configure buffer auto configure.";
        leaf enable {
          type boolean;
          default "true";
          description
            "Enable/disable buffer auto configure.";
        }
      }
    }//global-config
    container global-query {
      config false;
      description
        "QoS global state.";
      container default-queue-statisticss {
        description
          "List of default queue statistics collected by telemetry.";
        list default-queue-statistics {
          key "interface-name service-class";
          description
            "Statistics of default queue collected by telemetry.";
          leaf interface-name {
          type leafref {
            path "/ifm:ifm/ifm:interfaces/ifm:interface/ifm:name";
          }
          description
            "Interface name.";
          }
          leaf service-class {
          type qos-service-class;
          description
            "Service class.";
          }
          leaf dropped-packets {
          type uint64;
          units "packet";
          description
            "Dropped packets.";
          }
          leaf dropped-bytes {
          type uint64;
          units "Byte";
          description
            "Dropped bytes.";
          }
          leaf passed-pps {
          type uint64;
          units "pps";
          description
            "Passed pps.";
          }
          leaf passed-bps {
          type uint64;
          units "bit/s";
          description
            "Passed bps.";
          }
          leaf total-packets {
          type uint64;
          units "packet";
          description
            "Total packets.";
          }
          leaf total-bytes {
          type uint64;
          units "Byte";
          description
            "Total bytes.";
          }
          leaf total-buffer {
          type uint32;
          units "kB";
          description
            "Total buffer.";
          }
          leaf current-buffer {
          type uint32;
          units "kB";
          description
            "Current buffer.";
          }
          leaf buffer-percent {
          type uint32;
          units "%";
          description
            "Buffer percent.";
          }
          leaf max-buffer-percent {
          type uint32;
          units "%";
          description
            "Max buffer percent.";
          }
          leaf buffer-time {
          type uint64;
          units "s";
          description
            "Buffer time.";
          }
          leaf clean-time {
          type uint64;
          units "s";
          description
            "Clean time.";
          }
        }
      }
      container all-queue-statisticss {
        description
          "List of all queue statistics collected by telemetry.";
        list all-queue-statistics {
          key "interface-name service-class";
          description
            "Statistics of all queue collected by telemetry.";
          leaf interface-name {
          type leafref {
            path "/ifm:ifm/ifm:interfaces/ifm:interface/ifm:name";
          }
          description
            "Interface name.";
          }
          leaf service-class {
          type qos-service-class;
          description
            "Service class.";
          }
          leaf dropped-packets {
          type uint64;
          units "packet";
          description
            "Dropped packets.";
          }
          leaf dropped-bytes {
          type uint64;
          units "Byte";
          description
            "Dropped bytes.";
          }
          leaf passed-pps {
          type uint64;
          units "pps";
          description
            "Passed pps.";
          }
          leaf passed-bps {
          type uint64;
          units "bit/s";
          description
            "Passed bps.";
          }
          leaf total-packets {
          type uint64;
          units "packet";
          description
            "Total packets.";
          }
          leaf total-bytes {
          type uint64;
          units "Byte";
          description
            "Total bytes.";
          }
        }
      }
      container channel-queue-statisticss {
        description
          "List of channelized sub-interface queue statistics collected by telemetry.";
        list channel-queue-statistics {
          key "interface-name service-class";
          description
            "Statistics of channelized sub-interface queue collected by telemetry.";
          leaf interface-name {
          type leafref {
            path "/ifm:ifm/ifm:interfaces/ifm:interface/ifm:name";
          }
          description
            "Interface name.";
          }
          leaf service-class {
          type qos-service-class;
          description
            "Service class.";
          }
          leaf dropped-packets {
          type uint64;
          units "packet";
          description
            "Dropped packets.";
          }
          leaf dropped-bytes {
          type uint64;
          units "Byte";
          description
            "Dropped bytes.";
          }
          leaf passed-pps {
          type uint64;
          units "pps";
          description
            "Passed pps.";
          }
          leaf passed-bps {
          type uint64;
          units "bit/s";
          description
            "Passed bps.";
          }
          leaf total-packets {
          type uint64;
          units "packet";
          description
            "Total packets.";
          }
          leaf total-bytes {
          type uint64;
          units "Byte";
          description
            "Total bytes.";
          }
          leaf total-buffer {
          type uint32;
          units "kB";
          description
            "Total buffer.";
          }
          leaf current-buffer {
          type uint32;
          units "kB";
          description
            "Current buffer.";
          }
          leaf buffer-percent {
          type uint32;
          units "%";
          description
            "Buffer percent.";
          }
          leaf max-buffer-percent {
          type uint32;
          units "%";
          description
            "Max buffer percent.";
          }
          leaf buffer-time {
          type uint64;
          units "s";
          description
            "Buffer time.";
          }
          leaf clean-time {
          type uint64;
          units "s";
          description
            "Clean time.";
          }
        }
      }
      container mode-flexe-queue-statisticss {
        description
          "List of flexe channel sub-interface queue statistics collected by telemetry.";
        list mode-flexe-queue-statistics {
          key "interface-name service-class";
          description
            "Statistics of flexe channel sub-interface queue collected by telemetry.";
          leaf interface-name {
          type leafref {
            path "/ifm:ifm/ifm:interfaces/ifm:interface/ifm:name";
          }
          description
            "Interface name.";
          }
          leaf service-class {
          type qos-service-class;
          description
            "Service class.";
          }
          leaf dropped-packets {
          type uint64;
          units "packet";
          description
            "Dropped packets.";
          }
          leaf dropped-bytes {
          type uint64;
          units "Byte";
          description
            "Dropped bytes.";
          }
          leaf passed-pps {
          type uint64;
          units "pps";
          description
            "Passed pps.";
          }
          leaf passed-bps {
          type uint64;
          units "bit/s";
          description
            "Passed bps.";
          }
          leaf total-packets {
          type uint64;
          units "packet";
          description
            "Total packets.";
          }
          leaf total-bytes {
          type uint64;
          units "Byte";
          description
            "Total bytes.";
          }
          leaf total-buffer {
          type uint32;
          units "kB";
          description
            "Total buffer.";
          }
          leaf current-buffer {
          type uint32;
          units "kB";
          description
            "Current buffer.";
          }
          leaf buffer-percent {
          type uint32;
          units "%";
          description
            "Buffer percent.";
          }
          leaf max-buffer-percent {
          type uint32;
          units "%";
          description
            "Max buffer percent.";
          }
          leaf buffer-time {
          type uint64;
          units "s";
          description
            "Buffer time.";
          }
          leaf clean-time {
          type uint64;
          units "s";
          description
            "Clean time.";
          }
        }
      }
      container user-informations {
        description
          "List of QoS user information.";
        list user-information {
          key "id direction";
          description
            "QoS user state.";
          leaf id {
            type uint32 {
              range "0..4294967294";
            }
            description
              "User id.";
          }
          leaf direction {
            type qos-direction-type;
            description
              "Direction.";
          }
          container user-queue-statisticss {
            description
              "List of user queue statistics.";
            list user-queue-statistics {
              key "service-class";
              description
                "User queue statistics.";
              leaf service-class {
                type hqos-service-class;
                description
                  "Service class.";
              }
              leaf pass-packet-rate {
                type uint64;
                units "pps";
                description
                  "Pass packet rate.";
              }
              leaf pass-byte-rate {
                type uint64;
                units "Byte/s";
                description
                  "Pass byte rate.";
              }
              leaf pass-packets {
                type uint64;
                units "packet";
                description
                  "Pass packets.";
              }
              leaf pass-bytes {
                type uint64;
                units "Byte";
                description
                  "Pass bytes.";
              }
              leaf discard-packet-rate {
                type uint64;
                units "pps";
                description
                  "Discard packet rate.";
              }
              leaf discard-byte-rate {
                type uint64;
                units "Byte/s";
                description
                  "Discard byte rate.";
              }
              leaf discard-packets {
                type uint64;
                units "packet";
                description
                  "Discard packets.";
              }
              leaf discard-bytes {
                type uint64;
                units "Byte";
                description
                  "Discard bytes.";
              }
              leaf pass-peak-packet-time {
                type yang:date-and-time;
                description
                  "Pass peak packet time.";
              }
              leaf pass-peak-packet-rate {
                type uint64;
                units "pps";
                description
                  "Pass peak packet rate.";
              }
              leaf pass-peak-byte-time {
                type yang:date-and-time;
                description
                  "Pass peak byte time.";
              }
              leaf pass-peak-byte-rate {
                type uint64;
                units "Byte/s";
                description
                  "Pass peak byte rate.";
              }
              leaf drop-peak-packet-time {
                type yang:date-and-time;
                description
                  "Wred drop peak packet time.";
              }
              leaf drop-peak-packet-rate {
                type uint64;
                units "pps";
                description
                  "Wred drop peak packet rate.";
              }
              leaf drop-peak-byte-time {
                type yang:date-and-time;
                description
                  "Wred drop peak byte time.";
              }
              leaf drop-peak-byte-rate {
                type uint64;
                units "Byte/s";
                description
                  "Wred drop peak byte rate.";
              }
              leaf tail-peak-packet-time {
                type yang:date-and-time;
                description
                  "Tail drop peak packet time.";
              }
              leaf tail-peak-packet-rate {
                type uint64;
                units "pps";
                description
                  "Tail drop peak packet rate.";
              }
              leaf tail-peak-byte-time {
                type yang:date-and-time;
                description
                  "Tail drop peak byte time.";
              }
              leaf tail-peak-byte-rate {
                type uint64;
                units "Byte/s";
                description
                  "Tail drop peak byte rate.";
              }
            }
          }
          container car-statisticss {
            description
              "List of CAR statistics.";
            list car-statistics {
              key "resource-type";
              description
                "CAR statistics.";
              leaf resource-type {
                type qos-res-type;
                description
                  "Resource type.";
              }
              leaf pass-packet-rate {
                type uint64;
                units "pps";
                description
                  "Pass packet rate.";
              }
              leaf pass-byte-rate {
                type uint64;
                units "Byte/s";
                description
                  "Pass byte rate.";
              }
              leaf pass-packets {
                type uint64;
                units "packet";
                description
                  "Pass packets.";
              }
              leaf pass-bytes {
                type uint64;
                units "Byte";
                description
                  "Pass bytes.";
              }
              leaf discard-packet-rate {
                type uint64;
                units "pps";
                description
                  "Discard packet rate.";
              }
              leaf discard-byte-rate {
                type uint64;
                units "Byte/s";
                description
                  "Discard byte rate.";
              }
              leaf discard-packets {
                type uint64;
                units "packet";
                description
                  "Discard packets.";
              }
              leaf discard-bytes {
                type uint64;
                units "Byte";
                description
                  "Discard bytes.";
              }
              leaf pass-peak-packet-time {
                type yang:date-and-time;
                description
                  "Pass peak packet time of L2 or L3V4.";
              }
              leaf pass-peak-packet-rate {
                type uint64;
                units "pps";
                description
                  "Pass peak packet rate of L2 or L3V4.";
              }
              leaf pass-peak-byte-time {
                type yang:date-and-time;
                description
                  "Pass peak byte time of L2 or L3V4.";
              }
              leaf pass-peak-byte-rate {
                type uint64;
                units "Byte/s";
                description
                  "Pass peak byte rate of L2 or L3V4.";
              }
              leaf drop-peak-packet-time {
                type yang:date-and-time;
                description
                  "Drop peak packet time of L2 or L3V4.";
              }
              leaf drop-peak-packet-rate {
                type uint64;
                units "pps";
                description
                  "Drop peak packet rate of L2 or L3V4.";
              }
              leaf drop-peak-byte-time {
                type yang:date-and-time;
                description
                  "Drop peak byte time of L2 or L3V4.";
              }
              leaf drop-peak-byte-rate {
                type uint64;
                units "Byte/s";
                description
                  "Drop peak byte rate of L2 or L3V4.";
              }
              leaf v6-pass-peak-packet-time {
                type yang:date-and-time;
                description
                  "Pass peak packet time of L3V6.";
              }
              leaf v6-pass-peak-packet-rate {
                type uint64;
                units "pps";
                description
                  "Pass peak packet rate of L3V6.";
              }
              leaf v6-pass-peak-byte-time {
                type yang:date-and-time;
                description
                  "Pass peak byte time of L3V6.";
              }
              leaf v6-pass-peak-byte-rate {
                type uint64;
                units "Byte/s";
                description
                  "Pass peak byte rate of L3V6.";
              }
              leaf v6-tail-peak-packet-time {
                type yang:date-and-time;
                description
                  "Tail drop peak packet time of L3V6.";
              }
              leaf v6-tail-peak-packet-rate {
                type uint64;
                units "pps";
                description
                  "Tail drop peak packet rate of L3V6.";
              }
              leaf v6-tail-peak-byte-time {
                type yang:date-and-time;
                description
                  "Tail drop peak byte time of L3V6.";
              }
              leaf v6-tail-peak-byte-rate {
                type uint64;
                units "Byte/s";
                description
                  "Tail drop peak byte rate of L3V6.";
              }
            }
          }
          container flow-queue-infos {
            description
              "List of flow queue information.";
            list flow-queue-info {
              key "service-class";
              description
                "Flow queue state.";
              leaf service-class {
                type hqos-service-class;
                description
                  "Service class.";
              }
              leaf schedule-type {
                type queue-schedule-mode;
                description
                  "Schedule type.";
              }
              leaf weight {
                type uint8;
                description
                  "Weight.";
              }
              leaf shaping {
                type uint32;
                units "kbit/s";
                description
                  "Shaping.";
              }
              leaf priority {
                type uint8;
                description
                  "Priority.";
              }
            }
          }
          container cir-info {
            description 
            "Committed information rate and Peak information rate state.";
            leaf cir {
              type uint32;
              units "kbit/s";
              description
                "Committed information rate.";
            }
            leaf pir {
              type uint32;
              units "kbit/s";
              description
                "Peak information rate.";
            }
          }
        }
      }
      container interface-traffic-policy-statisticss {
        description
        "List of traffic policy statistics of interface.";
        list interface-traffic-policy-statistics {
          key "interface-name pe-vlan-id vlan-id direction slot-id";
          description
            "Traffic policy statistics.";
          leaf interface-name {
            type leafref {
              path "/ifm:ifm/ifm:interfaces/ifm:interface/ifm:name";
            }
            description
              "Interface name.";
          }
          leaf pe-vlan-id {
            type uint16 {
              range "0..4094";
            }
            description
              "Pe VLAN id.";
          }
          leaf vlan-id {
            type uint16 {
              range "0..4094";
            }
            description
              "VLAN id.";
          }
          leaf direction {
            type qos-direction-type;
            description
              "Direction.
              If this field is unnecessary, the controller can set a default value both.";
          }
          leaf slot-id {
            type slot-id;
            description
              "Slot id. The chassis id must also be specified when have multi chassis, such as 3, clc1/3 or ccc1/3.";
          }
          leaf traffic-policy-name {
            type string {
              length "1..127";
            }
            description
              "Policy name.";
          }
          leaf multi-policy-mode {
            type boolean;
            description
              "Enabled/disabled multiple policys.";
          }
          leaf apply-time {
            type yang:date-and-time;
            description
              "Time of applying a policy.";
          }
          leaf switch-status {
            type statistics-switch-status;
            description
              "Status of enabling/disabling statistics.";
          }
          leaf switch-time {
            type yang:date-and-time;
            description
              "Time of enabling/disabling statistics.";
          }
          leaf clear-time {
            type yang:date-and-time;
            description
              "Time of clearing statistics.";
          }
          leaf clear-flag {
            type boolean;
            description
              "Enable/disable clearing statistics.";
          }
          uses policy-statistics-type;
          container rule-based-staticss {
            description
              "List of traffic rule classifier statistics.";
            list rule-based-statics {
              key "classifier-name traffic-policy-name service-type ifmatch-id rule-id";
              description
                "Traffic classifier statistics.";
              leaf classifier-name {
                type leafref {
                  path "/qos/classifier-template/traffic-classifiers/traffic-classifier/name";
                }
                description
                  "Name of a traffic classifier.";
              }
              leaf traffic-policy-name {
                type leafref {
                  path "/qos/classifier-template/traffic-policys/traffic-policy/name";
                }
                description
                  "Name of a traffic policy.";
              }
              leaf service-type {
                type qos-rule-service-type;
                description
                  "Service type.";
              }
              leaf ifmatch-id {
                type uint32 {
                  range "1..4294967295";
                }
                description
                  "Ifmatch-id of a traffic classifier.";
              }
              leaf rule-id {
                type uint32 {
                  range "0..4294967295";
                }
                description
                  "Rule-id.";
              }
              leaf acl-name {
                type string {
                  length "1..63";
                }
                description
                  "Acl number or name.";
              }
              leaf protocol-family {
                type protocol-family;
                description
                  "IP protocol version.";
              }
              leaf match-pass-packets {
                type uint64;
                units "packet";
                description
                  "Number of matched and passed packets.";
              }
              leaf match-pass-bytes {
                type uint64;
                units "Byte";
                description
                  "Number of matched and passed bytes.";
              }
              leaf match-drop-packets {
                type uint64;
                units "packet";
                description
                  "Number of matched but discarded packets.";
              }
              leaf match-drop-bytes {
                type uint64;
                units "Byte";
                description
                  "Number of matched but discarded bytes.";
              }
              leaf match-pass-patket-rate {
                type uint64;
                units "pps";
                description
                  "Rate of the packets that match the policy rule and passed.";
              }
              leaf match-pass-byte-rate {
                type uint64;
                units "Byte/s";
                description
                  "Rate of the bytes that match the policy rule and passed.";
              }
              leaf match-drop-patket-rate {
                type uint64;
                units "pps";
                description
                  "Rate of the patkets that match the policy rule and passed.";
              }
              leaf match-drop-byte-rate {
                type uint64;
                units "Byte/s";
                description
                  "Rate of the rates that match the policy rule and passed.";
              }
            }
          }
          container classifier-based-staticss {
            description
              "List of action car statistics.";
            list classifier-based-statics {
              key "classifier-name traffic-policy-name";
              description
                "Action car statistics.";
              leaf classifier-name {
                type leafref {
                  path "/qos/classifier-template/traffic-classifiers/traffic-classifier/name";
                }
                description
                  "Name of a traffic classifier.";
              }
              leaf traffic-policy-name {
                type leafref {
                  path "/qos/classifier-template/traffic-policys/traffic-policy/name";
                }
                description
                  "Name of a traffic policy.";
              }
              leaf service-type {
                type qos-rule-service-type;
                description
                  "Service type.";
              }
              leaf share-mode {
                type switch-flag;
                default "enable";
                description
                  "Sharing mode. After the policy is applied, the attribute of this node cannot be changed.";
              }
              leaf match-pass-packets {
                type uint64;
                units "packet";
                description
                  "Number of matched and passed packets.";
              }
              leaf match-pass-bytes {
                type uint64;
                units "Byte";
                description
                  "Number of matched and passed bytes.";
              }
              leaf match-drop-packets {
                type uint64;
                units "packet";
                description
                  "Number of matched but discarded packets.";
              }
              leaf match-drop-bytes {
                type uint64;
                units "Byte";
                description
                  "Number of matched but discarded bytes.";
              }
              leaf match-pass-patket-rate {
                type uint64;
                units "pps";
                description
                  "Rate of the packets that match the policy rule and passed.";
              }
              leaf match-pass-byte-rate {
                type uint64;
                units "Byte/s";
                description
                  "Rate of the bytes that match the policy rule and passed.";
              }
              leaf match-drop-patket-rate {
                type uint64;
                units "pps";
                description
                  "Rate of the patkets that match the policy rule and passed.";
              }
              leaf match-drop-byte-rate {
                type uint64;
                units "Byte/s";
                description
                  "Rate of the rates that match the policy rule and passed.";
              }
            }
          }
		  container classifier-statisticss {
            description
              "List of traffic classifier statistics.";
            list classifier-statistics {
              key "classifier-name";
              description
                "Traffic classifier statistics.";
              leaf classifier-name {
                type string {
                  length "1..127";
                }
                description
                  "Name of a traffic classifier.";
              }
              uses classifier-statistics-type;
              leaf unknownunisup-pass-packets {
                type uint64;
                units "packet";
                description
                  "Number of the passed packets by Unknown Unicast Suppression.";
              }
              leaf unknownunisup-pass-bytes {
                type uint64;
                units "Byte";
                description
                  "Number of the passed bytes by Unknown Unicast Suppression.";
              }
              leaf unknownunisup-pass-packet-rate {
                type uint64;
                units "pps";
                description
                  "Rate of the passed packets Unknown Unicast Suppression.";
              }
              leaf unknownunisup-pass-byte-rate {
                type uint64;
                units "Byte/s";
                description
                  "Rate of the passed bytes by Unknown Unicast Suppression.";
              }
              leaf unknownunisup-drop-packets {
                type uint64;
                units "packet";
                description
                  "Number of the discarded packets by Unknown Unicast Suppression.";
              }
              leaf unknownunisup-drop-bytes {
                type uint64;
                units "Byte";
                description
                  "Number of the discarded bytes by Unknown Unicast Suppression.";
              }
              leaf unknownunisup-drop-packet-rate {
                type uint64;
                units "pps";
                description
                  "Rate of the discarded packets by Unknown Unicast Suppression.";
              }
              leaf unknownunisup-drop-byte-rate {
                type uint64;
                units "Byte/s";
                description
                  "Rate of the discarded bytes by Unknown Unicast Suppression.";
              }
              leaf multicastsup-pass-packets {
                type uint64;
                units "packet";
                description
                  "Number of the passed packets by Multicast Suppression.";
              }
              leaf multicastsup-pass-bytes {
                type uint64;
                units "Byte";
                description
                  "Number of the passed bytes by Multicast Suppression.";
              }
              leaf multicastsup-pass-packet-rate {
                type uint64;
                units "pps";
                description
                  "Rate of the passed packets Multicast Suppression.";
              }
              leaf multicastsup-pass-byte-rate {
                type uint64;
                units "Byte/s";
                description
                  "Rate of the passed bytes by Multicast Suppression.";
              }
              leaf multicastsup-drop-packets {
                type uint64;
                units "packet";
                description
                  "Number of the discarded packets by Multicast Suppression.";
              }
              leaf multicastsup-drop-bytes {
                type uint64;
                units "Byte";
                description
                  "Number of the discarded bytes by Multicast Suppression.";
              }
              leaf multicastsup-drop-packet-rate {
                type uint64;
                units "pps";
                description
                  "Rate of the discarded packets by Multicast Suppression.";
              }
              leaf multicastsup-drop-byte-rate {
                type uint64;
                units "Byte/s";
                description
                  "Rate of the discarded bytes by Multicast Suppression.";
              }
              leaf broadcastsup-pass-packets {
                type uint64;
                units "packet";
                description
                  "Number of the passed packets by Broadcast Suppression.";
              }
              leaf broadcastsup-pass-bytes {
                type uint64;
                units "Byte";
                description
                  "Number of the passed bytes by Broadcast Suppression.";
              }
              leaf broadcastsup-pass-packet-rate {
                type uint64;
                units "pps";
                description
                  "Rate of the passed packets Broadcast Suppression.";
              }
              leaf broadcastsup-pass-byte-rate {
                type uint64;
                units "Byte/s";
                description
                  "Rate of the passed bytes by Broadcast Suppression.";
              }
              leaf broadcastsup-drop-packets {
                type uint64;
                units "packet";
                description
                  "Number of the discarded packets by Broadcast Suppression.";
              }
              leaf broadcastsup-drop-bytes {
                type uint64;
                units "Byte";
                description
                  "Number of the discarded bytes by Broadcast Suppression.";
              }
              leaf broadcastsup-drop-packet-rate {
                type uint64;
                units "pps";
                description
                  "Rate of the discarded packets by Broadcast Suppression.";
              }
              leaf broadcastsup-drop-byte-rate {
                type uint64;
                units "Byte/s";
                description
                  "Rate of the discarded bytes by Broadcast Suppression.";
              }
            }
          }
          container multi-policy-statisticss {
            description
              "List of multiple traffic policy statistics for interface.";
            list multi-policy-statistics {
              key "traffic-policy-name";
              description
                "Multiple traffic policy statistics for interface.";
              leaf traffic-policy-name {
                type leafref {
                  path "/qos:qos/qos:classifier-template/qos:traffic-policys/qos:traffic-policy/qos:name";
                }
                description
                  "Policy name.";
              }
              leaf apply-time {
                type yang:date-and-time;
                description
                  "Time of applying a policy.";
              }
              leaf switch-status {
                type statistics-switch-status;
                description
                  "Status of enabling/disabling statistics.";
              }
              leaf switch-time {
                type yang:date-and-time;
                description
                  "Time of enabling/disabling statistics.";
              }
              leaf clear-time {
                type yang:date-and-time;
                description
                  "Time of clearing statistics.";
              }
              leaf clear-flag {
                type boolean;
                description
                  "Enable/disable clearing statistics.";
              }
              uses multi-policy-statistics-type;
              container classifier-statisticss {
                description
                  "List of traffic classifier statistics.";
                list classifier-statistics {
                  key "classifier-name";
                  description
                    "Traffic classifier statistics.";
                  leaf classifier-name {
                    type string {
                      length "1..127";
                    }
                    description
                      "Name of a traffic classifier.";
                  }
                  uses multi-policy-classifier-statistics-type;
                }
              }
            }
          }
        }
      }
      container interface-classifier-statisticss {
        description
          "List of interface traffic classifier statistics.";
        list interface-classifier-statistics {
          key "interface-name classifier-name policy-name direction slot-id";
            description
            "Statistics of traffic classifier statistics for interface.";
          leaf interface-name {
            type leafref {
              path "/ifm:ifm/ifm:interfaces/ifm:interface/ifm:name";
            }
              description
              "Interface name.";
          }
          leaf classifier-name {
            type string {
              length "1..127";
            }
            description
              "Name of a traffic classifier.";
          }
          leaf policy-name {
            type leafref {
              path "/qos:qos/qos:classifier-template/qos:traffic-policys/qos:traffic-policy/qos:name";
            }
            description
              "Name of a traffic policy.";
          }
          leaf direction {
            type qos-direction-type;
            description
              "Direction.
              If this field is unnecessary, the controller can set a default value both.";
          }
          leaf slot-id {
            type string {
              length "1..32";
            }
            description
              "Slot id.";
          }
          leaf match-packets {
            type uint64;
            units "packet";
            description
              "Number of matched packets.";
          }
          leaf match-bytes {
            type uint64;
            units "Byte";
            description
              "Number of matched bytes.";
          }
          leaf match-packet-rate {
            type uint64;
            units "pps";
            description
              "Rate of matched packets.";
          }
          leaf match-byte-rate {
            type uint64;
            units "Byte/s";
            description
              "Rate of matched bytes.";
          }
          leaf match-pass-packets {
            type uint64;
            units "packet";
            description
              "Number of matched and passed packets.";
          }
          leaf match-pass-bytes {
            type uint64;
            units "Byte";
            description
              "Number of matched and passed bytes.";
          }
          leaf match-pass-packet-rate {
            type uint64;
            units "pps";
            description
              "Rate of the packets matching the traffic classifier and passed.";
          }
          leaf match-pass-byte-rate {
            type uint64;
            units "Byte/s";
            description
              "Rate of the bytes matching the traffic classifier and passed.";
          }
          leaf match-drop-packets {
            type uint64;
            units "packet";
            description
              "Number of matched but discarded packets.";
          }
          leaf match-drop-bytes {
            type uint64;
            units "Byte";
            description
              "Number of matched but discarded bytes.";
          }
          leaf match-drop-packet-rate {
            type uint64;
            units "pps";
            description
              "Rate of the packets matching the traffic classifier but discarded.";
          }
          leaf match-drop-byte-rate {
            type uint64;
            units "Byte/s";
            description
              "Rate of the bytes matching the traffic classifier but discarded.";
          }
          leaf car-drop-packets {
            type uint64;
            units "packet";
            description
              "Rate of the discarded packets by CAR.";
          }
          leaf car-drop-bytes {
            type uint64;
            units "Byte";
            description
              "Rate of the discarded bytes by CAR.";
          }
          leaf car-drop-packet-rate {
            type uint64;
            units "pps";
            description
              "Rate of the discarded packets by CAR.";
          }
          leaf car-drop-byte-rate {
            type uint64;
            units "Byte/s";
            description
              "Rate of the discarded bytes by CAR.";
          }
          leaf filter-packets {
            type uint64;
            units "packet";
            description
              "Number of filtered bytes.";
          }
          leaf filter-bytes {
            type uint64;
            units "Byte";
            description
              "Number of filtered packets.";
          }
          leaf filter-packet-rate {
            type uint64;
            units "pps";
            description
              "Rate of filtered packets.";
          }
          leaf filter-byte-rate {
            type uint64;
            units "Byte/s";
            description
              "Rate of filtered bytes.";
          }
        }
      }
      container mpls-te-statisticss {
        description
          "List of MPLS TE statistics.";
        list mpls-te-statistics {
          key "interface-name direction service-class";
          description
            "MPLS te statistics.";
          leaf interface-name {
            type leafref {
              path "/ifm:ifm/ifm:interfaces/ifm:interface/ifm:name";
            }
            description
              "Interface name.";
          }
          leaf direction {
            type qos-direction-type;
            description
              "Direction.";
          }
          leaf service-class {
            type qos-service-class-total;
            description
              "Service class.";
          }
          leaf pass-packets {
            type uint64;
            units "packet";
            description
              "Pass packets.";
          }
          leaf pass-bytes {
            type uint64;
            units "Byte";
            description
              "Pass bytes.";
          }
          leaf pass-packet-rate {
            type uint64;
            units "pps";
            description
              "Pass packet rate.";
          }
          leaf pass-byte-rate {
            type uint64;
            units "Byte/s";
            description
              "Pass byte rate.";
          }
          leaf drop-packets {
            type uint64;
            units "packet";
            description
              "Drop packets.";
          }
          leaf drop-bytes {
            type uint64;
            units "Byte";
            description
              "Drop bytes.";
          }
          leaf drop-packet-rate {
            type uint64;
            units "pps";
            description
              "Drop packet rate.";
          }
          leaf drop-byte-rate {
            type uint64;
            units "Byte/s";
            description
              "Drop byte rate.";
          }
          leaf total-buffer {
            type uint32;
            units "kB";
            description
              "Total buffer.";
          }
          leaf current-buffer {
            type uint32;
            units "kB";
            description
              "Current buffer.";
          }
          leaf clear-time {
            type yang:date-and-time;
            description
              "Time of clearing statistics.";
          }
        }
      }
      container vlan-traffic-policy-statisticss {
        description
          "List of configure statistics of traffic policy.";
        list vlan-traffic-policy-statistics {
          key "vlan-id";
          description
            "Statistics of traffic policy.";
          leaf vlan-id {
            type uint16 {
              range "1..4094";
            }
            description
              "VLAN id.";
          }
          leaf direction {
            type qos:qos-direction-type;
            description
              "Direction.";
          }
          leaf traffic-policy-name {
            type string {
              length "1..127";
            }
            description
              "Policy name.";
          }
          leaf apply-time {
            type yang:date-and-time;
            description
              "Time of applying a policy.";
          }
          leaf clear-time {
            type yang:date-and-time;
            description
              "Time of clearing statistics.";
          }
          leaf clear-flag {
            type boolean;
            description
              "Flag of clearing statistics.";
          }
          leaf match-packets {
            type uint64;
            units "packet";
            description
              "Number of matched packets.";
          }
          leaf match-bytes {
            type uint64;
            units "Byte";
            description
              "Number of matched bytes.";
          }
          leaf match-packet-rate {
            type uint64;
            units "pps";
            description
              "Rate of matched packets.";
          }
          leaf match-byte-rate {
            type uint64;
            units "Byte/s";
            description
              "Rate of matched bytes.";
          }
          leaf match-pass-packets {
            type uint64;
            units "packet";
            description
              "Number of matched and passed packets.";
          }
          leaf match-pass-bytes {
            type uint64;
            units "Byte";
            description
              "Number of matched and passed bytes.";
          }
          leaf match-pass-packet-rate {
            type uint64;
            units "pps";
            description
              "Rate of the packets that match the policy and passed.";
          }
          leaf match-pass-byte-rate {
            type uint64;
            units "Byte/s";
            description
              "Rate of the bytes that match the policy and passed.";
          }
          leaf match-drop-packets {
            type uint64;
            units "packet";
            description
              "Number of matched but discarded packets.";
          }
          leaf match-drop-bytes {
            type uint64;
            units "Byte";
            description
              "Number of matched but discarded bytes.";
          }
          leaf match-drop-packet-rate {
            type uint64;
            units "pps";
            description
              "Rate of the packets that match the policy but are discarded.";
          }
          leaf match-drop-byte-rate {
            type uint64;
            units "Byte/s";
            description
              "Rate of the bytes that match the policy but are discarded.";
          }
          leaf miss-packets {
            type uint64;
            units "packet";
            description
              "Number of unmatched packets.";
          }
          leaf miss-bytes {
            type uint64;
            units "Byte";
            description
              "Number of unmatched bytes.";
          }
          leaf miss-packet-rate {
            type uint64;
            units "pps";
            description
              "Rate of the packets that do not match the policy.";
          }
          leaf miss-byte-rate {
            type uint64;
            units "Byte/s";
            description
              "Rate of the bytes that do not match the policy.";
          }
          leaf urpf-packets {
            type uint64;
            units "packet";
            description
              "Number of packets discarded by URPF.";
          }
          leaf urpf-bytes {
            type uint64;
            units "Byte";
            description
              "Number of bytes discarded by URPF.";
          }
          leaf urpf-packet-rate {
            type uint64;
            units "pps";
            description
              "Rate of packets discarded by URPF.";
          }
          leaf urpf-byte-rate {
            type uint64;
            units "Byte/s";
            description
              "Rate of bytes discarded by URPF.";
          }
          leaf car-packets {
            type uint64;
            units "packet";
            description
              "Number of packets processed by CAR.";
          }
          leaf car-bytes {
            type uint64;
            units "Byte";
            description
              "Number of bytes processed by CAR.";
          }
          leaf car-packet-rate {
            type uint64;
            units "pps";
            description
              "Rate of packets processed by CAR.";
          }
          leaf car-byte-rate {
            type uint64;
            units "Byte/s";
            description
              "Rate of bytes processed by CAR.";
          }
          leaf filter-packets {
            type uint64;
            units "packet";
            description
              "Number of filtered packets.";
          }
          leaf filter-bytes {
            type uint64;
            units "Byte";
            description
              "Number of filtered bytes.";
          }
          leaf filter-packet-rate {
            type uint64;
            units "pps";
            description
              "Rate of filtered packets.";
          }
          leaf filter-byte-rate {
            type uint64;
            units "Byte/s";
            description
              "Rate of filtered bytes.";
          }
          container rule-based-statisticss {
            description
              "List of traffic statistics based on rule.";
            list rule-based-statistics {
              key "classifier-name traffic-policy-name ifmatch-id";
              description
                "Statistics of traffic statistics based on rule.";
              leaf classifier-name {
                type leafref {
                  path "/qos/classifier-template/traffic-classifiers/traffic-classifier/name";
                }
                description
                  "Name of a traffic classifier.";
              }
              leaf traffic-policy-name {
                type leafref {
                  path "/qos/classifier-template/traffic-policys/traffic-policy/name";
                }
                description
                  "Name of a traffic policy.";
              }
              leaf ifmatch-id {
                type uint32 {
                  range "1..4294967295";
                }
                description
                  "Ifmatch-id of a traffic classifier.";
              }
              leaf service-type {
                type qos-rule-service-type;
                description
                  "Service type.";
              }
              leaf acl-name {
                type string {
                  length "1..63";
                }
                description
                  "Acl number or name.";
              }
              leaf protocol-family {
                type ip-family;
                description
                  "IP protocol version.";
              }
              leaf rule-id {
                type uint32 {
                  range "1..4294967295";
                }
                description
                  "Rule-id.";
              }
              leaf match-pass-packets {
                type uint64;
                units "packet";
                description
                  "Number of matched and passed packets.";
              }
              leaf match-pass-bytes {
                type uint64;
                units "Byte";
                description
                  "Number of matched and passed bytes.";
              }
              leaf match-drop-packets {
                type uint64;
                units "packet";
                description
                  "Number of matched but discarded packets.";
              }
              leaf match-drop-bytes {
                type uint64;
                units "Byte";
                description
                  "Number of matched but discarded bytes.";
              }
              leaf match-pass-patket-rate {
                type uint64;
                units "pps";
                description
                  "Rate of the packets that match the policy rule and passed.";
              }
              leaf match-pass-byte-rate {
                type uint64;
                units "Byte/s";
                description
                  "Rate of the bytes that match the policy rule and passed.";
              }
              leaf match-drop-patket-rate {
                type uint64;
                units "pps";
                description
                  "Rate of the patkets that match the policy rule and passed.";
              }
              leaf match-drop-byte-rate {
                type uint64;
                units "Byte/s";
                description
                  "Rate of the rates that match the policy rule and passed.";
              }
            }
          }
        }
      }
      container vlan-classifier-statisticss {
		description
		  "List of clear VLAN Traffic classifier statistics slot-id.";
		list vlan-classifier-statistics {
		  key "vlan-id direction classifier-name policy-name slot-id";
		  description
			"Statistics of traffic classifier statistics for VLAN.";
          leaf vlan-id {
			type uint32 {
			  range "1..4094";
			}
            description
			  "VLAN id.";
          }
		  leaf direction {
			type qos:trust-direction-type;
              description
			  "Direction.";
          }
		  leaf classifier-name {
			type string {
			  length "1..127";
			}
			description
			  "Name of a traffic classifier.";
		  }
		  leaf policy-name {
			type leafref {
			  path "/qos:qos/qos:classifier-template/qos:traffic-policys/qos:traffic-policy/qos:name";
			}
			description
			  "Name of a traffic policy.";
		  }
          leaf slot-id {
            type string {
              length "1..32";
            }
            description
              "Slot id.";
          }
              leaf match-packets {
                type uint64;
                units "packet";
                description
                  "Number of matched packets.";
              }
              leaf match-bytes {
                type uint64;
                units "Byte";
                description
                  "Number of matched bytes.";
              }
              leaf match-packet-rate {
                type uint64;
                units "pps";
                description
                  "Rate of matched packets.";
              }
              leaf match-byte-rate {
                type uint64;
                units "Byte/s";
                description
                  "Rate of matched bytes.";
              }
              leaf match-pass-packets {
                type uint64;
                units "packet";
                description
                  "Number of matched and passed packets.";
              }
              leaf match-pass-bytes {
                type uint64;
                units "Byte";
                description
                  "Number of matched and passed bytes.";
              }
              leaf match-pass-packet-rate {
                type uint64;
                units "pps";
                description
                  "Rate of the packets matching the traffic classifier and passed.";
              }
              leaf match-pass-byte-rate {
                type uint64;
                units "Byte/s";
                description
                  "Rate of the bytes matching the traffic classifier and passed.";
              }
              leaf match-drop-packets {
                type uint64;
                units "packet";
                description
                  "Number of matched but discarded packets.";
              }
              leaf match-drop-bytes {
                type uint64;
                units "Byte";
                description
                  "Number of matched but discarded bytes.";
              }
              leaf match-drop-packet-rate {
                type uint64;
                units "pps";
                description
                  "Rate of the packets matching the traffic classifier but discarded.";
              }
              leaf match-drop-byte-rate {
                type uint64;
                units "Byte/s";
                description
                  "Rate of the bytes matching the traffic classifier but discarded.";
              }
              leaf car-drop-packets {
                type uint64;
                units "packet";
                description
                  "Rate of the discarded packets by CAR.";
              }
              leaf car-drop-bytes {
                type uint64;
                units "Byte";
                description
                  "Rate of the discarded bytes by CAR.";
              }
              leaf car-drop-packet-rate {
                type uint64;
                units "pps";
                description
                  "Rate of the discarded packets by CAR.";
              }
              leaf car-drop-byte-rate {
                type uint64;
                units "Byte/s";
                description
                  "Rate of the discarded bytes by CAR.";
              }
              leaf filter-packets {
                type uint64;
                units "packet";
                description
                  "Number of filtered bytes.";
              }
              leaf filter-bytes {
                type uint64;
                units "Byte";
                description
                  "Number of filtered packets.";
              }
              leaf filter-packet-rate {
                type uint64;
                units "pps";
                description
                  "Rate of filtered packets.";
              }
              leaf filter-byte-rate {
                type uint64;
                units "Byte/s";
                description
                  "Rate of filtered bytes.";
              }
            }
          }
      container vpn-traffic-policy-statisticss {
        description
          "List of traffic policy statistics of vpn instance.";
        list vpn-traffic-policy-statistics {
          key "vpn-instance";
          description
            "Traffic policy statistics.";
          leaf vpn-instance {
            type leafref {
              path "/ni:network-instance/ni:instances/ni:instance/ni:name";
            }
            description
              "Vpn instance name.";
          }
          leaf direction {
            type qos:qos-direction-type;
            description
              "Direction.";
          }
          leaf traffic-policy-name {
            type string {
              length "1..127";
            }
            description
              "Policy name.";
          }
          leaf apply-time {
            type yang:date-and-time;
            description
              "Time of applying a policy.";
          }
          leaf clear-time {
            type yang:date-and-time;
            description
              "Time of clearing statistics.";
          }
          leaf clear-flag {
            type boolean;
            description
              "Flag of clearing statistics.";
          }
          leaf match-packets {
            type uint64;
            units "packet";
            description
              "Number of matched packets.";
          }
          leaf match-bytes {
            type uint64;
            units "Byte";
            description
              "Number of matched bytes.";
          }
          leaf match-packet-rate {
            type uint64;
            units "pps";
            description
              "Rate of matched packets.";
          }
          leaf match-byte-rate {
            type uint64;
            units "Byte/s";
            description
              "Rate of matched bytes.";
          }
          leaf match-pass-packets {
            type uint64;
            units "packet";
            description
              "Number of matched and passed packets.";
          }
          leaf match-pass-bytes {
            type uint64;
            units "Byte";
            description
              "Number of matched and passed bytes.";
          }
          leaf match-pass-packet-rate {
            type uint64;
            units "pps";
            description
              "Rate of the packets that match the policy and passed.";
          }
          leaf match-pass-byte-rate {
            type uint64;
            units "Byte/s";
            description
              "Rate of the bytes that match the policy and passed.";
          }
          leaf match-drop-packets {
            type uint64;
            units "packet";
            description
              "Number of matched but discarded packets.";
          }
          leaf match-drop-bytes {
            type uint64;
            units "Byte";
            description
              "Number of matched but discarded bytes.";
          }
          leaf match-drop-packet-rate {
            type uint64;
            units "pps";
            description
              "Rate of the packets that match the policy but are discarded.";
          }
          leaf match-drop-byte-rate {
            type uint64;
            units "Byte/s";
            description
              "Rate of the bytes that match the policy but are discarded.";
          }
          leaf miss-packets {
            type uint64;
            units "packet";
            description
              "Number of unmatched packets.";
          }
          leaf miss-bytes {
            type uint64;
            units "Byte";
            description
              "Number of unmatched bytes.";
          }
          leaf miss-packet-rate {
            type uint64;
            units "pps";
            description
              "Rate of the packets that do not match the policy.";
          }
          leaf miss-byte-rate {
            type uint64;
            units "Byte/s";
            description
              "Rate of the bytes that do not match the policy.";
          }
          leaf urpf-packets {
            type uint64;
            units "packet";
            description
              "Number of packets discarded by URPF.";
          }
          leaf urpf-bytes {
            type uint64;
            units "Byte";
            description
              "Number of bytes discarded by URPF.";
          }
          leaf urpf-packet-rate {
            type uint64;
            units "pps";
            description
              "Rate of packets discarded by URPF.";
          }
          leaf urpf-byte-rate {
            type uint64;
            units "Byte/s";
            description
              "Rate of bytes discarded by URPF.";
          }
          leaf car-packets {
            type uint64;
            units "packet";
            description
              "Number of packets processed by CAR.";
          }
          leaf car-bytes {
            type uint64;
            units "Byte";
            description
              "Number of bytes processed by CAR.";
          }
          leaf car-packet-rate {
            type uint64;
            units "pps";
            description
              "Rate of packets processed by CAR.";
          }
          leaf car-byte-rate {
            type uint64;
            units "Byte/s";
            description
              "Rate of bytes processed by CAR.";
          }
          leaf filter-packets {
            type uint64;
            units "packet";
            description
              "Number of filtered packets.";
          }
          leaf filter-bytes {
            type uint64;
            units "Byte";
            description
              "Number of filtered bytes.";
          }
          leaf filter-packet-rate {
            type uint64;
            units "pps";
            description
              "Rate of filtered packets.";
          }
          leaf filter-byte-rate {
            type uint64;
            units "Byte/s";
            description
              "Rate of filtered bytes.";
          }
          container rule-based-staticss {
            description
              "List of traffic rule classifier statistics.";
            list rule-based-statics {
              key "classifier-name traffic-policy-name ifmatch-id";
              description
                "Traffic classifier statistics.";
              leaf classifier-name {
                type leafref {
                  path "/qos/classifier-template/traffic-classifiers/traffic-classifier/name";
                }
                description
                  'Name of a traffic classifier.
If this field is unnecessary, the controller can set a default value "no-classifier-name-set".';
              }
              leaf traffic-policy-name {
                type leafref {
                  path "/qos/classifier-template/traffic-policys/traffic-policy/name";
                }
                description
                  "Name of a traffic policy.";
              }
              leaf ifmatch-id {
                type uint32 {
                  range "1..4294967295";
                }
                description
                  "Ifmatch-id of a traffic classifier.";
              }
              leaf service-type {
                type qos-rule-service-type;
                description
                  "Service type.";
              }
              leaf acl-name {
                type string {
                  length "1..63";
                }
                description
                  "Acl number or name.";
              }
              leaf protocol-family {
                type ip-family;
                description
                  "IP protocol version.";
              }
              leaf rule-id {
                type uint32 {
                  range "1..4294967295";
                }
                description
                  "Rule-id.";
              }
              leaf match-pass-packets {
                type uint64;
                units "packet";
                description
                  "Number of matched and passed packets.";
              }
              leaf match-pass-bytes {
                type uint64;
                units "Byte";
                description
                  "Number of matched and passed bytes.";
              }
              leaf match-drop-packets {
                type uint64;
                units "packet";
                description
                  "Number of matched but discarded packets.";
              }
              leaf match-drop-bytes {
                type uint64;
                units "Byte";
                description
                  "Number of matched but discarded bytes.";
              }
              leaf match-pass-patket-rate {
                type uint64;
                units "pps";
                description
                  "Rate of the packets that match the policy rule and passed.";
              }
              leaf match-pass-byte-rate {
                type uint64;
                units "Byte/s";
                description
                  "Rate of the bytes that match the policy rule and passed.";
              }
              leaf match-drop-patket-rate {
                type uint64;
                units "pps";
                description
                  "Rate of the patkets that match the policy rule and passed.";
              }
              leaf match-drop-byte-rate {
                type uint64;
                units "Byte/s";
                description
                  "Rate of the rates that match the policy rule and passed.";
              }
            }
          }
        }
      }
      container vpn-classifier-statisticss {
		description
		  "List of vpn traffic classifier statistics.";
		list vpn-classifier-statistics {
		  key "vpn-instance classifier-name policy-name direction slot-id";
		  description
			"Operational state of vpn traffic classifier statistics.";
          leaf vpn-instance {
            type leafref {
              path "/ni:network-instance/ni:instances/ni:instance/ni:name";
            }
            description
              "Vpn instance name.";
          }
		  leaf classifier-name {
			type string {
			  length "1..127";
			}
			description
			  "Name of a traffic classifier.";
		  }
		  leaf policy-name {
			type leafref {
			  path "/qos:qos/qos:classifier-template/qos:traffic-policys/qos:traffic-policy/qos:name";
			}
			description
			  "Name of a traffic policy.";
		  }
          leaf direction {
            type trust-direction-type;
            description
              "Direction.
              If this field is unnecessary, the controller can set a default value both.";
          }
          leaf slot-id {
            type string {
              length "1..32";
            }
            description
              "Slot id.";
          }
		  leaf match-packets {
			type uint64;
			units "packet";
			description
			  "Number of matched packets.";
		  }
		  leaf match-bytes {
			type uint64;
			units "Byte";
			description
			  "Number of matched bytes.";
		  }
		  leaf match-packet-rate {
			type uint64;
			units "pps";
			description
			  "Rate of matched packets.";
		  }
		  leaf match-byte-rate {
			type uint64;
			units "Byte/s";
			description
			  "Rate of matched bytes.";
		  }
		  leaf match-pass-packets {
			type uint64;
			units "packet";
			description
			  "Number of matched and passed packets.";
		  }
		  leaf match-pass-bytes {
			type uint64;
			units "Byte";
			description
			  "Number of matched and passed bytes.";
		  }
		  leaf match-pass-packet-rate {
			type uint64;
			units "pps";
			description
			  "Rate of the packets matching the traffic classifier and passed.";
		  }
		  leaf match-pass-byte-rate {
			type uint64;
			units "Byte/s";
			description
			  "Rate of the bytes matching the traffic classifier and passed.";
		  }
		  leaf match-drop-packets {
			type uint64;
			units "packet";
			description
			  "Number of matched but discarded packets.";
		  }
		  leaf match-drop-bytes {
			type uint64;
			units "Byte";
			description
			  "Number of matched but discarded bytes.";
		  }
		  leaf match-drop-packet-rate {
			type uint64;
			units "pps";
			description
			  "Rate of the packets matching the traffic classifier but discarded.";
		  }
		  leaf match-drop-byte-rate {
			type uint64;
			units "Byte/s";
            description
			  "Rate of the bytes matching the traffic classifier but discarded.";
		  }
		  leaf car-drop-packets {
			type uint64;
			units "packet";
			description
			  "Rate of the discarded packets by CAR.";
		  }
		  leaf car-drop-bytes {
			type uint64;
			units "Byte";
			description
			  "Rate of the discarded bytes by CAR.";
		  }
		  leaf car-drop-packet-rate {
			type uint64;
			units "pps";
			description
			  "Rate of the discarded packets by CAR.";
		  }
		  leaf car-drop-byte-rate {
			type uint64;
			units "Byte/s";
			description
			  "Rate of the discarded bytes by CAR.";
		  }
		  leaf filter-packets {
			type uint64;
			units "packet";
			description
			  "Number of filtered bytes.";
		  }
		  leaf filter-bytes {
			type uint64;
			units "Byte";
			description
			  "Number of filtered packets.";
		  }
		  leaf filter-packet-rate {
			type uint64;
			units "pps";
			description
			  "Rate of filtered packets.";
		  }
		  leaf filter-byte-rate {
			type uint64;
			units "Byte/s";
			description
			  "Rate of filtered bytes.";
		  }
		}
      }
      container global-classifier-statisticss {
		description
		  "List of global traffic classifier statistics.";
		list global-classifier-statistics {
		  key "classifier-name policy-name direction slot-id";
		  description
			"Operational state of global traffic classifier statistics.";
		  leaf classifier-name {
			type string {
			  length "1..127";
			}
			description
			  "Name of a traffic classifier.";
		  }
		  leaf policy-name {
			type leafref {
			  path "/qos:qos/qos:classifier-template/qos:traffic-policys/qos:traffic-policy/qos:name";
			}
			description
			  "Name of a traffic policy.";
		  }
          leaf direction {
            type trust-direction-type;
            description
              "Direction.
              If this field is unnecessary, the controller can set a default value both.";
          }
          leaf slot-id {
            type string {
              length "1..32";
            }
            description
              "Slot id.";
          }
		  leaf match-packets {
			type uint64;
			units "packet";
			description
			  "Number of matched packets.";
		  }
		  leaf match-bytes {
			type uint64;
			units "Byte";
			description
			  "Number of matched bytes.";
		  }
		  leaf match-packet-rate {
			type uint64;
			units "pps";
			description
			  "Rate of matched packets.";
		  }
		  leaf match-byte-rate {
			type uint64;
			units "Byte/s";
			description
			  "Rate of matched bytes.";
		  }
		  leaf match-pass-packets {
			type uint64;
			units "packet";
			description
			  "Number of matched and passed packets.";
		  }
		  leaf match-pass-bytes {
			type uint64;
			units "Byte";
			description
			  "Number of matched and passed bytes.";
		  }
		  leaf match-pass-packet-rate {
			type uint64;
			units "pps";
			description
			  "Rate of the packets matching the traffic classifier and passed.";
		  }
		  leaf match-pass-byte-rate {
			type uint64;
			units "Byte/s";
			description
			  "Rate of the bytes matching the traffic classifier and passed.";
		  }
		  leaf match-drop-packets {
			type uint64;
			units "packet";
			description
			  "Number of matched but discarded packets.";
		  }
		  leaf match-drop-bytes {
			type uint64;
			units "Byte";
			description
			  "Number of matched but discarded bytes.";
		  }
		  leaf match-drop-packet-rate {
			type uint64;
			units "pps";
			description
			  "Rate of the packets matching the traffic classifier but discarded.";
		  }
		  leaf match-drop-byte-rate {
			type uint64;
			units "Byte/s";
			description
			  "Rate of the bytes matching the traffic classifier but discarded.";
		  }
		  leaf car-drop-packets {
			type uint64;
			units "packet";
			description
			  "Rate of the discarded packets by CAR.";
		  }
		  leaf car-drop-bytes {
			type uint64;
			units "Byte";
			description
			  "Rate of the discarded bytes by CAR.";
		  }
		  leaf car-drop-packet-rate {
			type uint64;
			units "pps";
			description
			  "Rate of the discarded packets by CAR.";
		  }
		  leaf car-drop-byte-rate {
			type uint64;
			units "Byte/s";
			description
			  "Rate of the discarded bytes by CAR.";
		  }
		  leaf filter-packets {
			type uint64;
			units "packet";
			description
			  "Number of filtered bytes.";
		  }
		  leaf filter-bytes {
			type uint64;
			units "Byte";
			description
			  "Number of filtered packets.";
		  }
		  leaf filter-packet-rate {
			type uint64;
			units "pps";
			description
			  "Rate of filtered packets.";
		  }
		  leaf filter-byte-rate {
			type uint64;
			units "Byte/s";
			description
			  "Rate of filtered bytes.";
		  }
		}
      }
      container group-classifier-statisticss {
		description
		  "List of qos group traffic classifier statistics.";
		list group-classifier-statistics {
		  key "group-name classifier-name policy-name direction slot-id";
		  description
			"Operational state of qos group traffic classifier statistics.";
          leaf group-name {
            type string {
              length "1..31";
            }
            description
              "Group name.";
          }
		  leaf classifier-name {
			type string {
			  length "1..127";
			}
			description
			  "Name of a traffic classifier.";
		  }
		  leaf policy-name {
			type leafref {
			  path "/qos:qos/qos:classifier-template/qos:traffic-policys/qos:traffic-policy/qos:name";
			}
			description
			  "Name of a traffic policy.";
		  }
          leaf direction {
            type trust-direction-type;
            description
              "Direction.
              If this field is unnecessary, the controller can set a default value both.";
          }
          leaf slot-id {
            type string {
              length "1..32";
            }
            description
              "Slot id.";
          }
		  leaf match-packets {
			type uint64;
			units "packet";
			description
			  "Number of matched packets.";
		  }
		  leaf match-bytes {
			type uint64;
			units "Byte";
			description
			  "Number of matched bytes.";
		  }
		  leaf match-packet-rate {
			type uint64;
			units "pps";
			description
			  "Rate of matched packets.";
		  }
		  leaf match-byte-rate {
			type uint64;
			units "Byte/s";
			description
			  "Rate of matched bytes.";
		  }
		  leaf match-pass-packets {
			type uint64;
			units "packet";
			description
			  "Number of matched and passed packets.";
		  }
		  leaf match-pass-bytes {
			type uint64;
			units "Byte";
			description
			  "Number of matched and passed bytes.";
		  }
		  leaf match-pass-packet-rate {
			type uint64;
			units "pps";
			description
			  "Rate of the packets matching the traffic classifier and passed.";
		  }
		  leaf match-pass-byte-rate {
			type uint64;
			units "Byte/s";
			description
			  "Rate of the bytes matching the traffic classifier and passed.";
		  }
		  leaf match-drop-packets {
			type uint64;
			units "packet";
			description
			  "Number of matched but discarded packets.";
		  }
		  leaf match-drop-bytes {
			type uint64;
			units "Byte";
			description
			  "Number of matched but discarded bytes.";
		  }
		  leaf match-drop-packet-rate {
			type uint64;
			units "pps";
			description
			  "Rate of the packets matching the traffic classifier but discarded.";
		  }
		  leaf match-drop-byte-rate {
			type uint64;
			units "Byte/s";
			description
			  "Rate of the bytes matching the traffic classifier but discarded.";
		  }
		  leaf car-drop-packets {
			type uint64;
			units "packet";
			description
			  "Rate of the discarded packets by CAR.";
		  }
		  leaf car-drop-bytes {
			type uint64;
			units "Byte";
			description
			  "Rate of the discarded bytes by CAR.";
		  }
		  leaf car-drop-packet-rate {
			type uint64;
			units "pps";
			description
			  "Rate of the discarded packets by CAR.";
		  }
		  leaf car-drop-byte-rate {
			type uint64;
			units "Byte/s";
			description
			  "Rate of the discarded bytes by CAR.";
		  }
		  leaf filter-packets {
			type uint64;
			units "packet";
			description
			  "Number of filtered bytes.";
		  }
		  leaf filter-bytes {
			type uint64;
			units "Byte";
			description
			  "Number of filtered packets.";
		  }
		  leaf filter-packet-rate {
			type uint64;
			units "pps";
			description
			  "Rate of filtered packets.";
		  }
		  leaf filter-byte-rate {
			type uint64;
			units "Byte/s";
			description
			  "Rate of filtered bytes.";
		  }
		}
      }
      container traffic-policy-states {
        description
          "Operational state of traffic policy records.";
        container interface-applys {
          description
            "List of interface apply result.";
          list interface-apply {
            key "interface-name direction slot-id policy-name";
            description
              "Operational state of interface apply.";
            leaf interface-name {
              type leafref {
                path "/ifm:ifm/ifm:interfaces/ifm:interface/ifm:name";
              }
              description
                "Interface name.";
            }
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
          }
        }
        container group-applys {
          description
            "List of qos group apply result.";
          list group-apply {
            key "group-name direction slot-id policy-name";
            description
              "Operational state of qos group apply.";
            leaf group-name {
              type leafref {
                path "/qos:qos/qos:classifier-template/qos:qos-groups/qos:qos-group/qos:group-name";
              }
              description
                "Group name.";
            }
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
          }
        }
        container vpn-applys {
          description
            "List of vpn instance apply result.";
          list vpn-apply {
            key "vpn-instance direction slot-id policy-name";
            description
              "Operational state of vpn instance.";
            leaf vpn-instance {
              type leafref {
                path "/ni:network-instance/ni:instances/ni:instance/ni:name";
              }
              description
                "Vpn instance name.";
            }
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
          }
        }
        container vlan-applys {
          description
            "List of VLAN apply result.";
          list vlan-apply {
            key "vlan-id direction slot-id policy-name";
            description
              "Operational state of VLAN apply.";
            leaf vlan-id {
              type leafref {
                path "/vlan:vlan/vlan:vlans/vlan:vlan/vlan:id";
              }
              description
                "VLAN apply result.";
            }
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
          }
        }
        container bd-applys {
          description
            "List of bd apply result.";
          list bd-apply {
            key "bd-id direction slot-id policy-name";
            description
              "Operational state of bd apply.";
			leaf bd-id {
              type uint32 {
                range "1..16777215";
              }
              description
                "BD ID.";
            }
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
          }
        }
        container global-applys {
          description
            "List of global apply result.";
          list global-apply {
            key "direction slot-id policy-name";
            description
              "Operational state of global apply.";
            leaf direction {
              type qos:trust-direction-type;
              description
                "Direction.";
            }
            leaf slot-id {
              type slot-id;
              description
                "Slot id.";
            }
            leaf policy-name {
              type leafref {
                path "/qos:qos/qos:classifier-template/qos:traffic-policys/qos:traffic-policy/qos:name";
              }
              description
                "Name of a traffic policy.";
            }
            leaf result {
              type qos:policy-apply-state;
              description
                "View and status of the traffic policy that is applied to the specified slot.";
            }
		  }
        }
      }
      container car-resources {
        description
          "List of CAR resource state.";
        list car-resource {
          key "slot-id car-type";
          description
            "CAR resource state.";
          leaf slot-id {
            type slot-id;
            description
              "Slot id.";
          }
          leaf car-type {
            type string {
              length "1..96";
            }
            description
              "Car type.";
          }
          leaf inbound-resource {
            type uint32;
            description
              "Inbound car resource.";
          }
          leaf outbound-resource {
            type uint32;
            description
              "Outbound car resource.";
          }
        }
      }
      container traffic-buffer-usages {
        description
          "List of traffic buffer usage.";
        list traffic-buffer-usage {
          key "slot-id direction chip-name";
          description
            "Traffic buffer usage state.";
          leaf slot-id {
            type string {
              length "1..15";
            }
            description
              "Slot id.";
          }
          leaf direction {
            type all-direction-type;
            description
              "Direction.";
          }
          leaf chip-name {
            type string {
              length "1..32";
            }
            description
              "Chip name.";
          }
          leaf chip-type {
            type string {
              length "1..32";
            }
            description
              "Chip type.";
          }
          leaf total-size {
            type uint32;
            units "kB";
            description
              "Total size.";
          }
          leaf used-size {
            type uint32;
            units "kB";
            description
              "Used size.";
          }
        }
      }
      container traffic-policy-application-resources {
        description
          "List of traffic policy resource state.";
        list traffic-policy-application-resource {
          key "slot-id";
          description
            "Traffic policy resource state.";
          leaf slot-id {
            type string {
              length "1..15";
            }
            description
              "Slot id.";
          }
          leaf used {
            type uint32;
            description
              "Used resource.";
          }
          leaf free {
            type uint32;
            description
              "Free resource.";
          }
        }
      }
      container user-group-queue-resources {
        description
          "List of user group queue resource state.";
        list user-group-queue-resource {
          key "slot-id direction tm-type pool";
          description
            "User group queue resource state.";
          leaf slot-id {
            type string {
              length "1..15";
            }
            description
              "Slot id.";
          }
          leaf direction {
            type qos-direction-type;
            description
              "Direction.";
          }
          leaf tm-type {
            type string {
	          length "1..32";
	        }
            description
              "Resource TM type.";
          }
          leaf pool {
            type string {
              length "1..32";
            }
            description
              "Resource pool.";
          }
          leaf used-number {
            type uint32;
            description
              "Used user group queue id resource.";
          }
          leaf free-number {
            type uint32;
            description
              "Free user group queue id resource.";
          }
        }
      }
      container queue-statisticss {
        description
          "List of queue statistics.";
        list queue-statistics {
          key "interface-name service-class";
          description
            "Queue statistics.";
          leaf interface-name {
            type leafref {
              path "/ifm:ifm/ifm:interfaces/ifm:interface/ifm:name";
            }
            description
              "Interface name.";
          }
          leaf service-class {
            type qos-service-class;
            description
              "Class of service.";
          }
          leaf pass-packets {
            type uint64;
            units "packet";
            description
              "Pass packets.";
          }
          leaf pass-bytes {
            type uint64;
            units "Byte";
            description
              "Pass bytes.";
          }
          leaf pass-packet-rate {
            type uint64;
            units "pps";
            description
              "Pass packet rate.";
          }
          leaf pass-byte-rate {
            type uint64;
            units "Byte/s";
            description
              "Pass byte rate.";
          }
          leaf discard-packets {
            type uint64;
            units "packet";
            description
              "Discard packets.";
          }
          leaf discard-bytes {
            type uint64;
            units "Byte";
            description
              "Discard bytes.";
          }
          leaf discard-packet-rate {
            type uint64;
            units "pps";
            description
              "Discard packet rate.";
          }
          leaf discard-byte-rate {
            type uint64;
            units "Byte/s";
            description
              "Discard byte rate.";
          }
        }
      }
      container port-buffer-usage-statisticss {
        description
          "List of port buffer usage.";
        list port-buffer-usage-statistics {
          key "slot-id interface-name";
          description
            "Operational state of port buffer usage.";
          leaf slot-id {
            type slot-id {
              pattern "[1-9]|1[0-6]";
            }
            description
              "Slot ID.";
          }
          leaf interface-name {
            type leafref {
              path "/ifm:ifm/ifm:interfaces/ifm:interface/ifm:name";
            }
            description
              "Interface name.";
          }
          leaf total-buffer {
            type uint64;
            units "kB";
            description
              "Total buffer size.";
          }
          leaf current-used {
            type uint64;
            units "kB";
            description
              "Current used buffer size.";
          }
          leaf remained {
            type uint64;
            units "kB";
            description
              "Remained buffer size.";
          }
          leaf peak-used {
            type uint64;
            units "kB";
            description
              "Peak buffer size.";
          }
          leaf average-used {
            type uint64;
            units "kB";
            description
              "Average buffer size.";
          }
        }
      }
	  container queue-buffer-usage-statisticss {
        description
          "List of queue buffer usage.";
        list queue-buffer-usage-statistics {
          key "slot-id interface-name queue-id";
          description
            "Operational state of queue buffer usage.";
          leaf slot-id {
            type slot-id {
              pattern "[1-9]|1[0-6]";
            }
            description
              "Slot ID.";
          }
          leaf interface-name {
            type leafref {
              path "/ifm:ifm/ifm:interfaces/ifm:interface/ifm:name";
            }
            description
              "Interface name.";
          }
          leaf queue-id {
            type uint32;
            description
              "Queue index.";
          }
          leaf current-used {
            type uint64;
            units "Byte";
            description
              "Current used buffer size.";
          }
          leaf peak-used {
            type uint64;
            units "Byte";
            description
              "Peak buffer size.";
          }
          leaf average-used {
            type uint64;
            units "Byte";
            description
              "Average buffer size.";
          }
          leaf total-buffer {
            type uint64;
            units "Byte";
            description
              "Total buffer size.";
          }
        }
      }
      container core-buffer-statisticss {
        description
          "List of core Buffer statistics.";
        list core-buffer-statistics {
          key "slot-id unit-id core-id";
          description
            "Statistics of core Buffer.";
          leaf slot-id {
            type slot-id;
            description
              "Slot Id.";
          }
          leaf unit-id {
            type uint32;
            description
              "Unit Id.";
          }
          leaf core-id {
            type uint32;
            description
              "Core Id.";
          }
          leaf total-buffer-cell {
            type uint32;
            description
              "Total Buffer.";
          }
          leaf total-buffer-byte {
            type uint32;
            description
              "Total Buffer.";
          }
          leaf current-used-cell {
            type uint32;
            description
              "Current Used Buffer.";
          }
          leaf current-used-byte {
            type uint32;
            description
              "Current Used Buffer.";
          }
          leaf current-percent {
            type string {
              length "1..31";
            }
            description
              "Current used Buffer Percent.";
          }
        }
      }
      container queue-drop-statisticss {
        description
          "List of queue dropped statistics.";
        list queue-drop-statistics {
          key "interface-name";
          description
            "Statistics of queue dropped.";
          leaf interface-name {
            type leafref {
              path "/ifm:ifm/ifm:interfaces/ifm:interface/ifm:name";
            }
            description
              "Interface Name.";
          }
          leaf queue0-drop-bytes {
            type uint64;
			units "Byte";
            description
              "Dropped bytes.";
          }
	  	leaf queue0-drop-packets {
            type uint64;
			units "packet";
            description
              "Dropped packets.";
          }
	  	 leaf queue1-drop-bytes {
            type uint64;
			units "Byte";
            description
              "Dropped bytes.";
          }
	  	leaf queue1-drop-packets {
            type uint64;
			units "packet";
            description
              "Dropped packets.";
          }
	  	 leaf queue2-drop-bytes {
            type uint64;
			units "Byte";
            description
              "Dropped bytes.";
          }
	  	leaf queue2-drop-packets {
            type uint64;
			units "packet";
            description
              "Dropped packets.";
          }
	  	leaf queue3-drop-bytes {
            type uint64;
			units "Byte";
            description
              "Dropped bytes.";
          }
	  	leaf queue3-drop-packets {
            type uint64;
			units "packet";
            description
              "Dropped packets.";
          }
	  	leaf queue4-drop-bytes {
            type uint64;
			units "Byte";
            description
              "Dropped bytes.";
          }
	  	leaf queue4-drop-packets {
            type uint64;
			units "packet";
            description
              "Dropped packets.";
          }
	  	leaf queue5-drop-bytes {
            type uint64;
			units "Byte";
            description
              "Dropped bytes.";
          }
	  	leaf queue5-drop-packets {
            type uint64;
			units "packet";
            description
              "Dropped packets.";
          }
	  	leaf queue6-drop-bytes {
            type uint64;
			units "Byte";
            description
              "Dropped bytes.";
          }
	  	leaf queue6-drop-packets {
            type uint64;
			units "packet";
            description
              "Dropped packets.";
          }
	  	leaf queue7-drop-bytes {
            type uint64;
			units "Byte";
            description
              "Dropped bytes.";
          }
	  	leaf queue7-drop-packets {
            type uint64;
			units "packet";
            description
              "Dropped packets.";
          }
        }
      }
      container ing-port-drop-statisticss {
        description
          "List of ingress Port Drop statistics.";
        list ing-port-drop-statistics {
          key "interface-name";
          description
            "Statistics of ingress Port Drop statistics.";
          leaf interface-name {
            type leafref {
              path "/ifm:ifm/ifm:interfaces/ifm:interface/ifm:name";
            }
            description
              "Interface Name.";
          }
          leaf drop-bytes {
            type uint64;
            description
              "Ingress Drop packets.";
          }
	  	leaf drop-packets {
            type uint64;
            description
              "Ingress Drop Bytes.";
          }
        }
      }
      container ing-port-queue-buf-statisticss {
        description
          "List of ingress Queue Buffer statistics.";
        list ing-port-queue-buf-statistics {
          key "interface-name queue-id";
          description
            "Statistics of ingress Queue Buffer statistics.";
          leaf interface-name {
            type leafref {
              path "/ifm:ifm/ifm:interfaces/ifm:interface/ifm:name";
            }
            description
              "Interface name.";
          }
          leaf queue-id {
            type uint32;
            description
              "Queue ID.";
          }
          leaf current-guarante {
            type uint64;
            description
              "Current Buffer.";
          }
        }
      }
      container port-ecn-statisticss {
	    config false;
        description
          "List of port ECN statistics.";
        list port-ecn-statistics {
          key "interface-name";
          description
            "Statistics of port ECN.";
          leaf interface-name {
            type leafref {
              path "/ifm:ifm/ifm:interfaces/ifm:interface/ifm:name";
            }
            description
              "Interface name.";
          }
          leaf packets {
            type uint64;
            description
              "ECN remarked packets.";
          }
        }
      }
      container port-queue-statisticss {
        config false;
        description
          "List of statistics on traffic shaping on interfaces.";
        list port-queue-statistics {
          key "interface-name service-class";
          description
            "Statistics of traffic shaping on interfaces.";
          leaf interface-name {
            type leafref {
              path "/ifm:ifm/ifm:interfaces/ifm:interface/ifm:name";
            }
            description
              "Interface name.";
          }
          leaf service-class {
            type qos-service-class;
            description
              "Class of service.";
          }
          leaf pass-packets {
            type uint64;
            units "packet";
            description
              "Number of passed packets.";
          }
          leaf pass-bytes {
            type uint64;
            units "Byte";
            description
              "Number of passed bytes.";
          }
          leaf drop-packets {
            type uint64;
            units "packet";
            description
              "Number of dropped packets.";
          }
          leaf drop-bytes {
            type uint64;
            units "Byte";
            description
              "Number of dropped bytes.";
          }
          leaf drop-tail-packets {
            type uint64;
            units "packet";
            description
              "Drop tail packets.";
          }
          leaf drop-tail-bytes {
            type uint64;
            units "Byte";
            description
              "Drop tail bytes.";
          }
          leaf drop-wred-packets {
            type uint64;
            units "packet";
            description
              "Drop wred packets.";
          }
          leaf drop-wred-bytes {
            type uint64;
            units "Byte";
            description
              "Drop wred bytes.";
          }
          leaf statistics-interval {
            type uint32;
            units "s";
            description
              "Statistics-interval.";
          }
          leaf pass-packet-rate {
            type uint64;
            units "pps";
            description
              "Rate of the packets passed during the latest 30 seconds. Some products are during the latest statistics-interval.";
          }
          leaf pass-byte-rate {
            type uint64;
            units "Byte/s";
            description
              "Rate of the bytes passed during the latest 30 seconds. Some products are during the latest statistics-interval.";
          }
          leaf drop-packet-rate {
            type uint64;
            units "pps";
            description
              "Rate of the packets dropped during the latest 30 seconds. Some products are during the latest statistics-interval.";
          }
          leaf drop-byte-rate {
            type uint64;
            units "Byte/s";
            description
              "Rate of the bytes dropped during the latest 30 seconds. Some products are during the latest statistics-interval.";
          }
          leaf drop-tail-packet-rate {
            type uint64;
            units "pps";
            description
              "Drop tail packet rate.";
          }
          leaf drop-tail-byte-rate {
            type uint64;
            units "Byte/s";
            description
              "Drop tail byte rate.";
          }
          leaf drop-wred-packet-rate {
            type uint64;
            units "pps";
            description
              "Drop WRED PktRate.";
          }
          leaf drop-wred-byte-rate {
            type uint64;
            units "Byte/s";
            description
              "Drop wred byte rate.";
          }
          leaf peak-time {
            type yang:date-and-time;
            description
              "Peak time.";
          }
          leaf peak-rate {
            type uint64;
            units "bit/s";
            description
              "Rate of the peak bytes during the latest 30 seconds.";
          }
          leaf current-queue-usage {
            type uint32;
            units "%";
            description
              "Current usage percentage of queue.";
          }
          leaf total-buffer-size {
            type uint32;
            units "kB";
            description
              "Size of total buffer.";
          }
          leaf used-buffer-size {
            type uint32;
            units "kB";
            description
              "Size of used buffer.";
          }
          leaf traffic-flow {
            type uint64;
            units "bit/s";
            description
              "Traffic flow towards this port.";
          }
          leaf physical-bandwidth {
            type uint64;
            units "bit/s";
            description
              "Physical bandwidth of port QoS.";
          }
        }
      }
      container port-queue-default-statisticss {
        config false;
        description
          "List of default queue statistics on traffic shaping on interfaces.";
        list port-queue-default-statistics {
          key "interface-name service-class";
          description
            "Statistics of default queue on traffic shaping on interfaces.";
          leaf interface-name {
            type leafref {
              path "/ifm:ifm/ifm:interfaces/ifm:interface/ifm:name";
            }
            description
              "Interface name.";
          }
          leaf service-class {
            type qos-service-class;
            description
              "Class of service.";
          }
          leaf pass-packets {
            type uint64;
            units "packet";
            description
              "Number of passed packets.";
          }
          leaf pass-bytes {
            type uint64;
            units "Byte";
            description
              "Number of passed bytes.";
          }
          leaf drop-packets {
            type uint64;
            units "packet";
            description
              "Number of dropped packets.";
          }
          leaf drop-bytes {
            type uint64;
            units "Byte";
            description
              "Number of dropped bytes.";
          }
          leaf statistics-interval {
            type uint32;
            units "s";
            description
              "Statistics-interval.";
          }
          leaf pass-packet-rate {
            type uint64;
            units "pps";
            description
              "Rate of the packets passed during the latest statistics-interval.";
          }
          leaf pass-byte-rate {
            type uint64;
            units "Byte/s";
            description
              "Rate of the bytes passed during the latest statistics-interval.";
          }
          leaf drop-packet-rate {
            type uint64;
            units "pps";
            description
              "Rate of the packets dropped during the latest statistics-interval.";
          }
          leaf drop-byte-rate {
            type uint64;
            units "Byte/s";
            description
              "Rate of the bytes dropped during the latest statistics-interval.";
          }
          leaf configured-queue-depth {
            type uint32;
            units "kB";
            description
              "Configured queue depth.";
          }
          leaf used-buffer-size {
            type uint32;
            units "kB";
            description
              "Size of used buffer.";
          }
          leaf reset-time {
            type yang:date-and-time;
            description
              "Statistics last reset time.";
          }
          leaf traffic-flow {
            type uint64;
            units "bit/s";
            description
              "Traffic flow towards this port.";
          }
          leaf physical-bandwidth {
            type uint64;
            units "bit/s";
            description
              "Physical bandwidth of port QoS.";
          }
        }
      }
      container port-queue-onboard-statisticss {
        config false;
        description
          "List of port-queue statistics on board with ETM.";
        list port-queue-onboard-statistics {
          key "interface-name service-class";
          description
            "Statistics of port-queue on board with ETM.";
          leaf interface-name {
            type leafref {
              path "/ifm:ifm/ifm:interfaces/ifm:interface/ifm:name";
            }
            description
              "Interface name.";
          }
          leaf service-class {
            type qos-service-class;
            description
              "Class of service.";
          }
          leaf pass-packets {
            type uint64;
            units "packet";
            description
              "Number of passed packets.";
          }
          leaf pass-bytes {
            type uint64;
            units "Byte";
            description
              "Number of passed bytes.";
          }
          leaf drop-packets {
            type uint64;
            units "packet";
            description
              "Number of dropped packets.";
          }
          leaf drop-bytes {
            type uint64;
            units "Byte";
            description
              "Number of dropped bytes.";
          }
        }
      }
      container default-flow-queue-statisticss {
        description
          "List of sliced sub-interface default flow-queue statistics.";
        list default-flow-queue-statistics {
          key "interface-name service-class";
          description
            "Sliced sub-interface default flow-queue statistics.";
          leaf interface-name {
          type leafref {
            path "/ifm:ifm/ifm:interfaces/ifm:interface/ifm:name";
          }
          description
            "Interface name.";
          }
          leaf service-class {
          type qos-service-class-8cos;
          description
            "Service class.";
          }
          leaf pass-packets {
          type uint64;
          units "packet";
          description
            "Pass packets.";
          }
          leaf pass-bytes {
          type uint64;
          units "Byte";
          description
            "Pass bytes.";
          }
          leaf pass-packet-rate {
          type uint64;
          units "pps";
          description
            "Pass packet rate.";
          }
          leaf pass-byte-rate {
          type uint64;
          units "Byte/s";
          description
            "Pass byte rate.";
          }
          leaf discard-packets {
          type uint64;
          units "packet";
          description
            "Discard packets.";
          }
          leaf discard-bytes {
          type uint64;
          units "Byte";
          description
            "Discard bytes.";
          }
          leaf discard-packet-rate {
          type uint64;
          units "pps";
          description
            "Discard packet rate.";
          }
          leaf discard-byte-rate {
          type uint64;
          units "Byte/s";
          description
            "Discard byte rate.";
          }
          leaf total-buffer-size {
            type uint32;
            units "kB";
            description
              "Size of total buffer.";
          }
          leaf used-buffer-size {
            type uint32;
            units "kB";
            description
              "Size of used buffer.";
          }
        }
      }
      container interface-profile-statistics {
        description
          "Statistics of profile interfaces.";
        container user-queues {
          description
            "List of user queue statistics on interfaces.";
          list user-queue {
            key "interface-name pe-vlan-id vlan-id direction service-class";
            description
              "Statistics of user queue on interfaces.";
            leaf interface-name {
              type leafref {
                path "/ifm:ifm/ifm:interfaces/ifm:interface/ifm:name";
              }
              description
                "Interface name.";
            }
            leaf pe-vlan-id {
              type uint32 {
                range "0..4094";
              }
              description
                "Pe VLAN id.";
            }
            leaf vlan-id {
              type uint32 {
                range "0..4094";
              }
              description
                "VLAN id.";
            }
            leaf direction {
              type qos-direction-type;
              description
                "Direction of profile.";
            }
            leaf service-class {
              type qos-service-class-8cos;
              description
                "Class of service.";
            }
            leaf pass-packets {
              type uint64;
              units "packet";
              description
                "Number of passed packets.";
            }
            leaf pass-bytes {
              type uint64;
              units "Byte";
              description
                "Number of passed bytes.";
            }
            leaf pass-packet-rate {
              type uint64;
              units "pps";
              description
                "Rate of the packets passed during the latest 30 seconds.";
            }
            leaf pass-byte-rate {
              type uint64;
              units "Byte/s";
              description
                "Rate of the bytes passed during the latest 30 seconds.";
            }
            leaf drop-packets {
              type uint64;
              units "packet";
              description
                "Number of dropped packets.";
            }
            leaf drop-bytes {
              type uint64;
              units "Byte";
              description
                "Number of dropped bytes.";
            }
            leaf drop-packet-rate {
              type uint64;
              units "pps";
              description
                "Rate of the packets dropped during the latest 30 seconds.";
            }
            leaf drop-byte-rate {
              type uint64;
              units "Byte/s";
              description
                "Rate of the bytes dropped during the latest 30 seconds.";
            }
            leaf random-drop-packets {
              type uint64;
              units "packet";
              description
                "Number of random dropped packets.";
            }
            leaf random-drop-bytes {
              type uint64;
              units "Byte";
              description
                "Number of random dropped bytes.";
            }
            leaf random-drop-packet-rate {
              type uint64;
              units "pps";
              description
                "Rate of the packets random dropped during the latest 30 seconds.";
            }
            leaf random-drop-byte-rate {
              type uint64;
              units "Byte/s";
              description
                "Rate of the bytes random dropped during the latest 30 seconds.";
            }
            leaf time-stamp {
              type yang:date-and-time;
              description
                "Time of last packet received or sent.";
            }
            leaf buffer-total {
              type uint32;
              units "kB";
              description
                "Size of buffer.";
            }
            leaf buffer-used {
              type uint32;
              units "kB";
              description
                "Size of used buffer.";
            }
            leaf clear-time {
              type yang:date-and-time;
              description
                "Time of clearing statistics.";
            }
          }
        }
        container cars {
          description
            "List of profile CAR statistics on interfaces.";
          list car {
            key "car-type interface-name pe-vlan-id vlan-id direction";
            description
              "Statistics of profile CAR on interfaces.";
            leaf car-type {
              type statistics-car-type;
              description
                "Car type.";
            }
            leaf interface-name {
              type leafref {
                path "/ifm:ifm/ifm:interfaces/ifm:interface/ifm:name";
              }
              description
                "Interface name.";
            }
            leaf pe-vlan-id {
              type uint32 {
                range "0..4094";
              }
              description
                "Pe VLAN id.";
            }
            leaf vlan-id {
              type uint32 {
                range "0..4094";
              }
              description
                "VLAN id.";
            }
            leaf direction {
              type qos-direction-type;
              description
                "Direction of profile.";
            }
            leaf pass-packets {
              type uint64;
              units "packet";
              description
                "Number of passed packets.";
            }
            leaf pass-bytes {
              type uint64;
              units "Byte";
              description
                "Number of passed bytes.";
            }
            leaf pass-packet-rate {
              type uint64;
              units "pps";
              description
                "Rate of the packets passed during the latest 30 seconds.";
            }
            leaf pass-byte-rate {
              type uint64;
              units "Byte/s";
              description
                "Rate of the bytes passed during the latest 30 seconds.";
            }
            leaf drop-packets {
              type uint64;
              units "packet";
              description
                "Number of dropped packets.";
            }
            leaf drop-bytes {
              type uint64;
              units "Byte";
              description
                "Number of dropped bytes.";
            }
            leaf drop-packet-rate {
              type uint64;
              units "pps";
              description
                "Rate of the packets dropped during the latest 30 seconds.";
            }
            leaf drop-byte-rate {
              type uint64;
              units "Byte/s";
              description
                "Rate of the bytes dropped during the latest 30 seconds.";
            }
          }
        }
        container share-shapings {
          description
            "List of share-shaping statistics on interfaces.";
          list share-shaping {
            key "interface-name pe-vlan-id vlan-id direction shaping-id";
            description
              "Statistics of share-shaping on interfaces.";
            leaf interface-name {
              type leafref {
                path "/ifm:ifm/ifm:interfaces/ifm:interface/ifm:name";
              }
              description
                "Interface name.";
            }
            leaf pe-vlan-id {
              type uint32 {
                range "0..4094";
              }
              description
                "Pe VLAN id.";
            }
            leaf vlan-id {
              type uint32 {
                range "0..4094";
              }
              description
                "VLAN id.";
            }
            leaf direction {
              type qos-direction-type;
              description
                "Direction of profile.";
            }
            leaf shaping-id {
              type uint64;
              description
                "Shaping id.";
            }
            leaf pass-packets {
              type uint64;
              units "packet";
              description
                "Number of passed packets.";
            }
            leaf pass-bytes {
              type uint64;
              units "Byte";
              description
                "Number of passed bytes.";
            }
            leaf pass-packet-rate {
              type uint64;
              units "pps";
              description
                "Rate of the packets passed during the latest 30 seconds.";
            }
            leaf pass-byte-rate {
              type uint64;
              units "Byte/s";
              description
                "Rate of the bytes passed during the latest 30 seconds.";
            }
            leaf drop-packets {
              type uint64;
              units "packet";
              description
                "Number of dropped packets.";
            }
            leaf drop-bytes {
              type uint64;
              units "Byte";
              description
                "Number of dropped bytes.";
            }
            leaf drop-packet-rate {
              type uint64;
              units "pps";
              description
                "Rate of the packets dropped during the latest 30 seconds.";
            }
            leaf drop-byte-rate {
              type uint64;
              units "Byte/s";
              description
                "Rate of the bytes dropped during the latest 30 seconds.";
            }
          }
        }
        container priority-cars {
          description
            "List of priority CAR statistics on interfaces.";
          list priority-car {
            key "interface-name pe-vlan-id vlan-id direction priority-num";
            description
              "Statistics of priority car on interfaces.";
            leaf interface-name {
              type leafref {
                path "/ifm:ifm/ifm:interfaces/ifm:interface/ifm:name";
              }
              description
                "Interface name.";
            }
            leaf pe-vlan-id {
              type uint32 {
                range "0..4094";
              }
              description
                "Pe VLAN id.";
            }
            leaf vlan-id {
              type uint32 {
                range "0..4094";
              }
              description
                "VLAN id.";
            }
            leaf direction {
              type qos-direction-type;
              description
                "Direction of profile.";
            }
            leaf priority-num {
              type qos-priority-num-type;
              description
                "Direction of profile.";
            }
            leaf pass-packets {
              type uint64;
              units "packet";
              description
                "Number of passed packets.";
            }
            leaf pass-bytes {
              type uint64;
              units "Byte";
              description
                "Number of passed bytes.";
            }
            leaf pass-packet-rate {
              type uint64;
              units "pps";
              description
                "Rate of the packets passed during the latest 30 seconds.";
            }
            leaf pass-byte-rate {
              type uint64;
              units "Byte/s";
              description
                "Rate of the bytes passed during the latest 30 seconds.";
            }
            leaf drop-packets {
              type uint64;
              units "packet";
              description
                "Number of dropped packets.";
            }
            leaf drop-bytes {
              type uint64;
              units "Byte";
              description
                "Number of dropped bytes.";
            }
            leaf drop-packet-rate {
              type uint64;
              units "pps";
              description
                "Rate of the packets dropped during the latest 30 seconds.";
            }
            leaf drop-byte-rate {
              type uint64;
              units "Byte/s";
              description
                "Rate of the bytes dropped during the latest 30 seconds.";
            }
          }
        }        
      }
      container hard-pipe-abilitys {
        description
          "List of interface support for hard pipe.";
        list hard-pipe-ability {
          key "interface-name";
          description
            "Operational state of interface support for hard pipe.";
          leaf interface-name {
            type leafref {
              path "/ifm:ifm/ifm:interfaces/ifm:interface/ifm:name";
            }
            description
              "Interface name.";
          }
          leaf ability {
            type ability-type;
            description
              "Ability type.";
          }
        }
      }
      container l2vpn-hard-pipe-statisticss {
        description
          "List of hard pipe traffic statisticss on the AC side.";
        list l2vpn-hard-pipe-statistics {
          key "interface-name";
          description
            "Statistics of hard pipe on the AC side.";
          leaf interface-name {
            type leafref {
              path "/ifm:ifm/ifm:interfaces/ifm:interface/ifm:name";
            }
            description
              "Interface name.";
          }
          leaf direction {
            type qos-direction-inbound;
            description
              "Direction.";
          }
          leaf pass-packets {
            type uint64;
            units "packet";
            description
              "Pass packets.";
          }
          leaf pass-bytes {
            type uint64;
            units "Byte";
            description
              "Pass bytes.";
          }
          leaf drop-packets {
            type uint64;
            units "packet";
            description
              "Drop packets.";
          }
          leaf drop-bytes {
            type uint64;
            units "Byte";
            description
              "Drop bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packet-rate {
            type uint64;
            units "pps";
            description
              "Rate of the packets dropped during the latest 30 seconds.";
          }
          leaf drop-byte-rate {
            type uint64;
            units "Byte/s";
            description
              "Rate of the bytes dropped during the latest 30 seconds.";
          }
        }
      }
      container traffic-policy-template-application {
        description
          "Traffic policy template application state.";
        leaf total-classifier {
          type uint32;
          description
            "Total traffic classifier.";
        }
        leaf created-classifier {
          type uint32;
          description
            "Created traffic classifier.";
        }
        leaf free-classifier {
          type uint32;
          description
            "Free traffic classifier.";
        }
        leaf total-behavior {
          type uint32;
          description
            "Total traffic behavior.";
        }
        leaf created-behavior {
          type uint32;
          description
            "Created traffic behavior.";
        }
        leaf free-behavior {
          type uint32;
          description
            "Free traffic behavior.";
        }
        leaf total-policy {
          type uint32;
          description
            "Total traffic policy.";
        }
        leaf created-policy {
          type uint32;
          description
            "Created traffic policy.";
        }
        leaf free-policy {
          type uint32;
          description
            "Free traffic policy.";
        }
      }
      container flow-car-statisticss {
        description
          "List of flow CAR statisticss.";
        list flow-car-statistics {
          key "ip-type slot-id direction";
          description
            "Flow CAR statistics.";
          leaf ip-type {
            type stream-direction-type;
            description
              "Type of an IP address.";
          }
          leaf slot-id {
            type slot-id;
            description
              "Slot id. The chassis ID must also be specified when have multi chassis, such as 3, clc1/3 or ccc1/3.";
          }
          leaf direction {
            type qos-direction-type;
            description
              "Direction.";
          }
          leaf ip {
            type inet:ipv4-address-no-zone;
            description
              "Ip.";
          }
          leaf pass-packets {
            type uint64;
            units "packet";
            description
              "Number of passed packets.";
          }
          leaf pass-bytes {
            type uint64;
            units "Byte";
            description
              "Number of passed bytes.";
          }
          leaf pass-packet-rate {
            type uint64;
            units "pps";
            description
              "Rate of the packets passed.";
          }
          leaf pass-byte-rate {
            type uint64;
            units "Byte/s";
            description
              "Rate of the bytes passed.";
          }
          leaf drop-packets {
           type uint64;
            units "packet";
            description
              "Number of dropped packets.";
          }
          leaf drop-bytes {
            type uint64;
            units "Byte";
            description
              "Number of dropped bytes.";
          }
          leaf drop-packet-rate {
            type uint64;
            units "pps";
            description
              "Rate of the packets dropped.";
          }
          leaf drop-byte-rate {
            type uint64;
            units "Byte/s";
            description
              "Rate of the bytes dropped.";
          }
        }
      }
      container interface-action-user-queue-statisticss {
        description
          "List of user queue statistics on behavior.";
        list interface-action-user-queue-statistics {
          key "interface-name pe-vlan-id vlan-id direction classifier-name service-class";
          description
            "Statistics of user queue on behavior.";
          leaf interface-name {
            type leafref {
              path "/ifm:ifm/ifm:interfaces/ifm:interface/ifm:name";
            }
            description
              "Interface name.";
          }
          leaf pe-vlan-id {
            type uint16 {
              range "0..4094";
            }
            description
              "Pe VLAN id.";
          }
          leaf vlan-id {
            type uint16 {
              range "0..4094";
            }
            description
              "VLAN id.";
          }
          leaf direction {
            type qos-direction-type;
            description
              "Direction.";
          }
          leaf classifier-name {
            type leafref {
              path "/qos/classifier-template/traffic-classifiers/traffic-classifier/name";
            }
            description
              "Name of a traffic classifier.";
          }
          leaf service-class {
            type hqos-service-class;
            description
              "Class of service.";
          }
          leaf pass-packets {
            type uint64;
            units "packet";
            description
              "Number of passed packets.";
          }
          leaf pass-bytes {
            type uint64;
            units "Byte";
            description
              "Number of passed bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packets {
            type uint64;
            units "packet";
            description
              "Number of dropped packets.";
          }
          leaf drop-bytes {
            type uint64;
            units "Byte";
            description
              "Number of dropped bytes.";
          }
          leaf drop-packet-rate {
            type uint64;
            units "pps";
            description
              "Rate of the packets dropped during the latest 30 seconds.";
          }
          leaf drop-byte-rate {
            type uint64;
            units "Byte/s";
            description
              "Rate of the bytes dropped during the latest 30 seconds.";
          }
          leaf buffer-total {
            type uint32;
            units "kB";
            description
              "Size of buffer.";
          }
          leaf buffer-used {
            type uint32;
            units "kB";
            description
              "Size of used buffer.";
          }
        }
      }      
      container interface-user-group-queue-statistics {
        description
          "List of user group queue statistics on interfaces.";
        list interface-user-group-queue-statistic {
          key "interface-name pe-vlan-id vlan-id direction service-class";
          description
            "Statistics of user group queue on interfaces.";
          leaf interface-name {
            type leafref {
              path "/ifm:ifm/ifm:interfaces/ifm:interface/ifm:name";
            }
            description
              "Interface name.";
          }
          leaf pe-vlan-id {
            type uint32 {
              range "0..4094";
            }
            description
              "Pe VLAN id.";
          }
          leaf vlan-id {
            type uint16 {
              range "0..4094";
            }
            description
              "VLAN id.";
          }
          leaf direction {
            type qos-direction-type;
            description
              "Direction of user-group-queue.";
          }
          leaf service-class {
            type qos-service-class-filter;
            description
              "Class of service.";
          }
          leaf pass-packets {
            type uint64;
            units "packet";
            description
              "Number of passed packets.";
          }
          leaf pass-bytes {
            type uint64;
            units "Byte";
            description
              "Number of passed bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packets {
            type uint64;
            units "packet";
            description
              "Number of dropped packets.";
          }
          leaf drop-bytes {
            type uint64;
            units "Byte";
            description
              "Number of dropped bytes.";
          }
          leaf drop-packet-rate {
            type uint64;
            units "pps";
            description
              "Rate of the packets dropped during the latest 30 seconds.";
          }
          leaf drop-byte-rate {
            type uint64;
            units "Byte/s";
            description
              "Rate of the bytes dropped during the latest 30 seconds.";
          }
        }
      }
      container interface-sub-port-queue-statistics {
        description
          "List of sub port queue statistics on interfaces.";
        list interface-sub-port-queue-statistic {
          key "interface-name service-class";
          description
            "Statistics of sub port queue on interfaces.";
          leaf interface-name {
            type leafref {
              path "/ifm:ifm/ifm:interfaces/ifm:interface/ifm:name";
            }
            description
              "Interface name.";
          }
          leaf service-class {
            type qos-service-class-total;
            description
              "Class of service.";
          }
          leaf pass-packets {
            type uint64;
            units "packet";
            description
              "Number of passed packets.";
          }
          leaf pass-bytes {
            type uint64;
            units "Byte";
            description
              "Number of passed bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packets {
            type uint64;
            units "packet";
            description
              "Number of dropped packets.";
          }
          leaf drop-bytes {
            type uint64;
            units "Byte";
            description
              "Number of dropped bytes.";
          }
          leaf drop-packet-rate {
            type uint64;
            units "pps";
            description
              "Rate of the packets dropped during the latest 30 seconds.";
          }
          leaf drop-byte-rate {
            type uint64;
            units "Byte/s";
            description
              "Rate of the bytes dropped during the latest 30 seconds.";
          }
        }
      }
      container interface-hard-pipe-statisticss {
        description
          "List of interface hard pipe statistics.";
        list interface-hard-pipe-statistics {
          key "interface-name";
          description
            "Interface hard pipe statistics.";
          leaf interface-name {
            type leafref {
              path "/ifm:ifm/ifm:interfaces/ifm:interface/ifm:name";
            }
            description
              "Interface name.";
          }
          leaf pass-packets {
            type uint64;
            units "packet";
            description
              "Pass packets.";
          }
          leaf pass-bytes {
            type uint64;
            units "Byte";
            description
              "Pass bytes.";
          }
          leaf drop-packets {
            type uint64;
            units "packet";
            description
              "Drop packets.";
          }
          leaf drop-bytes {
            type uint64;
            units "Byte";
            description
              "Drop bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packet-rate {
            type uint64;
            units "pps";
            description
              "Rate of the packets dropped during the latest 30 seconds.";
          }
          leaf drop-byte-rate {
            type uint64;
            units "Byte/s";
            description
              "Rate of the bytes dropped during the latest 30 seconds.";
          }
        }
      }
      container acl-resource-usages {
        description
          "List of display acl resource usage.";
        list acl-resource-usage {
          key "slot-id chip-id resource-name";
          config false;
          description
            "Operational state of acl resource usage.";
          leaf slot-id {
            type string {
              length "1..32";
            }
            description
              "Slot id.";
          }
          leaf chip-id {
            type uint32;
            description
              "Chip id.";
          }
          leaf resource-name {
            type string {
              length "1..32";
            }
            description
              "Acl resource name.";
          }
          leaf acl-total {
            type uint32;
            description
              "Total acl resource.";
          }
          leaf acl-used {
            type uint32;
            description
              "Used acl resource.";
          }
        }
      }
      container acl-core-resource-usages {
        description
          "List of display acl core resource usage.";
        list acl-core-resource-usage {
          key "slot-id chip-id core-id resource-name";
          config false;
          description
            "Operational state of acl resource usage.";
          leaf slot-id {
            type string {
              length "1..32";
            }
            description
              "Slot id.";
          }
          leaf chip-id {
            type uint32;
            description
              "Chip id.";
          }
          leaf core-id {
            type uint32;
            description
              "Core id.";
          }
		      leaf resource-name {
            type string {
              length "1..32";
            }
            description
              "Acl resource name.";
          }
          leaf acl-total {
            type uint32;
            description
              "Total acl resource.";
          }
          leaf acl-used {
            type uint32;
            description
              "Used acl resource.";
          }
        }
      }
      container acl-bank-resource-usages {
        description
          "List of display acl bank resource usage.";
        list acl-bank-resource-usage {
          key "slot-id chip-id entry-used-list direction service-name";
          description
            "Operational state of display acl bank resource usage.";
          leaf slot-id {
            type string {
              length "1..32";
            }
            description
              "Slot id.";
          }
          leaf chip-id {
            type uint32;
            description
              "Chip id.";
          }
          leaf entry-used-list {
            type uint32;
            description
              "Used entry in bank.";
          }
          leaf direction {
            type string {
              length "1..32";
            }
            description
              "Direction.";
          }
          leaf service-name {
            type string {
              length "1..32";
            }
            description
              "Server name.";
          }
          leaf entry-free {
            type uint32;
            description
              "Free entry number in bank.";
          }
          leaf bankid-list {
            type string {
              length "1..255";
            }
            description
              "Name of bank.";
          }
          leaf service-type {
            type acl-service-type;
            description
              "Type of a delivered service.";
          }
          leaf group-id {
            type uint32;
            description
              "Group id.";
          }
        }
      }
      container acl-core-bank-resource-usages {
        description
          "List of display acl core bank resource usage.";
        list acl-core-bank-resource-usage {
          key "slot-id chip-id core-id entry-used-list direction service-name";
          description
            "Operational state of display acl bank resource usage.";
          leaf slot-id {
            type string {
              length "1..32";
            }
            description
              "Slot id.";
          }
          leaf chip-id {
            type uint32;
            description
              "Chip id.";
          }
          leaf core-id {
            type uint32;
            description
              "Core id.";
          }
          leaf entry-used-list {
            type uint32;
            description
              "Used entry in bank.";
          }
          leaf direction {
            type string {
              length "1..32";
            }
            description
              "Direction.";
          }
          leaf service-name {
            type string {
              length "1..32";
            }
            description
              "Server name.";
          }
          leaf entry-free {
            type uint32;
            description
              "Free entry number in bank.";
          }
          leaf bankid-list {
            type string {
              length "1..255";
            }
            description
              "Name of bank.";
          }
          leaf service-type {
            type acl-service-type;
            description
              "Type of a delivered service.";
          }
          leaf group-id {
            type uint32;
            description
              "Group id.";
          }
        }
      }
      container qos-resource-rules {
        description
          "List of resource rule.";
        list qos-resource-rule {
          key "rule-type slot-id resource-pool";
          description
            "Display resource rule state.";
          leaf rule-type {
            type rule-type;
            description
              "Rule type.";
          }
          leaf slot-id {
            type string {
              length "1..15";
              pattern '(c[cl]c\d+/)?\d+';
            }
            description
              "Slot ID. The chassis ID must also be specified when have multi chassis, such as 3, clc1/3 or ccc1/3.";
          }
          leaf resource-pool {
            type string {
              length "1..32";
            }
            description
              "Resource pool.";
          }
          leaf used-resource {
            type uint32;
            description
              "Used resource.";
          }
          leaf free-resource {
            type uint32;
            description
              "Free resource.";
          }
          leaf reserved-resource {
            type uint32;
            description
              "Reserved resource.";
          }
          leaf total-resource {
            type uint32;
            description
              "Total resource.";
          }
          leaf utilization-rate {
            type uint32{
              range "0..100";
            }
            description
              "Resource utilization rate.";
          }
        }
      }
      container sub-port-queue-resources {
        description
          "List of sub port queue resource state.";
        list sub-port-queue-resource {
          key "slot-id direction tm-type";
          description
            "Display sub port queue resource state.";
          leaf slot-id {
            type string {
              length "1..15";
              pattern '(c[cl]c\d+/)?\d+';
            }
            description
              "Slot ID. The chassis ID must also be specified when have multi chassis, such as 3, clc1/3 or ccc1/3.";
          }
          leaf direction {
            type out-direction-type;
            description
              "Direction.";
          }
          leaf tm-type {
            type string{
              length "1..32";
            }
            description
              "Resource TM type.";
          }
          leaf used-resource {
            type uint32;
            description
             "Used resource.";
          }
          leaf free-resource {
            type uint32;
            description
              "Free resource.";
          }
        }
      }
      container dp-resources {
        description
          "List of dp resource state.";
        list dp-resource {
          key "slot-id direction tm";
          description
            "Display dp resource state.";
          leaf slot-id {
            type string {
              length "1..15";
              pattern '(c[cl]c\d+/)?\d+';
            }
            description
              "Slot ID. The chassis ID must also be specified when have multi chassis, such as 3, clc1/3 or ccc1/3.";
          }
          leaf direction {
            type out-direction-type;
            description
              "Direction.";
          }
          leaf tm {
            type string{
              length "1..32";
            }
            description
              "TM.";
          }
          leaf used-resource {
            type uint32;
            description
             "Used resource.";
          }
          leaf free-resource {
            type uint32;
            description
              "Free resource.";
          }
        }
      }
      container interface-car-statisticss {
        description
          "List of interface CAR statistics.";
        list interface-car-statistics {
          key "interface-name direction vlan-id slot-id vid";
          description
            "Car statistics.";
          leaf interface-name {
            type leafref {
              path "/ifm:ifm/ifm:interfaces/ifm:interface/ifm:name";
            }
            description
              "Interface name.";
          }
          leaf direction {
            type qos-direction-type;
            description
              "Direction.";
          }
          leaf vlan-id {
            type uint16 {
              range "0..4094";
            }
            description
              "VLAN ID.";
          }
          leaf slot-id {
            type slot-id;
            description
              "Slot ID.";
          }
          leaf vid {
            type uint16 {
              range "0..4094";
            }
            description
              "Vid.";
          }
          uses car-statistics-type;
        }
      }
      container interface-simple-car-statisticss {
        description
          "List of interface CAR statistics.";
        list interface-simple-car-statistics {
          key "interface-name direction slot-id";
          description
            "Car statistics.";
          leaf interface-name {
            type leafref {
              path "/ifm:ifm/ifm:interfaces/ifm:interface/ifm:name";
            }
            description
              "Interface name.";
          }
          leaf direction {
            type qos-direction-type;
            description
              "Direction.";
          }
          leaf slot-id {
            type slot-id;
            description
              "Slot ID.";
          }
          leaf pass-packets {
            type uint64;
            units "packet";
            description
              "Pass packets.";
          }
          leaf pass-bytes {
            type uint64;
            units "Byte";
            description
              "Pass bytes.";
          }
          leaf drop-packets {
            type uint64;
            units "packet";
            description
              "Drop packets.";
          }
          leaf drop-bytes {
            type uint64;
            units "Byte";
            description
              "Drop bytes.";
          }
        }
      }
    container interface-car-l2-port-statisticss {
        description
          "List of interface CAR L2Port statistics.";
        list interface-car-l2-port-statistics {
          key "interface-name direction vlan-id slot-id";
          description
            "CAR L2Port statistics.";
          leaf interface-name {
            type leafref {
              path "/ifm:ifm/ifm:interfaces/ifm:interface/ifm:name";
            }
            description
              "Interface name.";
          }
          leaf direction {
            type qos-direction-type;
            description
              "Direction.";
          }
          leaf vlan-id {
            type uint16 {
              range "0..4094";
            }
            description
              "VLAN ID.";
          }
          leaf slot-id {
            type slot-id;
            description
              "Slot ID.";
          }
          uses car-statistics-type;
        }
      }
      container interface-car-8021p-dscp-statisticss {
        description
          "List of interface CAR 8021p DSCP statistics.";
        list interface-car-8021p-dscp-statistics {
          key "interface-name direction pe-vlan-id priority-value slot-id";
          description
            "CAR 8021p DSCP statistics.";
          leaf interface-name {
            type leafref {
              path "/ifm:ifm/ifm:interfaces/ifm:interface/ifm:name";
            }
            description
              "Interface name.";
          }
          leaf direction {
            type qos-direction-type;
            description
              "Direction.";
          }
          leaf pe-vlan-id {
            type uint16 {
              range "0..4094";
            }
            description
              "PE VLAN ID.";
          }
          leaf priority-value {
            type uint16 {
              range "0..63";
            }
            description
              "Priority Value.";
          }
          leaf slot-id {
            type slot-id;
            description
              "Slot ID.";
          }
          uses car-statistics-type;
        }
      }
      container interface-extend-statisticss {
        description
          "List of interface extend statistics.";
        list interface-extend-statistics {
          key "interface-name";
          description
            "Extend statistics.";
          leaf interface-name {
            type leafref {
              path "/ifm:ifm/ifm:interfaces/ifm:interface/ifm:name";
            }
            description
              "Interface name.";
          }
          leaf interface-car-inbound-drop-packets {
            type uint64;
            units "packet";
            description
              "Number of interface car inbound drop packets.";
          }
          leaf interface-car-outbound-drop-packets {
            type uint64;
            units "packet";
            description
              "Number of interface car outbound drop packets.";
          }
          leaf port-queue-outbound-drop-packets {
            type uint64;
            units "packet";
            description
              "Number of port queue outbound drop packets.";
          }
          leaf vlan-car-inbound-drop-packets {
            type uint64;
            units "packet";
            description
              "Number of arp VLAN car inbound drop packets.";
          }
          leaf vlan-car-outbound-drop-packets {
            type uint64;
            units "packet";
            description
              "Number of arp VLAN car outbound drop packets.";
          }
          leaf receive-packet-equal-64bytes {
            type string {
              length "1..32";
            }
            units "packet";
            description
              "Receive packets equal to 64 bytes.";
          }
          leaf receive-packet-between-65to127bytes {
            type string {
              length "1..32";
            }
            units "packet";
            description
              "Receive packets 65~127 bytes.";
          }
          leaf receive-packet-between-128to255bytes {
            type string {
              length "1..32";
            }
            units "packet";
            description
              "Receive packets 128~255 bytes.";
          }
          leaf receive-packet-between-256to511bytes {
            type string {
              length "1..32";
            }
            units "packet";
            description
              "Receive packets 256~511 bytes.";
          }
          leaf receive-packet-between-512to1023bytes {
            type string {
              length "1..32";
            }
            units "packet";
            description
              "Receive packets 512~1023 bytes.";
          }
          leaf receive-packet-between-1024to1518bytes {
            type string {
              length "1..32";
            }
            units "packet";
            description
              "Receive packets 1024~1518 bytes.";
          }
          leaf receive-packet-larger-1518bytes {
            type string {
              length "1..32";
            }
            units "packet";
            description
              "Receive packets more than 1518 bytes.";
          }
          leaf send-packet-equal-64bytes {
            type string {
              length "1..32";
            }
            units "packet";
            description
              "Send packets equal to 64 bytes.";
          }
          leaf send-packet-between-65to127bytes {
            type string {
              length "1..32";
            }
            units "packet";
            description
              "Send packets 65~127 bytes.";
          }
          leaf send-packet-between-128to255bytes {
            type string {
              length "1..32";
            }
            units "packet";
            description
              "Send packets 128~255 bytes.";
          }
          leaf send-packet-between-256to511bytes {
            type string {
              length "1..32";
            }
            units "packet";
            description
              "Send packets 256~511 bytes.";
          }
          leaf send-packet-between-512to1023bytes {
            type string {
              length "1..32";
            }
            units "packet";
            description
              "Send packets 512~1023 bytes.";
          }
          leaf send-packet-between-1024to1518bytes {
            type string {
              length "1..32";
            }
            units "packet";
            description
              "Send packets 1024~1518 bytes.";
          }
          leaf send-packet-larger-1518bytes {
            type string {
              length "1..32";
            }
            units "packet";
            description
              "Send packets more than 1518 bytes.";
          }
        }
      }
      container sub-port-queue-abnormal-allocations {
        description
          "List of the total allocation of sub port queue request resource failures.";
        list sub-port-queue-abnormal-allocation {
          key "slot-id direction";
          description
            "The total allocation list of sub port queue request resource failure state.";
          leaf slot-id {
            type slot-id;
            description
              "Slot ID.";
          }
          leaf direction {
            type out-direction-type;
            description
              "Direction.";
          }
          leaf total-abnormal-number {
            type uint32;
            description
              "Total abnormal number.";
          }
          container abnormal-configurations {
            description
              "List of sub port queue request resource failure.";
            list abnormal-configuration {
              key "interface-name";
              description
                "Sub port queue request resource failure state.";
              leaf interface-name {
                type leafref {
                  path "/ifm:ifm/ifm:interfaces/ifm:interface/ifm:name";
                }
                description
                  "Interface name.";
              }
              leaf configuration {
                type string{
                  length "1..128";
                }
                description
                  "Configuration information.";
              }
            }
          }
        }
      }
      container user-group-queue-abnormal-allocations {
        description
          "List of the total allocation of user group queue request resource failures.";
        list user-group-queue-abnormal-allocation {
          key "slot-id direction";
          description
            "The total allocation list of user group queue request resource failure state.";
          leaf slot-id {
            type slot-id;
            description
              "Slot ID.";
          }
          leaf direction {
            type qos-direction-type;
            description
              "Direction.";
          }
          leaf total-abnormal-number {
            type uint32;
            description
              "Total abnormal number.";
          }
          container abnormal-configurations {
            description
              "List of user group queue request resource failure.";
            list abnormal-configuration {
              key "interface-name";
              description
                "User group queue request resource failure state.";
              leaf interface-name {
                type leafref {
                  path "/ifm:ifm/ifm:interfaces/ifm:interface/ifm:name";
                }
                description
                  "Interface name.";
              }
              leaf configuration {
                type string{
                  length "1..128";
                }
                description
                "Configuration information.";
              }
            }
          }
        }
      }
      container user-queue-abnormal-allocations {
        description
          "List of the total allocation of user queue request resource failures.";
        list user-queue-abnormal-allocation {
          key "slot-id direction";
          description
            "The total allocation list of user queue request resource failure state.";
          leaf slot-id {
            type slot-id;
            description
              "Slot ID.";
          }
          leaf direction {
            type qos-direction-type;
            description
              "Direction.";
          }
          leaf total-abnormal-number {
            type uint32;
            description
              "Total abnormal number.";
          }
          container abnormal-configurations {
            description
              "List of qos profile request resource failure.";
            list abnormal-configuration {
              key "interface-name";
              description
                "QoS profile request resource failure state.";
              leaf interface-name {
                type string{
                  length "1..64";
                }
                description
                  "Interface name.";
              }
              leaf configuration {
                type string{
                  length "1..128";
                }
                description
                  "Configuration information.";
              }
            }
          }
        }
      }
      container user-queue-resources {
        description
          "List of user queue resource.";
        list user-queue-resource {
          key "slot-id direction tm-type resource-pool";
          description
            "Display user queue resource state.";
          leaf slot-id {
            type string {
              length "1..15";
            }
            description
              "Slot ID.";
          }
          leaf direction {
            type qos-direction-type;
            description
              "Direction.";
          }
          leaf tm-type {
            type string {
              length "1..32";
            }
            description
              "Resource TM type.";
          }
          leaf resource-pool {
            type string {
              length "1..32";
            }
            description
              "Resource pool.";
          }
          leaf used-id-resource {
            type string {
              length "1..16";
            }
            description
              "Used ID resource.";
          }
          leaf free-id-resource {
            type string {
            length "1..16";
            }
              description
            "Free ID resource.";
          }
          leaf used-cir-resource {
            type string {
              length "1..16";
            }
            description
              "Used cir resource.";
          }
          leaf used-pir-resource {
            type string {
              length "1..16";
            }
            description
              "Used pir resource.";
          }
          leaf free-cir-resource {
            type string {
              length "1..16";
            }
            description
              "Free cir resource.";
          }
          leaf free-pir-resource {
            type string {
              length "1..16";
            }
            description
              "Free pir resource.";
          }
        }
      }
      container fabric-queue-unicast-statisticss {
        description
          "List of fabric queue unicast statistics.";
        list fabric-queue-unicast-statistics {
          key "source-slot-id destination-slot-id";
          description
            "Fabric queue unicast statistics.";
          leaf source-slot-id {
            type string {
              length "1..32";
              pattern '(c[cl]c\d+/)?\d+';
            }
            description
              "Source slot ID.";
          }
          leaf destination-slot-id {
            type string {
              length "1..32";
              pattern '(c[cl]c\d+/)?\d+';
            }
            description
              "Destination slot ID.";
          }
          leaf cos-value-type {
            type cos-value-type;
            description
              "Service class type.";
          }
          leaf source-tm-number {
            type uint32;
            description
              "Source TM number.";
          }
          leaf destination-tm-number {
            type uint32;
            description
              "Destination TM number.";
          }
          leaf pass-packets {
            type uint64;
            units "packet";
            description
              "Number of passed packets.";
          }
          leaf pass-bytes {
            type uint64;
            units "Byte";
            description
             "Number of passed bytes.";
          }
          leaf discard-packets {
            type uint64;
            units "packet";
            description
              "Number of dropped packets.";
          }
          leaf discard-bytes {
            type uint64;
            units "Byte";
            description
              "Number of dropped bytes.";
          }
        }
      }
      container fabric-queue-multicast-statisticss {
        description
          "List of fabric queue multicast statistics.";
        list fabric-queue-multicast-statistics {
          key "source-slot-id";
          description
            "Fabric queue multicast statistics.";
          leaf source-slot-id {
            type string {
              length "1..32";
              pattern '(c[cl]c\d+/)?\d+';
            }
            description
              "Source slot ID.";
          }
          leaf cos-value-type {
            type cos-value-type;
            description
              "Service class type.";
          }
          leaf source-tm-number {
            type uint32;
            description
              "Source TM number.";
          }
          leaf destination-tm-number {
            type uint32;
            description
              "Destination TM number.";
          }
          leaf pass-packets {
            type uint64;
            units "packet";
            description
              "Number of passed packets.";
          }
          leaf pass-bytes {
            type uint64;
            units "Byte";
            description
             "Number of passed bytes.";
          }
          leaf discard-packets {
            type uint64;
            units "packet";
            description
              "Number of dropped packets.";
          }
          leaf discard-bytes {
            type uint64;
            units "Byte";
            description
              "Number of dropped bytes.";
          }
        }
      }
      container slot-port-queue-statisticss {
        description
          "List of statistics on traffic shaping on interfaces based slot.";
        list slot-port-queue-statistics {
          key "slot-id service-class";
          description
            "Port queue statistics.";
          leaf slot-id {
            type string {
              length "1..15";
              pattern '(c[cl]c\d+/)?\d+';
            }
            description
              "Slot ID. The chassis ID must also be specified when have multi chassis, such as 3, clc1/3 or ccc1/3.";
          }
          leaf service-class {
            type qos-service-class;
            description
              "Class of service.";
          }
          leaf pass-packets {
            type uint64;
            units "packet";
            description
              "Number of passed packets.";
          }
          leaf pass-bytes {
            type uint64;
            units "Byte";
            description
              "Number of passed bytes.";
          }
          leaf pass-packet-rate {
            type uint64;
            units "pps";
            description
              "Rate of the packets passed during the latest 30 seconds.";
          }
          leaf pass-byte-rate {
            type uint64;
            units "Byte/s";
            description
              "Rate of the bytes passed during the latest 30 seconds.";
          }
          leaf drop-packets {
            type uint64;
            units "packet";
            description
              "Number of dropped packets.";
          }
          leaf drop-tail-packets {
            type uint64;
            units "packet";
            description
              "Drop tail packets.";
          }
          leaf drop-wred-packets {
            type uint64;
            units "packet";
            description
              "Drop wred packets.";
          }
          leaf drop-bytes {
            type uint64;
            units "Byte";
            description
              "Number of dropped bytes.";
          }
          leaf drop-tail-bytes {
            type uint64;
            units "Byte";
            description
              "Drop tail bytes.";
          }
          leaf drop-wred-bytes {
            type uint64;
            units "Byte";
            description
              "Drop wred bytes.";
          }
          leaf drop-packet-rate {
            type uint64;
            units "pps";
            description
              "Rate of the packets dropped during the latest 30 seconds.";
          }
          leaf drop-tail-packet-rate {
            type uint64;
            units "pps";
            description
              "Drop tail packet rate.";
          }
          leaf drop-wred-packet-rate {
            type uint64;
            units "pps";
            description
              "Drop wred packet rate.";
          }
          leaf drop-byte-rate {
            type uint64;
            units "Byte/s";
            description
              "Rate of the bytes dropped during the latest 30 seconds.";
          }
          leaf drop-tail-byte-rate {
            type uint64;
            units "Byte/s";
            description
              "Drop tail byte rate.";
          }
          leaf drop-wred-byte-rate {
            type uint64;
            units "Byte/s";
            description
              "Drop wred byte rate.";
          }
        }
      }
      container slot-channel-profile-statisticss {
        description
          "List of channel parameters of a board.";
        list slot-channel-profile-statistics {
          key "slot-id tm-id channel-id";
          description
            "Operational state of the channel profile.";
          leaf slot-id {
            type slot-id;
            description
              "Slot ID.";
          }
          leaf tm-id {
            type uint8 {
              range "0..1";
            }
            description
              "TM ID.";
          }
          leaf channel-id {
            type uint8 {
              range "0..15";
            }
            description
              "Channel ID.";
          }
          leaf channel-profile-name {
            type leafref {
              path "../../../../queue-scheduler-template/channel-profiles/channel-profile/name";
            }
            description
              "Channel profile name.";
          }
          leaf slot-configured-bandwidth {
            type uint32;
            units "kbit/s";
            description
              "Configured bandwidth of board.";
          }
          leaf slot-real-bandwidth {
            type uint32;
            units "kbit/s";
            description
              "Real bandwidth of board.";
          }
          leaf slot-quantity {
            type uint32;
            description
              "Quantity of board.";
          }
          leaf slot-max-quantity {
            type uint32;
            description
              "Max quantity of board.";
          }
          leaf bandwidth-pool-0 {
            type uint32;
            units "kbit/s";
            description
              "Bandwidth of pool 0.";
          }
          leaf bandwidth-pool-1 {
            type uint32;
            units "kbit/s";
            description
              "Bandwidth of pool 1.";
          }
          leaf used-quantity-pool-0 {
            type uint32;
            description
              "Used quantity pool 0.";
          }
          leaf free-quantity-pool-0 {
            type uint32;
            description
              "Free quantity pool 0.";
          }
          leaf used-quantity-pool-1 {
            type uint32;
            description
              "Used quantity pool 1.";
          }
          leaf free-quantity-pool-1 {
            type uint32;
            description
              "Free quantity pool 1.";
          }
          leaf used-pir-pool-0 {
            type uint32;
            units "kbit/s";
            description
              "Used pir pool 0.";
          }
          leaf free-pir-pool-0 {
            type uint32;
            units "kbit/s";
            description
              "Free pir pool 0.";
          }
          leaf used-banknote-pool-0 {
            type uint32;
            description
              "Used banknote pool 0.";
          }
          leaf free-banknote-pool-0 {
            type uint32;
            description
              "Free banknote pool 0.";
          }
          leaf used-pir-pool-1 {
            type uint32;
            units "kbit/s";
            description
              "Used pir pool 1.";
          }
          leaf free-pir-pool-1 {
            type uint32;
            units "kbit/s";
            description
              "Free pir pool 1.";
          }
          leaf used-banknote-pool-1 {
            type uint32;
            description
              "Used banknote pool 1.";
          }
          leaf free-banknote-pool-1 {
            type uint32;
            description
              "Free banknote pool 1.";
          }
          leaf auto-adjustment {
            type switch-flag;
            description
              "Auto adjustment configuration.";
          }
          leaf auto-adjustment-state {
            type auto-adjustment-state;
            description
              "Auto adjustment state.";
          }
        }
      }
      container interface-ecn-thresholds {
        description
          "List of information about the ECN threshold.";
        list interface-ecn-threshold {
          key "interface-name queue-id";
          config false;
          description
            "Operational state of information about the ECN threshold.";
          leaf interface-name {
            type string {
              length "1..63";
            }
            description
              "Interface name.";
          }
          leaf queue-id {
            type uint8{
              range "0..7";
            }
            description
              "Queue index.";
          }
          leaf ecn-min {
            type uint32;
            units "kB";
            description
              "Lower ECN threshold.";
          }
          leaf ecn-max {
            type uint32;
            units "kB";
            description
              "Upper ECN threshold.";
          }
          leaf probability {
            type uint32;
            units "%";
            description
              "Maximum drop probability of the ECN.";
          }
          leaf queue-size {
            type uint32;
            units "kB";
            description
              "Maximum drop probability of the ECN.";
          }
        }
      }
      container slot-forward-modes {
        description
          "List of the configured and currently used packet forwarding modes.";
        list slot-forward-mode {
          key "slot-id";
          config false;
          description
            "Operational state of display the configured and currently used packet forwarding modes.";
          leaf slot-id {
            type slot-id;
            description
              "Slot ID.";
          }
          leaf config-mode {
            type qos:forward-mode;
            description
              "Configured packet forwarding mode.";
          }
          leaf current-mode {
            type qos:forward-mode;
            description
              "Currently used packet forwarding mode.";
          }
        }
      }
      container interface-monitoring-results {
        description
          "List of display historical information about congestion monitoring of queues on a specified interface.";
        list interface-monitoring-result {
          key "interface-name queue-id record-number query-type";
          description
            "Operational data of congestion monitoring of queues on a specified interface.";
          leaf interface-name {
            type string {
              length "1..63";
            }
            description
              "Monitoring result for interface name.";
          }
          leaf queue-id {
            type uint8 {
              range "0..7";
            }
            description
              "Monitoring result for queue id.";
          }
          leaf record-number {
            type uint8 {
              range "1..100";
            }
            description
              "Monitoring result for record number.";
          }
          leaf query-type {
            type qos-query-type;
            description
              "Monitoring result for Query type.";
          }
          leaf time {
            type yang:date-and-time;
            description
              "Monitoring result for data time.";
          }
          leaf buffer-usage {
            type uint32;
            description
              "Monitoring result for buff usage.";
          }
          leaf percent {
            type uint8;
            units "%";
            description
              "Monitoring result for percent value.";
          }
          leaf burst-start-time {
            type yang:date-and-time;
            description
              "Time when microbursts start.";
          }
          leaf burst-start-buffer {
            type uint32;
            description
              "Buffer usage when microbursts start.";
          }
          leaf burst-start-buffer-percent {
            type uint8;
            units "%";
            description
              "The percentage of buffer usage when microbursts start.";
          }
          leaf burst-peak-time {
            type yang:date-and-time;
            description
              "Time when the microburst buffer usage reaches the peak value.";
          }
          leaf burst-peak-buffer {
            type uint32;
            description
              "Buffer usage when the microburst buffer usage reaches the peak value.";
          }
          leaf burst-peak-buffer-percent {
            type uint8;
            units "%";
            description
              "The percentage of buffer usage when the microburst buffer usage reaches the peak value.";
          }
          leaf slot-id {
            type uint32;
            description
              "Slot-id.";
          }
          leaf burst-number {
            type uint32;
            description
              "The number of microbursts.";
          }
        }
      }
      container scheduler-tree-share-dps {
        description
          "List of scheduler-tree share-dp state.";
        list scheduler-tree-share-dp {
          key "slot-id interface-name";
          description
            "Scheduler-tree share-dp state.";
          leaf slot-id {
            type string {
              length "1..15";
            }
            description
              "Slot id.";
          }
          leaf interface-name {
            type leafref {
              path "/ifm:ifm/ifm:interfaces/ifm:interface/ifm:name";
            }
            description
              "Interface name.";
          }
          leaf trunk-name {
            type leafref {
              path "/ifm:ifm/ifm:interfaces/ifm:interface/ifm:name";
            }
            description
              "Trunk name.";
          }
          leaf tm-id {
            type uint32;
            description
              "TM ID.";
          }
          leaf sq-id {
            type uint32;
            description
              "SQ ID.";
          }
          leaf gq-id {
            type uint32;
            description
              "GQ ID.";
          }
          leaf vi-id {
            type uint32;
            description
              "VI ID.";
          }
          leaf dp-id {
            type uint32;
            description
              "DP ID.";
          }
        }
      }
      container tm-chip-buffer-usage-statisticss {
        description
          "List of tm chip buffer usage.";
        list tm-chip-buffer-usage-statistics {
          key "slot-id";
          description
            "Operational state of slot buffer usage.";
          leaf slot-id {
            type slot-id;
            description
              "Slot ID.";
          }
          leaf total-buffer {
            type uint64;
            units "kB";
            description
              "Total buffer size.";
          }
          leaf used-buffer {
            type uint64;
            units "kB";
            description
              "Current used buffer size.";
          }
          leaf used-percentage {
            type uint32 {
              range "0..100";
            }
            units "%";
            description
              "Current used buffer percentage.";
          }
        }
      }
      container intf-ing-buf-usage-statisticss {
        config false;
        description
          "List of interface buffer ingress-usage statistics.";
        list intf-ing-buf-usage-statistics {
          key "interface-name queue-id";
          description
              "Statistics of interface ingress buffer-usage.";
          leaf interface-name {
              type leafref {
                path "/ifm:ifm/ifm:interfaces/ifm:interface/ifm:name";
              }
              description
                  "Interface name.";
          }
          leaf queue-id {
              type uint32;
              description
                  "Queue index.";
          }
          leaf pfc-dynamic {
              type boolean;
              description
                  "Is pfc dynamic.";
          }
          leaf current-guaranteed {
              type uint32;
              units "Byte";
              description
                  "Current guaranteed buffer.";
          }
          leaf total-guaranteed {
              type uint32;
              units "Byte";
              description
                  "Total guaranteed buffer.";
          }
          leaf current-buffer {
              type uint32;
              units "Byte";
              description
                  "Current buffer.";
          }
          leaf total-buffer {
              type uint32;
              units "Byte";
              description
                  "Total buffer.";
          }
          leaf current-headroom {
              type uint32;
              units "Byte";
              description
                  "Current headroom buffer.";
          }
          leaf total-headroom {
              type uint32;
              units "Byte";
              description
                  "Total headroom buffer.";
          }
        }
      }
    }
  }
  rpc reset-interface-traffic-policy-statistics {
    description
      "To clear traffic policy statistics."; 
    ext:node-ref "/qos:qos/qos:global-query/qos:interface-traffic-policy-statisticss";
    input {
      leaf interface-name {
        type leafref {
          path "/ifm:ifm/ifm:interfaces/ifm:interface/ifm:name";
        }
        mandatory true;
        description
          "Interface name.";
      }
      leaf policy-name {
        type leafref {
          path "/qos:qos/qos:classifier-template/qos:traffic-policys/qos:traffic-policy/qos:name";
        }
        description
          "Policy name.";
      }
      leaf classifier-name {
        type leafref {
          path "/qos:qos/qos:classifier-template/qos:traffic-classifiers/qos:traffic-classifier/qos:name";
        }
        description
          "Classifier name.";
      }
      leaf direction {
        type qos-direction-type;
        mandatory true;
        description
          "Direction.";
      }
      leaf pe-vlan-id {
        type uint32 {
          range "0..4094";
        }
        mandatory true;
        description
          "Pe VLAN id.";
      }
      leaf vlan-id {
        type uint32 {
          range "0..4094";
        }
        mandatory true;
        description
          "VLAN id.";
      }
    }
  }//rpc reset-interface-traffic-policy-statistics
  rpc reset-multi-policy-statistics {
    description
      "To clear multiple traffic policy statistics."; 
    ext:node-ref "/qos:qos/qos:global-query/qos:interface-traffic-policy-statisticss/qos:interface-traffic-policy-statistics/qos:multi-policy-statisticss";
    input {
      leaf interface-name {
        type leafref {
          path "/ifm:ifm/ifm:interfaces/ifm:interface/ifm:name";
        }
        mandatory true;
        description
          "Interface name.";
      }
      leaf direction {
        type qos-direction-type;
        mandatory true;
        description
          "Direction.";
      }
      leaf traffic-policy-name {
        type leafref {
          path "/qos:qos/qos:classifier-template/qos:traffic-policys/qos:traffic-policy/qos:name";
        }
        mandatory true;
        description
          "Policy name.";
      }
    }
  }//rpc reset-multi-policy-statistics
  rpc reset-mpls-te-statistics {
    description
      "To clear MPLS te statistics.";
    ext:node-ref "/qos:qos/qos:global-query/qos:mpls-te-statisticss";
    input {
      leaf interface-name {
        type string {
              length "1..64";
            }
        mandatory true;
        description
          "Interface name.";
      }
      leaf direction {
        type qos-direction-type;
        mandatory true;
        description
          "Direction.";
      }
    }
  }//rpc reset-mpls-te-statistics
  rpc reset-global-policy-statistics {
    description
      "Clear global policy statistics.";
    ext:node-ref "/qos:qos/qos:global-config/qos:global-policys/qos:global-policy/qos:global-policy-statisticss";
    input {
      leaf direction {
        type qos-direction-type;
        mandatory true;
        description
          "Direction.";
      }
      leaf slot-id {
        type slot-id;
        description
          "Slot id.";
      }
      leaf policy-name {
        type template-name;
        mandatory true;
        description
          "Policy name.";
      }
      leaf classifier-name {
        type leafref {
          path "/qos:qos/qos:classifier-template/qos:traffic-classifiers/qos:traffic-classifier/qos:name";
        }
        description
          "Classifier name.";
      }
    }
  }
  rpc reset-user-group-queue-statistics {
    description
      "Clear user group statistics.";
    ext:node-ref "/qos:qos/qos:queue-scheduler-template/qos:user-group-queues/qos:user-group-queue/qos:user-group-queue-statisticss";
    input {
      leaf user-group-queue-name {
        type leafref {
            path "/qos:qos/qos:queue-scheduler-template/qos:user-group-queues/qos:user-group-queue/qos:name";
        }
        mandatory true;
        description
          "User group queue name.";
      }
      leaf direction {
        type qos-gq-direction-type;
        mandatory true;
        description
          "Direction.";
      }
      leaf slot-id {
        type slot-id;
        description
          "Slot id.";
      }
    }
  }
  rpc reset-vlan-traffic-policy-statistics {
    ext:node-ref "/qos:qos/qos:global-query/qos:vlan-traffic-policy-statisticss";
    description
      "To clear VLAN traffic policy statistics.";
    input  {
      leaf policy-name {
        type leafref {
          path "/qos:qos/qos:classifier-template/qos:traffic-policys/qos:traffic-policy/qos:name";
        }
        description
          "Traffic policy name.";
      }
      leaf classifier-name {
        type leafref {
          path "/qos:qos/qos:classifier-template/qos:traffic-classifiers/qos:traffic-classifier/qos:name";
        }
        description
          "Classifier name.";
      }
      leaf direction {
        type qos:qos-direction-type;
        description
          "Direction.";
      }
      leaf vlan-id {
        type uint16 {
          range "1..4094";
        }
        description
          "VLAN id.";
      }
    }
  }
  rpc reset-vpn-traffic-policy-statistics {
    ext:node-ref "/qos:qos/qos:global-query/qos:vpn-traffic-policy-statisticss";
    description
      "To clear vpn traffic policy statistics.";
    input  {
      leaf vpn-instance {
        type leafref {
          path "/ni:network-instance/ni:instances/ni:instance/ni:name";
        }
        description
          "Vpn instance.";
      }
      leaf policy-name {
        type leafref {
          path "/qos:qos/qos:classifier-template/qos:traffic-policys/qos:traffic-policy/qos:name";
        }
        description
          "Traffic policy name.";
      }
      leaf classifier-name {
        type leafref {
          path "/qos:qos/qos:classifier-template/qos:traffic-classifiers/qos:traffic-classifier/qos:name";
        }
        description
          "Classifier name.";
      }
      leaf direction {
        type qos:qos-direction-type;
        description
          "Direction.";
      }
    }
  }
  rpc reset-interface-profile-statistics {
    description
      "To clear profile statistics of interface.";
    ext:node-ref "/qos:qos/qos:global-query/qos:interface-profile-statistics";
    input {
      leaf interface-name {
        type string {
              length "1..88";
            }
        mandatory true;
        description
          "Interface name.";
      }
      leaf direction {
        type qos-direction-type;
        mandatory true;
        description
          "Direction.";
      }
      leaf pe-vlan-id {
        type uint32 {
          range "0..4094";
        }
        mandatory true;
        description
          "Pe VLAN id.";
      }
      leaf vlan-id {
        type uint32 {
          range "0..4094";
        }
        mandatory true;
        description
          "VLAN id.";
      }
    }
  }//rpc reset-interface-profile-user-queue-statistics
  rpc reset-interface-default-flow-queue-statistics {
    description
      "To clear default flow queue statistics of interface.";
    ext:node-ref "/qos:qos/qos:global-query/qos:default-flow-queue-statisticss";
    input {
      leaf interface-name {
        type string {
          length "1..64";
        }
        mandatory true;
        description
          "Interface name.";
      }
    }
  }//rpc reset-interface-default-flow-queue-statistics
  rpc reset-interface-hard-pipe-statistics {
    description
      "To clear hard pipe statistics of interface.";
    ext:node-ref "/qos:qos/qos:global-query/qos:interface-hard-pipe-statisticss";
    input {
      leaf interface-name {
        type string {
          length "1..64";
        }
        mandatory true;
        description
          "Interface name.";
      }
    }
  }//rpc reset-interface-hard-pipe-statistics
  rpc reset-interface-lv-hard-pipe-statistics {
    description
      "To clear MPLS l2vpn hard pipe statistics of interface.";
    ext:node-ref "/qos:qos/qos:global-query/qos:l2vpn-hard-pipe-statisticss";
    input {
      leaf interface-name {
        type string {
          length "1..64";
        }
        mandatory true;
        description
          "Interface name.";
      }
    }
  }//rpc reset-interface-lv-hard-pipe-statistics
  rpc reset-interface-car-statistics {
    description
      "To clear car statistics of interface.";
    ext:node-ref "/qos:qos/qos:global-query/qos:interface-car-statisticss";
    ext:node-ref "/qos:qos/qos:global-query/qos:interface-car-l2-port-statisticss";
    ext:node-ref "/qos:qos/qos:global-query/qos:interface-car-8021p-dscp-statisticss";
    input {
      leaf interface-name {
        type string {
          length "1..63";
        }
        mandatory true;
        description
          "Interface name.";
      }
      leaf direction {
        type qos-direction-type;
        mandatory true;
        description
          "Direction.";
      }
      leaf vlan-id {
        type uint16 {
          range "0..4094";
        }
        description
          "VLAN id.";
      }
      leaf vid {
        type uint16 {
          range "0..4094";
        }
        description
          "Vid.";
      }
      leaf ce-vid {
        type uint16 {
          range "0..4094";
        }
        description
          "Ce vid.";
      }
    }
  }//rpc reset-interface-car-statistics
  rpc reset-interface-user-group-queue-statistics {
    description
      "Clear user group statistics.";
    ext:node-ref "/qos:qos/qos:global-query/qos:interface-user-group-queue-statistics";
    input {
      leaf interface-name {
        type string {
          length "1..64";
        }
        mandatory true;
        description
          "Interface name.";
      }
      leaf direction {
        type qos-direction-type;
        mandatory true;
        description
          "Direction.";
      }
      leaf pe-vlan-id {
        type uint32 {
          range "1..4094";
        }
        description
          "Pe VLAN id.";
      }
      leaf ce-vlan-id {
        type uint32 {
          range "1..4094";
        }
        description
          "Ce VLAN id.";
      }
      leaf vlan-id {
        type uint32 {
          range "1..4094";
        }
        description
          "VLAN id.";
      }
    }
  }//rpc reset-interface-user-group-queue-statistics
  rpc reset-interface-user-queue-statistics {
    description
      "Clear user queue statistics.";
    ext:node-ref "/ifm:ifm/ifm:interfaces/ifm:interface/qos:qos/qos:user-queue-applys/qos:user-queue-apply/qos:user-queue-applys-stats";
    input {
      leaf interface-name {
        type string {
          length "1..64";
        }
        mandatory true;
        description
          "Interface name.";
      }
      leaf direction {
        type qos-direction-type;
        mandatory true;
        description
          "Direction.";
      }
    }
  }//rpc reset-interface-user-queue-statistics  
    rpc reset-interface-action-user-queue-statistics {
    description
      "Clear action user queue statistics.";
    ext:node-ref "/qos:qos/qos:global-query/qos:interface-action-user-queue-statisticss";
    input {
      leaf interface-name {
        type leafref {
          path "/ifm:ifm/ifm:interfaces/ifm:interface/ifm:name";
        }
        mandatory true;
        description
          "Interface name.";
      }
      leaf direction {
        type qos-direction-type;
        mandatory true;
        description
          "Direction.";
      }
      leaf classifier-name {
        type leafref {
          path "/qos:qos/qos:classifier-template/qos:traffic-classifiers/qos:traffic-classifier/qos:name";
        }
        mandatory true;
        description
          "Name of a traffic classifier.";
      }
      leaf pe-vlan-id {
        type uint16 {
          range "1..4094";
        }
        description
          "Pe VLAN id.";
      }
      leaf vlan-id {
        type uint16 {
          range "1..4094";
        }
        description
          "VLAN id.";
      }
    }
  }//rpc reset-interface-action-user-queue-statistics
  rpc reset-interface-port-queue-statistics {
    description
      "To clear interface port queue statistics.";
    ext:node-ref "/qos:qos/qos:global-query/qos:port-queue-statisticss";
    ext:node-ref "/qos:qos/qos:global-query/qos:port-queue-default-statisticss";
    ext:node-ref "/qos:qos/qos:global-query/qos:port-queue-onboard-statisticss";
    input {
      leaf interface-name {
        type leafref {
          path "/ifm:ifm/ifm:interfaces/ifm:interface/ifm:name";
        }
        description
          "Interface name.";
      }
      leaf service-class {
        type qos-service-class;
        description
          "Class of service.";
      }
      leaf on-board {
        type empty;
        description
          "On board.";
      }
      leaf default {
        type empty;
        description
          "Default.";
      }
    }
  }//rpc reset-interface-port-queue-statistics
  rpc reset-slot-port-queue-statistics {
    description
      "To clear slot port queue statistics.";
    ext:node-ref "/qos:qos/qos:global-query/qos:slot-port-queue-statisticss";
    input {
      leaf slot-id {
        type slot-id;
        mandatory true;
        description
          "Slot ID.";
      }
      leaf service-class {
        type qos-service-class;
        description
          "Class of service.";
      }
    }
  }//rpc reset-slot-port-queue-statistics
  rpc reset-user-informations {
    description
      "To clear QoS user information.";
    ext:node-ref "/qos:qos/qos:global-query/qos:user-informations";
    input {
      leaf id {
        type uint32 {
          range "0..4294967294";
        }
        mandatory true;
        description
          "User ID.";
      }
      leaf direction {
        type qos-direction-type;
        mandatory true;
        description
          "Direction.";
      }
    }
  }//reset-user-informations
  rpc reset-queue-statistics {
    description
      "To clear interface qos queue statistics.";
    ext:node-ref "/qos:qos/qos:global-query/qos:queue-statisticss";
    input {
      leaf interface-name {
        type leafref {
          path "/ifm:ifm/ifm:interfaces/ifm:interface/ifm:name";
        }
        description
          "Interface name.";
      }
      leaf service-class {
        type qos-service-class;
        description
          "Class of service.";
      }
      leaf slot-id {
        type string {
          length "1..31";
          pattern '(c[cl]c\d+/)?\d+';
        }
        description
          "Slot ID.";
      }
    }
  }//reset-queue-statistics
  rpc reset-interface-sub-port-queue-statistics {
    description
      "To clear interface sub port queue statistics.";
    ext:node-ref "/qos:qos/qos:global-query/qos:interface-sub-port-queue-statistics";
    input {
      leaf interface-name {
        type leafref {
          path "/ifm:ifm/ifm:interfaces/ifm:interface/ifm:name";
        }
        mandatory true;
        description
          "Interface name.";
      }
    }
  }//reset-interface-sub-port-queue-statistics
  rpc reset-fabric-queue-unicast-statistics {
    description
      "To clear statistics for unicast fabric queue.";
    ext:node-ref "/qos:qos/qos:global-query/qos:fabric-queue-unicast-statisticss";
    input {
      leaf source-slot-id {
        type string {
          length "1..32";
          pattern '(c[cl]c\d+/)?\d+';
        }
        mandatory true;
        description
          "Source slot ID.";
      }
      leaf destination-slot-id {
        type string {
          length "1..32";
          pattern '(c[cl]c\d+/)?\d+';
        }
        description
          "Destination slot ID.";
      }
    }
  }//reset-fabric-queue-unicast-statistics
  rpc reset-fabric-queue-multicast-statistics {
    description
      "To clear statistics for multicast fabric queue.";
    ext:node-ref "/qos:qos/qos:global-query/qos:fabric-queue-multicast-statisticss";
    input {
      leaf slot-id {
        type slot-id;
        mandatory true;
        description
          "Slot ID.";
      }
    }
  }//reset-fabric-queue-multicast-statistics
  rpc reset-flow-car-tables{
    description
      "To clear flow CAR tables.";
    input {
      leaf slot-id {
        type slot-id;
        description
          "Slot id.";
      }
      leaf ip-type {
        type stream-direction-type;
        description
          "Type of an IP address.";
      }
      leaf ip {
        type inet:ipv4-address-no-zone;
        description
          "IP.";
      }
    }
  }//rpc reset-flow-car-tables
  rpc reset-flow-car-statisticss{
    description
      "To clear flow CAR statisticss.";
    ext:node-ref "/qos:qos/qos:global-query/qos:flow-car-statisticss";
    input {
      leaf slot-id {
        type slot-id;
        mandatory true;
        description
          "Slot id.";
      }
      leaf direction {
        type qos-direction-type;
        mandatory true;
        description
          "Direction.";
      }
      leaf ip-type {
        type stream-direction-type;
        mandatory true;
        description
          "Type of an IP address.";
      }
      leaf ip {
        type inet:ipv4-address-no-zone;
        description
          "IP.";
      }
    }
  }//rpc reset-flow-car-statisticss
  rpc reset-interface-ecn-statistics {
    description
      "The reset qos ecn statistics command clears statistics on packets with the ECN flag on an interface.";
    input {
      leaf interface-name {
        type string {
          length "1..63";
        }
        description
          "Interface name.";
      }
    }
  }//reset-interface-ecn-statistics
  rpc reset-interface-buffer-usage-statistics {
    description
      "The reset qos buffer-usage command clears statistics about the device buffer usage.";
    input {
      leaf interface-name {
        type string {
          length "1..49";
        }
        description
          "Interface name.";
      }
      leaf slot-id {
        type string {
          length "1..31";
          pattern '(c[cl]c\d+/)?\d+';
        }
        description
          "Slot ID.";
      }
    }
  }//reset-interface-buffer-usage-statistics
  augment "/ifm:ifm/ifm:interfaces/ifm:interface" {
    description
      "Adds qos configuration to ifm interface model.";
    container qos {
      must "/ifm:ifm/ifm:interfaces/ifm:interface/ifm:name!='NULL0'";
      description
        "Configure QoS apply.";
      container trusts {
        description
          "List of configure trust ip-dscp or 8021p.";
        list trust {
          must "./vlan-mode='false' or (./vlan-mode='true' and not(../../../ifm:l2-mode-enable='true'))";
          must "./vlan-mode='false' or (./vlan-mode='true' and ../../../ethernet:ethernet/ethernet:main-interface/ethernet:l2-attribute) or ../../../ifm:class='sub-interface'";
          must "direction='in-outbound' and not(../trust[type=current()/type][direction='inbound']) and not(../trust[type=current()/type][direction='outbound']) or (direction!='in-outbound' and not(../trust[type=current()/type][direction='in-outbound']))";
          key "type direction vlan-mode begin-vlan end-vlan";
          description
            "Configure trust ip-dscp or 8021p.";
          leaf type {
            type trust-type;
            description
              "Trust ip-dscp or 8021p.";
          }
          leaf direction {
            type trust-direction-type;
            description
              "Direction.";
          }
          leaf vlan-mode {
            type boolean;
            description
              "Enable/disable VLAN mode.";
          }
          leaf begin-vlan {
            type uint32 {
              range "0..4094";
            }
            description
              "Begin VLAN id.";
          }
          leaf end-vlan {
            type uint32 {
              range "0..4094";
            }
            description
              "End VLAN id.";
          }
          leaf diffserv-domain-name {
            when "../type='ip-dscp'";
            type leafref {
              path "/qos:qos/qos:classifier-template/qos:diffserv-domains/qos:diffserv-domain/qos:name";
            }
            mandatory true;
            description
              "Name of a diffserv domain.";
          }
          leaf vpn-mode {
            type boolean;
            default "false";
            description
              "Enable/disable VPN mode.";
          }
        }
      }
      container traffic-policy-applys {
        description
          "List of configure traffic policy application.";
        list traffic-policy-apply {
          must "../../../ifm:l2-mode-enable='false' and ./identifier='no' or ../../../ifm:l2-mode-enable='true'";
          must "./vlan-mode='false' or (./vlan-mode='true' and not(../../../ifm:l2-mode-enable='true'))";
          must "./vlan-mode='false' or (./vlan-mode='true' and ../../../ethernet:ethernet/ethernet:main-interface/ethernet:l2-attribute) or ../../../ifm:class='sub-interface'";
          key "policy-name direction layer vlan-mode pe-vlan-id";
          description
            "Configure traffic policy application.";
          leaf policy-name {
            type leafref {
              path "/qos:qos/qos:classifier-template/qos:traffic-policys/qos:traffic-policy/qos:name";
            }
            must "not(../identifier!='no' and ../identifier!='none' and ../../../../ifm:l2-mode-enable='true' and /qos:qos/qos:classifier-template/qos:traffic-policys/qos:traffic-policy[qos:name=current()]/qos:share-mode='enable')";
            description
              "Policy name.";
          }
          leaf direction {
            type qos-direction-type;
            description
              "Direction.";
          }
          leaf layer {
            type policy-apply-layer-type;
            description
              "Classification based on Layer 2 or Layer 3 information.
              If this field is unnecessary, the controller can set a default value 0xffffffff.";
          }
          leaf vlan-mode {
            type boolean;
            description
              "Enable/disable VLAN mode.";
          }
          leaf pe-vlan-id {
            type uint32 {
              range "0..4094";
            }
            must "(../vlan-mode='false' and ../pe-vlan-id=0) or ../vlan-mode='true'";
            description
              "Pe VLAN id.";
          }
          leaf vlan-id {
            when "../vlan-mode='true'";
            type pub-type:vlan-range {
              pattern '((409[0-4]|40[0-8][0-9]|[1-3][0-9]{3}|[1-9][0-9]{1,2}|[1-9])+(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)';
            }
            mandatory true;
            description
              "VLAN id.";
          }
          leaf identifier {
            type identifier-type;
            default "no";
            description
              "Identifier. The range supported by this node varies according to the interface type. This node does not support modification or deletion.";
          }
        }
      }
      container traffic-policy-multi-applys {
        must "count(traffic-policy-multi-apply[direction='inbound'])<=16";
        must "count(traffic-policy-multi-apply[direction='outbound'])<=16";
        description
          "List of configure traffic multi policy application.";
        list traffic-policy-multi-apply {
          must "not(../../traffic-policy-applys/traffic-policy-apply[direction=current()/direction])";
          key "policy-name direction";
          unique "direction match-precedence";
          max-elements "32";
          description
            "Configure traffic policy multi application.";
          leaf policy-name {
            type leafref {
              path "/qos:qos/qos:classifier-template/qos:traffic-policys/qos:traffic-policy/qos:name";
            }
            must "/qos:qos/qos:classifier-template/qos:traffic-policys/qos:traffic-policy[name=current()]/qos:ipv6-fragment-inner-protocol-switch/qos:enable='false'";
            description
              "Policy name.";
          }
          leaf direction {
            type qos-direction-type;
            description
              "Direction.";
          }
          leaf match-precedence {
            type uint16 {
              range "1..1024";
            }
            mandatory true;
            description
              "Specify the precedence of traffic policy.";
          }
        }
      }
      container traffic-policys {
        description
          "List of configure traffic policy application.";
        list traffic-policy {
          key "policy-name direction";
          description
            "Configure traffic policy application.";
          leaf policy-name {
            type leafref {
              path "/qos:qos/qos:classifier-template/qos:traffic-policys/qos:traffic-policy/qos:name";
            }
            description
              "Policy name.";
          }
          leaf direction {
            type trust-direction-type;
            description
              "Direction.";
          }
          leaf priority {
            type policy-apply-order;
            description
              "Three policy can applied on interface.";
          }
        }
      }
      container profile-applys {
        description
          "List of configure QoS profile application.";
        list profile-apply {
          must "./ce-begin-vlan-id <= ./ce-end-vlan-id";
          must "(./type='interface' and ./pe-vlan-id=0 and ./ce-begin-vlan-id=0 and ./ce-end-vlan-id=0) or (./type='vlan' and ./pe-vlan-id=0 and ./ce-begin-vlan-id!=0) or (./type='pe' and ./pe-vlan-id!=0 and ./ce-begin-vlan-id!=0)";
          must "../../../ifm:type!='Virtual-Ethernet' or ../../../ifm:class='sub-interface'";
          must "../../../ifm:type!='Global-VE' or ../../../ifm:class='sub-interface'";
          key "profile-name direction type pe-vlan-id ce-begin-vlan-id ce-end-vlan-id identify-type";
          description
            "Configure QoS profile application.";
          leaf profile-name {
            type leafref {
              path "/qos:qos/qos:queue-scheduler-template/qos:profiles/qos:profile/qos:name";
            }
            description
              "Qos profile name.";
          }
          leaf direction {
            type qos-direction-type;
            description
              "Direction.";
          }
          leaf type {
            type profile-apply-type;
            description
              "Profile apply type.";
          }
          leaf pe-vlan-id {
            type uint32 {
              range "0..4094";
            }
            description
              "Pe VLAN id.";
          }
          leaf ce-begin-vlan-id {
            type uint32 {
              range "0..4094";
            }
            description
              "Ce begin VLAN id.";
          }
          leaf ce-end-vlan-id {
            type uint32 {
              range "0..4094";
            }
            description
              "Ce end VLAN id.";
          }
          leaf identify-type {
            type identify-type;
            description
              "Identify type. The range supported by this node varies according to the interface type.";
          }
          leaf linkage-bandwidth {
            type linkage-bandwidth-type;
            must "../linkage-bandwidth='disable' or not(../../../../ifm:type='Virtual-Ethernet' or ../../../../ifm:type='Global-VE') or (../../../../ifm:bandwidth or ../../../../ifm:bandwidth-kbps)";
            default "disable";
            description
              "Linkage bandwidth.";
          }
          leaf group-name {
            when "../linkage-bandwidth='disable'";
            type template-name;
            description
              "The name of user queue group.";
          }
        }
      }
      container user-queue-applys {
        description
          "List of configure user queue application.";
        list user-queue-apply {
          key "direction";
          description
            "Configure user queue application.";
          leaf direction {
            type qos-direction-type;
            description
              "Direction.";
          }
          leaf cir {
            type uint32{
                range "0 | 16..4294967294";
            }
            units "kbit/s";
            mandatory true;
            description
            "Committed information rate.";
          }
          leaf pir {
            type uint32{
                range "0 | 16..4294967294";
            }
            units "kbit/s";
            must "../pir>=../cir";
            mandatory true;
            description
              "Peak information rate.";
          }
          leaf flow-queue-name {
            type leafref {
              path "/qos:qos/qos:queue-scheduler-template/qos:flow-queues/qos:flow-queue/qos:name";
            }
            must "/qos:qos/qos:queue-scheduler-template/qos:flow-queues/qos:flow-queue[qos:name=current()]/qos:mode='normal'";
            description
              "Flow queue.";
          }
          leaf flow-mapping-name {
            type leafref {
              path "/qos:qos/qos:queue-scheduler-template/qos:flow-mappings/qos:flow-mapping/qos:name";
            }
            description
              "Flow Mapping.";
          }
          leaf user-group-queue-name {
            type leafref {
              path "/qos:qos/qos:queue-scheduler-template/qos:user-group-queues/qos:user-group-queue/qos:name";
            }
            must "/qos:qos/qos:queue-scheduler-template/qos:user-group-queues/qos:user-group-queue[qos:name=current()]/qos:mode='normal'";
            description
              "Group Queue.";
          }
          leaf service-template-name {
            type leafref {
              path "/qos:qos/qos:queue-scheduler-template/qos:service-templates/qos:service-template/qos:name";
          }
            description
              "Service Template.";
          }
          leaf adjust-on-card {
            type adjust-on-card-type;
            must "(../service-template-name and ../adjust-on-card='enable') or ../adjust-on-card='disable'";
            default "disable";
            description
              "Adjust on card flag.";
          }
          container user-queue-applys-stats {
            config false;
            description
              "List of statistics of interface user queue.";
            list user-queue-applys-stat {
              key "service-class";
              description
              "Statistics of interface user queue.";
              leaf service-class {
                type hqos-service-class;
                description
                  "Class of service.";
              }
              leaf pass-packets {
                type uint64;
                units "packet";
                description
                  "Number of passed packets.";
              }
              leaf pass-bytes {
                type uint64;
                units "Byte";
                description
                  "Number of passed bytes.";
              }
              leaf pass-packet-rate {
                type uint64;
                units "pps";
                description
                  "Rate of the packets passed during the latest 30 seconds.";
              }
              leaf pass-byte-rate {
                type uint64;
                units "Byte/s";
                description
                  "Rate of the bytes passed during the latest 30 seconds.";
              }
              leaf drop-packets {
                type uint64;
                units "packet";
                description
                  "Number of dropped packets.";
              }
              leaf drop-bytes {
                type uint64;
                units "Byte";
                description
                  "Number of dropped bytes.";
              }
              leaf drop-packet-rate {
                type uint64;
                units "pps";
                description
                  "Rate of the packets dropped during the latest 30 seconds.";
              }
              leaf drop-byte-rate {
                type uint64;
                units "Byte/s";
                description
                  "Rate of the bytes dropped during the latest 30 seconds.";
              }
            }
          }
        }
      }
      container port-queues {
        description
          "List of configure port queue.";
        list port-queue {
          key "service-class";
          max-elements  "8";
          description
            "Configure port queue.";
          leaf service-class {
            type qos-service-class;
            description
              "Class of service.";
          }
          leaf port-wred-name {
            type leafref {
              path "/qos:qos/qos:wred-template/qos:port-wreds/qos:port-wred/qos:name";
            }
            description
              "Port wred name.";
          }
          choice config-type {
            mandatory true;
            description
              "Specify config type.";
            case shaping-mode {
              description
                "Specify config type choice case as shaping mode.";
              leaf queue-schedule-mode {
                type queue-schedule-mode;
                mandatory true;
                description
                  "Schedule Mode.";
              }
              leaf weight {
                when "../queue-schedule-mode='wfq'";
                type uint8 {
                  range "1..100";
                }
                mandatory true;
                description
                  "Weight of wfq scheduling strategy.";
              }
              leaf pbs {
                when "../shaping-value or ../shaping-percentage";
                type uint32 {
                  range "1..10000000";
                }
                units "Byte";
                description
                  "Peak burst size.";
              }
              leaf low-latency {
                when "../queue-schedule-mode='pq'";
                type queue-low-latency;
                description
                  "Low latency. Some boards do not support this object.";
              }
              choice shaping-parameters {
                description
                  "Specify shaping parameters.";
                case shaping {
                  description
                    "Specify shaping parameters choice case as shaping value.";
                  leaf shaping-value {
                    type uint32 {
                      range "0..4294967294";
                    }
                    units "Mbit/s";
                    description
                      "Shaping value.";
                  }
                }
                case shaping-percent {
                  description
                    "Specify shaping parameters choice case as shaping percentage value.";
                  leaf shaping-percentage {
                    type uint8 {
                      range "0..100";
                    }
                    units "%";
                    description
                      "Shaping percentage.";
                  }
                }
              }
            }
            case cir-mode {
              description
                "Specify config type choice case as cir mode. Some boards do not support this object.";
              leaf cir-schedule-mode {
                type queue-cir-schedule-mode;
                mandatory true;
                description
                  "Scheduling strategy of cir.";
              }
              leaf pir-schedule-mode {
                type queue-schedule-mode;
                mandatory true;
                description
                  "Scheduling strategy of pir.";
              }
              leaf pir-weight {
                when "../pir-schedule-mode='wfq'";
                type uint8 {
                  range "1..100";
                }
                mandatory true;
                description
                  "Weight of wfq scheduling strategy.";
              }
              leaf cbs {
                type uint32 {
                  range "1..10000000";
                }
                units "Byte";
                must "../pir-pbs>=../cbs or not(../pir-pbs)";
                description
                  "Committed burst size.";
              }
              leaf pir-pbs {
                type uint32 {
                  range "1..10000000";
                }
                units "Byte";
                must "../pir-pbs>=../cbs or not(../cbs)";
                description
                  "Peak burst size.";
              }
             choice cir-parameters {
               mandatory true;
               description
                 "Specify cir parameters.";
               case cir {
                 description
                   "Specify cir parameters choice case as cir value.";
                 leaf cir-value {
                   type uint32 {
                     range "0..4294967294";
                   }
                   units "Mbit/s";
                   must "../pir-value>=../cir-value";
                   mandatory true;
                   description
                     "Specify cir value.";
                 }
                 leaf pir-value {
                   type uint32 {
                     range "0..4294967294";
                   }
                   units "Mbit/s";
                   must "../pir-value>=../cir-value";
                   mandatory true;
                   description
                     "Peak information rate.";
                   }
                }
                case cir-percent {
                  description
                    "Specify cir parameters choice case as cir percentage value.";
                  leaf cir-percentage {
                    type uint8 {
                      range "0..100";
                    }
                    units "%";
                    must "../pir-percentage>=../cir-percentage";
                    mandatory true;
                    description
                      "Cir percentage.";
                  }
                  leaf pir-percentage {
                    type uint8 {
                      range "0..100";
                    }
                    units "%";
                    must "../pir-percentage>=../cir-percentage";
                    mandatory true;
                    description
                      "Pir percentage.";
                  }
                }
              }
            }
          }
        }
      }
      container port-queue-states {
        config false;
        description
          "List of statistics of port queue.";
        list port-queue-state {
          key "service-class";
          description
            "Statistics of port queue.";
          leaf service-class {
            type qos-service-class;
            description
              "Class of service.";
          }
          leaf port-wred-name {
            type leafref {
              path "/qos:qos/qos:wred-template/qos:port-wreds/qos:port-wred/qos:name";
            }
            description
              "Port wred name.";
          }
          choice config-type {
            description
              "Specify config type.";
            case shaping-mode {
              description
                "Specify config type choice case as shaping mode.";
              leaf queue-schedule-mode {
                type queue-schedule-mode;
                description
                  "Schedule Mode.";
              }
              leaf weight {
                when "../queue-schedule-mode='wfq'";
                type uint8 {
                  range "1..100";
                }
                description
                  "Weight of wfq scheduling strategy.";
              }
              leaf pbs {
                when "../shaping-value or ../shaping-percentage";
                type uint32 {
                  range "1..10000000";
                }
                units "Byte";
                description
                  "Peak burst size.";
              }
              leaf low-latency {
                when "../queue-schedule-mode='pq'";
                type queue-low-latency;
                description
                  "Low latency. Some boards do not support this object.";
              }
              choice shaping-parameters {
                description
                  "Specify shaping parameters.";
                case shaping {
                  description
                    "Specify shaping parameters choice case as shaping value.";
                  leaf shaping-value {
                    type uint32 {
                      range "0..4294967294";
                    }
                    units "Mbit/s";
                    description
                      "Shaping value.";
                  }
                }
                case shaping-percent {
                  description
                    "Specify shaping parameters choice case as shaping percentage value.";
                  leaf shaping-percentage {
                    type uint8 {
                      range "0..100";
                    }
                    units "%";
                    description
                      "Shaping percentage.";
                  }
                }
              }
            }
            case cir-mode {
              description
                "Specify config type choice case as cir mode. Some boards do not support this object.";
              leaf cir-schedule-mode {
                type queue-cir-schedule-mode;
                description
                  "Scheduling strategy of cir.";
              }
              leaf pir-schedule-mode {
                type queue-schedule-mode;
                description
                  "Scheduling strategy of pir.";
              }
              leaf pir-weight {
                when "../pir-schedule-mode='wfq'";
                type uint8 {
                  range "1..100";
                }
                description
                  "Weight of wfq scheduling strategy.";
              }
              leaf cbs {
                type uint32 {
                  range "1..10000000";
                }
                units "Byte";
                description
                  "Committed burst size.";
              }
              leaf pir-pbs {
                type uint32 {
                  range "1..10000000";
                }
                units "Byte";
                description
                  "Peak burst size.";
              }
             choice cir-parameters {
               description
                 "Specify cir parameters.";
               case cir {
                 description
                   "Specify cir parameters choice case as cir value.";
                 leaf cir-value {
                   type uint32 {
                     range "0..4294967294";
                   }
                   units "Mbit/s";
                   description
                     "Specify cir value.";
                 }
                 leaf pir-value {
                   type uint32 {
                     range "0..4294967294";
                   }
                   units "Mbit/s";
                   description
                     "Peak information rate.";
                   }
                }
                case cir-percent {
                  description
                    "Specify cir parameters choice case as cir percentage value.";
                  leaf cir-percentage {
                    type uint8 {
                      range "0..100";
                    }
                    units "%";
                    description
                      "Cir percentage.";
                  }
                  leaf pir-percentage {
                    type uint8 {
                      range "0..100";
                    }
                    units "%";
                    description
                      "Pir percentage.";
                  }
                }
              }
            }
          }
        }
      }
      container port-queue-template-applys {
        description
          "List of configure port queue template applications.";
        list port-queue-template-apply {
          key "port-queue-template-name";
          max-elements "1";
          description
            "Configure port queue template applications.";
          leaf port-queue-template-name {
            type leafref {
              path "/qos:qos/qos:queue-scheduler-template/qos:port-queue-templates/qos:port-queue-template/qos:name";
            }
            description
              "Port queue template name.";
          }
        }
      }
      container port-queue-alarms {
        description "List of configure port queue alarm.";
        list port-queue-alarm {
          key "service-class";
          max-elements  "8";
          description
            "Configure port queue alarm.";
          ext:generated-by system {
            when "../../../ifm:class='main-interface' and (../../../ifm:type='Ethernet' or ../../../ifm:type='GigabitEthernet' or ../../../ifm:type='Eth-Trunk' or 
../../../ifm:type='Ip-Trunk' or ../../../ifm:type='Pos' or ../../../ifm:type='100GE' or ../../../ifm:type='200GE' or ../../../ifm:type='40GE' or ../../../ifm:type='10GE' or 
../../../ifm:type='4x10GE' or ../../../ifm:type='10x10GE' or ../../../ifm:type='3x40GE' or ../../../ifm:type='4x25GE' or ../../../ifm:type='25GE' or 
../../../ifm:type='XGigabitEthernet' or ../../../ifm:type='FlexE' or ../../../ifm:type='FlexE-200GE' or ../../../ifm:type='50|100GE' or ../../../ifm:type='50GE' or 
../../../ifm:type='FlexE-50G' or ../../../ifm:type='FlexE-100G' or ../../../ifm:type='FlexE-50|100G' or ../../../ifm:type='400GE' or ../../../ifm:type='FlexE-400G' or ../../../ifm:type='FlexE-10G')";
            description "The configuration is generated automatically.";
            ext:filter "service-class = 'cs6' or service-class = 'cs7'";
          }
          leaf service-class {
            type qos-service-class;
            description
              "Class of service.";
          }
          leaf buffer-percentage {
            type uint32 {
              range "0..100";
            }
            mandatory true;
            description
              "Buffer percentage.";
          }
        }
      }
      container port-queue-alarm-states {
        config false;
        description "List of operational state of port queue alarm.";
        list port-queue-alarm-state {
          key "service-class";
          max-elements  "8";
          description
            "Operational state of port queue alarm. This node has two default configurations, corresponding to service classes of CS6 and CS7, respectively.";
          leaf service-class {
            type qos-service-class;
            description
              "Class of service.";
          }
          leaf buffer-percentage {
            type uint32 {
              range "0..100";
            }
            description
              "Buffer percentage.";
          }
        }
      }
      container port-queue-discard-alarms {
        description "List of configure port queue discard alarm.";
        list port-queue-discard-alarm {
          key "service-class";
          max-elements "8";
          description
            "Configure port queue discard alarm.";
          leaf service-class {
            type qos-service-class;
            description
              "Class of service.";
          }
          leaf type {
            type discard-type;
            mandatory true;
            description
              "Discard type.";
          }
          leaf discard-number {
            when "../type='discard-packet' or ../type='discard-byte'";
            type uint32 {
              range "1..4294967295";
            }
            mandatory true;
            description
              "Discard number. The units is 'packet' when the type is discard-packet. Then units is 'Byte' when the type is discard-byte.";
          }
          leaf discard-packet-coefficient {
            when "../type='discard-packet-ratio'";
            type uint8 {
              range "1..9";
            }
            mandatory true;
            description
              "Ratio coefficient of the discard packets.";
          }
          leaf discard-packet-exponent {
            when "../type='discard-packet-ratio'";
            type uint8 {
              range "1..5";
            }
            mandatory true;
            description
              "Ratio exponent of the discard packets.";
          }
          leaf interval-time {
            type uint16 {
              range "15..3600";
            }
            units "s";
            default "30";
            description
              "Monitoring time of the port queue discard alarm.";
          }
          leaf repeat-count {
            type uint32 {
              range "2..10";
            }
            description
              "Repeat count of alarm threshold reached.";
          }
        }
      }
      container set-queue-stats {
        description
          "List of configure queue statisticss interval.";
        list set-queue-stat {
          key "interval";
          max-elements "1";
          description
            "Configure queue statisticss interval.";
          leaf interval {
            type interval-value;
            description
              "Specify the value of interval (Unit: s).";
          }
        }
      }
      container link-adjustment {
        description
          "Configure link adjustment. Some interfaces do not support this object.";
        leaf adjust-value {
          type int32 {
            range "-64..-1 | 1..64";
          }
          units "Byte";
          must "not(../../../ethernet:ethernet/ethernet:main-interface/ethernet:l2-attribute)";
          description
            "Adjust value.";
        }
        leaf shaping-mode {
          type link-adjustment-type;
          must "not(../../../ethernet:ethernet/ethernet:main-interface/ethernet:l2-attribute)";
          description
            "Shaping mode. If users access the network through PPPoA, the remote link type must be set to cell; if users access the network through PPPoE, the remote link type does not need to be set to cell.";
        }
      }
      container qos-queues {
        description
          "List of configure QoS Queue.";
        list qos-queue {
          key "service-class";
          max-elements  "8";
          description
            "Configure QoS Queue.";
          ext:generated-by system {
            description "The instances are created and deleted following the interface.";
          }
          ext:operation-exclude create {
            description "The instances cannot be created.";
          }
          leaf service-class {
            type qos-service-class;
            description
              "Class of service.";
          }
          choice cir-parameters {
            mandatory true;
            description
               "Specify cir-parameters.";
            case cir {
              description
                "Specify cir parameters choice case as cir value.";
              leaf cir {
                type uint32 {
                  range "0..4294967294";
                }
                units "Mbit/s";
                description
                  "Committed information rate.";
              }
            }
            case cir-percent {
              description
                "Specify cir parameters choice case as cir percentage value.";
              leaf cir-percent {
                type uint8 {
                  range "0..100";
                }
                units "%";
                description
                  "CIR percentage.";
              }
            }
          }
          choice pir-parameters {
            mandatory true;
            description
               "Specify pir-parameters.";
            case pir {
              description
                "Specify pir parameters choice case as pir value.";
              leaf pir {
                type uint32 {
                  range "1..4294967294";
                }
                units "Mbit/s";
                must "../pir>=../cir";
                description
                  "Peak information rate.";
              }
            }
            case pir-percent {
              description
                "Specify pir parameters choice case as pir percent value.";
              leaf pir-percent {
                type uint8 {
                  range "0..100";
                }
                units "%";
                must "../pir-percent>=../cir-percent";
                description
                  "PIR percentage.";
              }
            }
          }
          leaf priority {
            type queue-schedule-mode;
            mandatory true;
            description
              "Priority.";
          }
        }
      }
      container queue-template-applys {
        description
          "List of configure queue template applications.";
        list queue-template-apply {
          key "queue-template-name";
          max-elements "1";
          description
            "Configure queue template applications.";
          leaf queue-template-name {
            type leafref {
              path "/qos:qos/qos:queue-scheduler-template/qos:qos-queue-templates/qos:qos-queue-template/qos:name";
            }
            description
              "Queue template name.";
          }
        }    
      }
      container soft-pipe-alarms {
        description
          "Configure softpipe bandwidth usage alarm. The soft-pipe alarm will not come into effect without hard-pipe configuration on the interface. Some interface do not support this object.";
        container soft-pipe-alarm {
          must "./bandwidth-usage-threshold>=./resume-threshold";
          presence "create soft-pipe-alarm";
          description
            "Enable/disable softpipe bandwidth usage alarm.";
          leaf bandwidth-usage-threshold {
            type uint8 {
              range "1..100";
            }
            mandatory true;
            description
             "The alarm threshold of soft-pipe bandwidth usage.";
          }
          leaf resume-threshold {
            type uint8 {
              range "1..100";
            }
            mandatory true;
            description
              "The resume threshold of soft-pipe bandwidth usage.";
          }
        }
      }
      container flow-queue-template-applys {
        description
          "List of configure flow queue template applications. This node can only be configured on the sliced sub-interface.";
        list flow-queue-template-apply {
          key "flow-queue-template-name";
          max-elements "1";
          description
            "Configure flow queue template applications.";
          leaf flow-queue-template-name {
            type leafref {
              path "/qos:qos/qos:queue-scheduler-template/qos:flow-queues/qos:flow-queue/qos:name";
            }
            must "/qos:qos/qos:queue-scheduler-template/qos:flow-queues/qos:flow-queue[qos:name=current()]/qos:mode='normal' or /qos:qos/qos:queue-scheduler-template/qos:flow-queues/qos:flow-queue[qos:name=current()]/qos:mode='8cos-enhance'";
            description
              "Flow queue template name.";
          }
        }
      }
      container mode-channel-bandwidth-maximize {
        when "../../ifm:type='Eth-Trunk'";
        description
          "Configure mode channel bandwidth maximize.";
        leaf enable-maximize {
          type enable-type;
          description
            "Bandwidth maximize.";
        }
      }
      container service-template-applys {
        description
          "List of configure service template applications.";
        list service-template-apply {
          key "service-template-name";
          max-elements "1";
          description
            "Configure service template applications.";
          leaf service-template-name {
            type leafref {
              path "/qos:qos/qos:queue-scheduler-template/qos:service-templates/qos:service-template/qos:name";
            }
            description
              "Service template name.";
          }
        }
      }
      container default-service-classs {
        description
          "List of configure default service class.";
        list default-service-class {
          key "service-class";
          max-elements "1";
          description
            "Configure default service class.";
          leaf service-class {
            type qos-service-class;
            description
              "Service class.";
          }
        }
      }
      container default-user-group-queues {
        when "../../ifm:class='main-interface' and (../../ifm:type='Ethernet' or ../../ifm:type='GigabitEthernet' or ../../ifm:type='Eth-Trunk' or " +
"../../ifm:type='100GE' or ../../ifm:type='200GE' or ../../ifm:type='40GE' or ../../ifm:type='10GE' or  ../../ifm:type='4x10GE' or " +
"../../ifm:type='10x10GE' or ../../ifm:type='3x40GE' or ../../ifm:type='4x25GE' or ../../ifm:type='25GE' or ../../ifm:type='XGigabitEthernet' or " +
"../../ifm:type='50|100GE' or ../../ifm:type='50GE' or ../../ifm:type='400GE')";
        description
          "List of configure default user group queue.";
        list default-user-group-queue {
          must "shaping or cir or weight";
          key "direction";
          description
            "Configure default user group queue.";
          leaf direction {
            type out-direction-type;
            description
              "Direction.";
          }
          leaf weight {
            type uint8 {
              range "1..63";
            }
            description
              "Weight.";
          }
          choice config-type {
            description
              "Specify user-group-queue config type.";
            case shaping-mode {
              description
                "Specify config type choice case as shaping mode.";
              leaf shaping {
                type uint32 {
                  range "66..4294967294";
                }
                units "kbit/s";
                mandatory true;
                description
                  "Rate of shaping.";
              }
              leaf pbs {
                type uint32 {
                  range "64..2097152";
                }
                units "Byte";
                description
                  "Peak burst size.";
              }
            }
            case cir-mode {
              description
                "Specify config type choice case as cir mode.";
              leaf cir {
                type uint32 {
                  range "66..4294967294";
                }
                units "kbit/s";
                mandatory true;
                description
                  "Committed information rate.";
              }
              leaf cbs {
                type uint32 {
                  range "64..2097152";
                }
                units "Byte";
                description
                  "Committed burst size.";
              }
              leaf pir {
                type uint32 {
                  range "66..4294967294";
                }
                units "kbit/s";
                must "../pir>=../cir";
                description
                  "Peak information rate.";
                ext:dynamic-default {
                  ext:default-value "../cir" {
                    description "The default value of pir is cir.";
                  }
                }
              }
              leaf pir-pbs {
                type uint32 {
                  range "64..2097152";
                }
                units "Byte";
                description
                  "Peak burst size.";
              }
            }
          }
        }
      }
      container default-sub-port-queues {
        when "../../ifm:class='main-interface' and (../../ifm:type='Ethernet' or ../../ifm:type='GigabitEthernet' or ../../ifm:type='Eth-Trunk' or " +
"../../ifm:type='100GE' or ../../ifm:type='200GE' or ../../ifm:type='40GE' or ../../ifm:type='10GE' or  ../../ifm:type='4x10GE' or " +
"../../ifm:type='10x10GE' or ../../ifm:type='3x40GE' or ../../ifm:type='4x25GE' or ../../ifm:type='25GE' or ../../ifm:type='XGigabitEthernet' or " +
"../../ifm:type='50|100GE' or ../../ifm:type='50GE' or ../../ifm:type='400GE')";
        description
          "List of configure default sub port queue.";
        list default-sub-port-queue {
          key "direction";
          description
            "Configure default sub port queue.";
          leaf direction {
            type out-direction-type;
            description
              "Direction.";
          }
          leaf shaping {
            type uint32 {
              range "66..4294967294";
            }
            units "kbit/s";
            mandatory true;
            description
              "Rate of shaping.";
          }
          leaf pbs {
            type uint32 {
              range "64..2097152";
            }
            units "Byte";
            description
              "Peak burst size.";
          }
        }
      }
      container port-shapings {
        description
          "Configure port shaping.";
        container port-shaping {
          presence "Create port-shaping.";
          description
            "Enable/disable port shaping.";
          leaf pbs {
            type uint32 {
              range "1..2147483646";
            }
            units "Byte";
            description
              "Peak burst size.";
          }
          leaf network-header-length {
            type int32 {
              range "-63..63";
            }
            description
              "Length value of network header.";
          }
          leaf weight-mode {
            when "../../../../ifm:type='Eth-Trunk'";
            type port-shaping-weight-mode-type;
            description
              "Scale scheduler parameters on aggregate interface weight.";
          }
          choice shaping-parameters {
            mandatory true;
            description
              "Specify shaping parameters.";
            case shaping-type {
              description
                "Specify shaping parameters choice case as shaping type.";
              leaf shaping-type {
                type shaping-value-type;
                description
                  "Shaping value type.";
              }
            }
            case shaping-value {
              description
                "Specify shaping parameters choice case as shaping value.";
              leaf shaping-value {
                type uint32 {
                  range "1..4294967294";
                }
                units "Mbit/s";
                description
                  "Shaping value.";
              }
            }
            case shaping-percent {
              description
                "Specify shaping parameters choice case as shaping percentage value.";
              leaf shaping-percentage {
                type uint8 {
                  range "1..100";
                }
                units "%";
                description
                  "Shaping percentage.";
              }
            }
          }
        }
      }
      container per-hop-behavior-disables {
        description
          "List of configure disable outbound priority mappings. If VLAN mode is set to false, map-type cannot be set to none and inner-8021p, outer-8021p, dscp, or MPLS-EXP for the same interface at the same time. If VLAN mode is set to true, map-type cannot be set to none and inner-8021p, outer-8021p, dscp, or MPLS-EXP for the same interface and VLAN at the same time.";
        list per-hop-behavior-disable {
          must "./vlan-mode='false' or (./vlan-mode='true' and ../../../ethernet:ethernet/ethernet:main-interface/ethernet:l2-attribute)";
          key "map-type vlan-mode";
          description
            "Configure disable outbound priority mappings.";
          leaf map-type {
            type map-type;
            description
              "Select map type.";
          }
          leaf vlan-mode {
            type boolean;
            description
              "Enable/disable VLAN mode.";
          }
          leaf vlan-id {
            when "../vlan-mode='true'";
            type pub-type:vlan-range {
              pattern '((409[0-4]|40[0-8][0-9]|[1-3][0-9]{3}|[1-9][0-9]{1,2}|[1-9])+(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)';
            }
            mandatory true;
            description
              "VLAN id.";
          }
        }
      }
      container per-hop-behavior-enables {
        description
          "Configure outbound priority mappings.";
        container per-hop-behavior-enable {
          presence "create per-hop-behavior-enable";
          description
            "Enable/disable outbound priority mappings.";
          leaf diffserv-domain-name {
            type leafref {
              path "/qos:qos/qos:classifier-template/qos:diffserv-domains/qos:diffserv-domain/qos:name";
            }
            mandatory true;
            description
              "Name of a diffserv domain.";
          }
        }
      }
      container per-hop-behavior-enable-vlans {
        description
          "List of configure outbound priority mappings with VLAN. The diffserv-domain-name cannot be set to different values for the same interface and VLAN at the same time.";
        list per-hop-behavior-enable-vlan {
          key "diffserv-domain-name";
          description
            "Configure outbound priority mappings with VLAN.";
          leaf diffserv-domain-name {
            type leafref {
              path "/qos:qos/qos:classifier-template/qos:diffserv-domains/qos:diffserv-domain/qos:name";
            }
            description
              "Name of a diffserv domain.";
          }
          leaf vlan-id {
            type pub-type:vlan-range {
              pattern '((409[0-4]|40[0-8][0-9]|[1-3][0-9]{3}|[1-9][0-9]{1,2}|[1-9])+(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)';
            }
            mandatory true;
            description
              "VLAN id.";
          }
        }
      }
      container per-hop-behavior {
        description
          "Configure outbound priority mappings.";
        leaf enable {
          type switch-type;
          description
            "Enable outbound priority mappings.";
        }
      }
      container cars {
        description
          "List of configure interface applying car.";
        list car {
          must "(./cir-value and ./cbs) or not(./cir-value)";
          key "direction vlan-mode begin-vlan end-vlan";
          description
            "Configure interface applying car.";
          leaf direction {
            type qos-direction-type;
            description
              "Direction.";
          }
          leaf vlan-mode {
            type boolean;
            description
              "Enable/disable VLAN mode.";
          }
          leaf begin-vlan {
            type uint16 {
              range "0..4094";
            }
            description
              "Begin VLAN id.";
          }
          leaf end-vlan {
            type uint16 {
              range "0..4094";
            }
            description
              "End VLAN id.";
          }
          choice cir-parameters {
            mandatory true;
            description
              "Specify cir parameters.";
            case cir {
              description
                "Specify cir parameters choice case as cir value.";
              leaf cir-value {
                type uint32 {
                  range "0..4294967295";
                }
                units "kbit/s";
                must "not(../pir-value) or ../pir-value>=../cir-value";
                mandatory true;
                description
                  "Committed information rate.";
              }
              leaf pir-value {
                type uint32 {
                  range "1..4294967295";
                }
                units "kbit/s";
                must "../pir-value>=../cir-value";
                description
                  "Peak information rate.";
              }
            }
            case cir-percentage {
              description
                "Specify cir parameters choice case as cir percentage value.";
              leaf cir-percent {
                when "../vlan-mode='false'";
                type uint8 {
                  range "0..100";
                }
                units "%";
                must "not(../pir-percent) or ../pir-percent>=../cir-percent";
                must "../identifier='no'";
                mandatory true;
                description
                  "Committed information rate percent.";
              }
              leaf pir-percent {
                when "../vlan-mode='false'";
                type uint8 {
                  range "0..100";
                }
                units "%";
                must "../pir-percent>=../cir-percent";
                description
                  "Peak information rate percent.";
              }
            }
          }
          leaf cbs {
            type uint32 {
              range "0..4294967295";
            }
            units "Byte";
            description
              "Committed burst size.";
          }
          leaf pbs {
            type uint32 {
              range "0..4294967295";
            }
            units "Byte";
            description
              "Peak burst size.";
          }
          leaf adjust-value {
            type int32 {
              range "-32..-1 | 1..31";
            }
            description
              "Adjust value.";
          }
          leaf green-action {
            type color-action-type;
            mandatory true;
            description
              "Action performed to the green packets.";
          }
          leaf green-service-class {
            when "../green-action='pass'";
            type qos-service-class;
            description
              "Service class marked to the green packets.";
          }
          leaf green-color {
            when "../green-service-class";
            type qos-color;
            mandatory true;
            description
              "Color marked to the green packets.";
          }
          leaf yellow-action {
            type color-action-type;
            ext:dynamic-default;
            description
              "Action performed to the yellow packets.";
          }
          leaf yellow-service-class {
            when "../yellow-action='pass'";
            type qos-service-class;
            description
              "Service class marked to the yellow packets.";
          }
          leaf yellow-color {
            when "../yellow-service-class";
            type qos-color;
            mandatory true;
            description
              "Color marked to the yellow packets.";
          }
          leaf red-action {
            type color-action-type;
            mandatory true;
            description
              "Action performed to the red packets.";
          }
          leaf red-service-class {
            when "../red-action='pass'";
            type qos-service-class;
            description
              "Service class marked to the red packets.";
          }
          leaf red-color {
            when "../red-service-class";
            type qos-color;
            mandatory true;
            description
              "Color marked to the red packets.";
          }
          leaf color-aware {
            type color-aware-type;
            description
              "Color Aware.";
          }
          leaf identifier {
            type identifier-type;
            default "no";
            description
              "Identifier. The range supported by this node varies according to the interface type. This node does not support modification or deletion.";
            ext:operation-exclude update {
            description "After the configuration is created, the node cannot be modified.";
            }
          }
        }
      }//cars
      container convergent-precedence {
        description
          "Configure convergent precedence.";
        leaf priority-type {
          type priority-convergent-type;
          description
            "Priority.";
        }
      }
      container drop-eligible-indicator-vlan {
        when "../../ethernet:ethernet/ethernet:main-interface/ethernet:l2-attribute/ethernet:pvid or ../../ethernet:ethernet/ethernet:main-interface/ethernet:l2-attribute/ethernet:trunk-vlans";
        description
          "Configure Drop Eligible Indicator.";
        leaf vlan-id {
          type pub-type:vlan-range {
            pattern '((409[0-4]|40[0-8][0-9]|[1-3][0-9]{3}|[1-9][0-9]{1,2}|[1-9])+(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)';
          }
          description
            "VLAN ID. The VLAN ID must fall within the VLAN ID range of the Layer 2 main interface.";
        }
      }
      container drop-eligible-indicator {
        description
          "Configure drop eligible indicator.";
        leaf enable {
          type empty;
          description
            "Enable drop eligible indicator.";
        }
      }
      container trust-untag-ip-precedence {
        description
          "Configure behavior aggregate (BA) classification based on the precedence value for untagged packets on a Layer 2 interface.";
        leaf enable {
          type untag-enable-type;
          description
            "Configure behavior aggregate (BA) classification based on the precedence value for untagged packets.";
        }
      }
      container trust-ip-precedences {
        description
          "List of configure behavior aggregate (BA) classification based on the precedence value of IP packets.";
        list trust-ip-precedence {
          key "vlan-mode";
          description
            "Configure behavior aggregate (BA) classification based on the precedence value of IP packets.";
          leaf vlan-mode {
            type boolean;
            description
              "Enable/disable VLAN mode.";
          }
          leaf vlan-id {
            when "../vlan-mode='true'";
            type pub-type:vlan-range {
              pattern '((409[0-4]|40[0-8][0-9]|[1-3][0-9]{3}|[1-9][0-9]{1,2}|[1-9])+(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)';
            }
            mandatory true;
            description
              "VLAN id.";
          }
        }
      }
      container share-shaping {
        must "not(not(./af1) and not(./af2) and not(./af3) and not(./af4) and not(./ef) and not(./cs6) and not(./cs7))";
        must "not(not(./be) and not(./af2) and not(./af3) and not(./af4) and not(./ef) and not(./cs6) and not(./cs7))";
        must "not(not(./be) and not(./af1) and not(./af3) and not(./af4) and not(./ef) and not(./cs6) and not(./cs7))";
        must "not(not(./be) and not(./af1) and not(./af2) and not(./af4) and not(./ef) and not(./cs6) and not(./cs7))";
        must "not(not(./be) and not(./af1) and not(./af2) and not(./af3) and not(./ef) and not(./cs6) and not(./cs7))";
        must "not(not(./be) and not(./af1) and not(./af2) and not(./af3) and not(./af4) and not(./cs6) and not(./cs7))";
        must "not(not(./be) and not(./af1) and not(./af2) and not(./af3) and not(./af4) and not(./ef) and not(./cs7))";
        must "not(not(./be) and not(./af1) and not(./af2) and not(./af3) and not(./af4) and not(./ef) and not(./cs6))";
        must "../port-queues/port-queue[service-class='be']/queue-schedule-mode and ../port-queues/port-queue[service-class='af1']/queue-schedule-mode and ../port-queues/port-queue[service-class='af2']/queue-schedule-mode and ../port-queues/port-queue[service-class='af3']/queue-schedule-mode and ../port-queues/port-queue[service-class='af4']/queue-schedule-mode and ../port-queues/port-queue[service-class='ef']/queue-schedule-mode and ../port-queues/port-queue[service-class='cs6']/queue-schedule-mode and ../port-queues/port-queue[service-class='cs7']/queue-schedule-mode";
        presence "Create share shaping.";
        description
          "Enable/disable interface share shaping. The configuration involves at least two queues, and the scheduling mode of the queues must be the same.";
        leaf be {
          type queue-select-be-type;
          must "not(../af1) or ../../port-queues/port-queue[service-class='be']/queue-schedule-mode=../../port-queues/port-queue[service-class='af1']/queue-schedule-mode";
          must "not(../af2) or ../../port-queues/port-queue[service-class='be']/queue-schedule-mode=../../port-queues/port-queue[service-class='af2']/queue-schedule-mode";
          must "not(../af3) or ../../port-queues/port-queue[service-class='be']/queue-schedule-mode=../../port-queues/port-queue[service-class='af3']/queue-schedule-mode";
          must "not(../af4) or ../../port-queues/port-queue[service-class='be']/queue-schedule-mode=../../port-queues/port-queue[service-class='af4']/queue-schedule-mode";
          must "not(../ef) or ../../port-queues/port-queue[service-class='be']/queue-schedule-mode=../../port-queues/port-queue[service-class='ef']/queue-schedule-mode";
          must "not(../cs6) or ../../port-queues/port-queue[service-class='be']/queue-schedule-mode=../../port-queues/port-queue[service-class='cs6']/queue-schedule-mode";
          must "not(../cs7) or ../../port-queues/port-queue[service-class='be']/queue-schedule-mode=../../port-queues/port-queue[service-class='cs7']/queue-schedule-mode";
          description
            "BE.";
        }
        leaf af1 {
          type queue-select-af1-type;
          must "not(../af2) or ../../port-queues/port-queue[service-class='af1']/queue-schedule-mode=../../port-queues/port-queue[service-class='af2']/queue-schedule-mode";
          must "not(../af3) or ../../port-queues/port-queue[service-class='af1']/queue-schedule-mode=../../port-queues/port-queue[service-class='af3']/queue-schedule-mode";
          must "not(../af4) or ../../port-queues/port-queue[service-class='af1']/queue-schedule-mode=../../port-queues/port-queue[service-class='af4']/queue-schedule-mode";
          must "not(../ef) or ../../port-queues/port-queue[service-class='af1']/queue-schedule-mode=../../port-queues/port-queue[service-class='ef']/queue-schedule-mode";
          must "not(../cs6) or ../../port-queues/port-queue[service-class='af1']/queue-schedule-mode=../../port-queues/port-queue[service-class='cs6']/queue-schedule-mode";
          must "not(../cs7) or ../../port-queues/port-queue[service-class='af1']/queue-schedule-mode=../../port-queues/port-queue[service-class='cs7']/queue-schedule-mode";
          description
            "AF1.";
        }
        leaf af2 {
          type queue-select-af2-type;
          must "not(../af3) or ../../port-queues/port-queue[service-class='af2']/queue-schedule-mode=../../port-queues/port-queue[service-class='af3']/queue-schedule-mode";
          must "not(../af4) or ../../port-queues/port-queue[service-class='af2']/queue-schedule-mode=../../port-queues/port-queue[service-class='af4']/queue-schedule-mode";
          must "not(../ef) or ../../port-queues/port-queue[service-class='af2']/queue-schedule-mode=../../port-queues/port-queue[service-class='ef']/queue-schedule-mode";
          must "not(../cs6) or ../../port-queues/port-queue[service-class='af2']/queue-schedule-mode=../../port-queues/port-queue[service-class='cs6']/queue-schedule-mode";
          must "not(../cs7) or ../../port-queues/port-queue[service-class='af2']/queue-schedule-mode=../../port-queues/port-queue[service-class='cs7']/queue-schedule-mode";
          description
            "AF2.";
        }
        leaf af3 {
          type queue-select-af3-type;
          must "not(../af4) or ../../port-queues/port-queue[service-class='af3']/queue-schedule-mode=../../port-queues/port-queue[service-class='af4']/queue-schedule-mode";
          must "not(../ef) or ../../port-queues/port-queue[service-class='af3']/queue-schedule-mode=../../port-queues/port-queue[service-class='ef']/queue-schedule-mode";
          must "not(../cs6) or ../../port-queues/port-queue[service-class='af3']/queue-schedule-mode=../../port-queues/port-queue[service-class='cs6']/queue-schedule-mode";
          must "not(../cs7) or ../../port-queues/port-queue[service-class='af3']/queue-schedule-mode=../../port-queues/port-queue[service-class='cs7']/queue-schedule-mode";
          description
            "AF3.";
        }
        leaf af4 {
          type queue-select-af4-type;
          must "not(../ef) or ../../port-queues/port-queue[service-class='af4']/queue-schedule-mode=../../port-queues/port-queue[service-class='ef']/queue-schedule-mode";
          must "not(../cs6) or ../../port-queues/port-queue[service-class='af4']/queue-schedule-mode=../../port-queues/port-queue[service-class='cs6']/queue-schedule-mode";
          must "not(../cs7) or ../../port-queues/port-queue[service-class='af4']/queue-schedule-mode=../../port-queues/port-queue[service-class='cs7']/queue-schedule-mode";
          description
            "AF4.";
        }
        leaf ef {
          type queue-select-ef-type;
          must "not(../cs6) or ../../port-queues/port-queue[service-class='ef']/queue-schedule-mode=../../port-queues/port-queue[service-class='cs6']/queue-schedule-mode";
          must "not(../cs7) or ../../port-queues/port-queue[service-class='ef']/queue-schedule-mode=../../port-queues/port-queue[service-class='cs7']/queue-schedule-mode";
          description
            "EF.";
        }
        leaf cs6 {
          type queue-select-cs6-type;
          must "not(../cs7) or ../../port-queues/port-queue[service-class='cs6']/queue-schedule-mode=../../port-queues/port-queue[service-class='cs7']/queue-schedule-mode";
          description
            "CS6.";
        }
        leaf cs7 {
          type queue-select-cs7-type;
          description
            "CS7."; 
        }
        leaf queue-schedule-mode {
          type queue-schedule-mode;
          description
            "Scheduling strategy of port queue.";
        }
        leaf weight {
          when "../queue-schedule-mode='wfq'";
          type uint8 {
            range "1..100";
          }
          mandatory true;
          description
            "Weight of wfq scheduling strategy.";
        }
        choice shaping-parameters {
          mandatory true;
          description
            "Specify shaping parameters.";
          case shaping {
            description
              "Specify shaping parameters choice case as shaping value.";
            leaf shaping-value {
              type uint32 {
                range "1..4294967294";
              }
              units "kbit/s";
              description
                "Shaping value.";
            }
          }
          case shaping-percent {
            description
              "Specify shaping parameters choice case as shaping percentage value.";
            leaf shaping-percentage {
              type uint8 {
                range "0..100";
              }
              units "%";
              description
                "Shaping percentage.";
            }
          }
        }
        leaf pbs {
          type uint32 {
            range "1..4194304";
          }
          units "Byte";
          description
            "Peak burst size.";
        }
      }
      container sub-port-queue-applys {
        description
          "List of configure sub port queue apply.";
        list sub-port-queue-apply {
          key "direction";
          description
            "Configure sub port queue apply.";
          leaf direction {
            type out-direction-type;
            description
              "Direction.";
          }
          leaf sub-port-queue-name {
            type leafref {
              path "/qos:qos/qos:queue-scheduler-template/qos:sub-port-queues/qos:sub-port-queue/qos:name";
            }
            mandatory true;
            description
              "Sub-port-queue template name.";
          }
          leaf group-name {
            type template-name;
            description
              "Group name.";
          }
        }
      }
      container user-vlan-user-group-queue-applys {
        description
          "List of configure user group queue on VLAN.";
        list user-vlan-user-group-queue-apply {
          must "./pe-end-vlan-id>=./pe-begin-vlan-id";
          must "./ce-end-vlan-id>=./ce-begin-vlan-id";		
          key "direction pe-begin-vlan-id pe-end-vlan-id ce-begin-vlan-id ce-end-vlan-id";
          description
            "Configure user group queue on VLAN.";
          leaf direction {
            type qos-direction-type;
            description
              "Direction.";
          }
          leaf pe-begin-vlan-id {
            type uint16 {
              range "0..4094";
            }
            description
              "Ce begin VLAN id.";
          }
          leaf pe-end-vlan-id {
            type uint16 {
              range "0..4094";
            }
            description
              "Ce end VLAN id.";
          }
          leaf ce-begin-vlan-id {
            type uint16 {
              range "1..4094";
            }
            description
              "Ce begin VLAN id.";
          }
          leaf ce-end-vlan-id {
            type uint16 {
              range "1..4094";
            }
            description
              "Ce end VLAN id.";
          }
          leaf identifier-type {
            type vlan-user-group-queue-identifier-type;
            mandatory true;
            description
              "Identify type. The range supported by this node varies according to the interface type. This node does not support modification or deletion.";
            ext:operation-exclude update {
              description "After the configuration is created, the node cannot be modified.";
            }
          }
          leaf user-group-queue-name {
            type leafref {
              path "/qos:qos/qos:queue-scheduler-template/qos:user-group-queues/qos:user-group-queue/qos:name";
            }
            must "/qos:qos/qos:queue-scheduler-template/qos:user-group-queues/qos:user-group-queue[qos:name=current()]/qos:mode='normal'";
            mandatory true;
            description
              "Group queue. This node does not support modification or deletion.";
            ext:operation-exclude update {
              description "After the configuration is created, the node cannot be modified.";
            }
          }
          leaf group-name {
            type template-name;
            description
              "The name of user queue group. This node does not support modification or deletion.";
            ext:operation-exclude update|delete {
              description "After the configuration is created, the node cannot be modified.";
            }
          }
        }
      }
      container bras-member-link-schedulers {
        when "../../ifm:type='Eth-Trunk'";
        description
          "List of configure weight based bandwidth allocation for member interfaces of a trunk.";
        list bras-member-link-scheduler {
          must "(user-access-type='subscriber-access' and direction='inbound') or user-access-type='leased-line-access'";
          key "user-access-type direction";
          description
            "Configure weight based bandwidth allocation for member interfaces of a trunk.";
          leaf user-access-type {
            type user-access-type;
            description
              "User access type.";
          }
          leaf direction {
            type qos-direction-type;
            description
              "Direction.";
          }
        }
      }
      container schedule-tree-distribute-modes {
        when "(../../ifm:type='Eth-Trunk' and ../../ifm:class='main-interface') or (../../ifm:type='Ip-Trunk' and ../../ifm:class='main-interface')";
        description
          "List of configure QoS schedule tree distribute mode outbound.";
        list schedule-tree-distribute-mode {
          key "direction";
          description
            "Configure QoS schedule tree distribute mode outbound.";
          leaf direction {
            type out-direction-type;
            description
              "Direction.";
          }
          leaf schedule-tree-mode {
            type schedule-tree-mode-type;
            default "distribute";
            description
              "Schedule tree mode.";
          }
        }
      }
      container loop-mode {
        when "../../ifm:type='Virtual-Ethernet'";
        presence "create loop-mode";
        description
          "Enable/disable QoS loop mode.";
      }
      container resource-pools {
        description
          "List of configure QoS queue resource.";
        list resource-pool {
          key "direction";
          description
            "Configure QoS queue resource.";
          leaf direction {
            type qos-direction-type;
            description
              "Direction.";
          }
          leaf pool-id {
            type pool-type;
            mandatory true;
            description
              "Pool-id.";
          }
        }
      }
      container user-group-queue-applys {
        description
          "List of configure user group queue application.";
        list user-group-queue-apply {
          key "direction";
          max-elements  "2";
          description
            "Configure user group queue application.";
          leaf direction {
            type qos-direction-type;
            description
              "Group queue direction.";
          }
          leaf group-queue-name {
            type leafref {
              path "/qos:qos/qos:queue-scheduler-template/qos:user-group-queues/qos:user-group-queue/qos:name";
            }
            must "/qos:qos/qos:queue-scheduler-template/qos:user-group-queues/qos:user-group-queue[qos:name=current()]/qos:mode='normal'";
            mandatory true;
            description
              "Group queue name.";
          }
          leaf group-name {
            type string {
              length "1..31";
            }
            description
              "Group-name.";
          }
        }
      }
      container mpls-l2vc {
        description
          "Configure MPLS l2vc.";
        leaf diffserv-domain-name {
          type leafref {
            path "/qos:qos/qos:classifier-template/qos:diffserv-domains/qos:diffserv-domain/qos:name";
          }
          description
            "Name of a diffserv-domain.";
        }
      }
      container member-link-schedulers {
        when "(../../ifm:type='Eth-Trunk' and ../../ifm:class='main-interface') or (../../ifm:type='Ip-Trunk' and ../../ifm:class='main-interface')";
        description
          "List of configure trunk flow split.";
        list member-link-scheduler {
          key "member-link-scheduler-type";
          description
            "Configure trunk flow split.";
          leaf member-link-scheduler-type {
            type member-link-scheduler-type;
            description
              "Business type.";
          }
          leaf direction {
            when "../member-link-scheduler-type='user-queue'";
            type out-direction-type;
            description
              "Direction.";
          }
        }
      }
      container qos-lr {
        when "../../ifm:type='MEth'";
        description
          "Configure limit on the rate of traffic on an interface.";
        choice cir-parameters {
          description
             "Specify cir-parameters.";
          case cir {
            description
              "Specify cir parameters choice case as cir value.";
            leaf cir-value {
              type uint32 {
                range "1..4294967294";
              }
              units "Mbit/s";
              description
                "Committed information rate.";
            }
          }
          case cir-percent {
            description
              "Specify cir parameters choice case as cir percentage value.";
            leaf cir-percent-value {
              type uint8 {
                range "1..100";
              }
              units "%";
              description
                "CIR percentage.";
            }
          }
        }
        container pps {
          description
            "Configure the rate limit on the management interface.";
          leaf packets {
            type uint32 {
              range "100..10240";
            }
            units "pps";
            default "3000";
            description
              "The maximum number of packets that are allowed to pass per second.";
          }
        }
      }
      container ldp-traffic {
        description
          "Configure ldp traffic.";
        leaf traffic-type {
          type traffic-type;
          description
            "Traffic of type.";
        }
      }
      container buffer-policy-mode {
        description
          "Configure buffer policy buffer mode.";
        leaf buffer-mode {
          type buffer-mode-type;
          description
            "Buffer mode.";
        }
      }
      container hard-pipe-apply {
        presence "Create hard pipe.";
        description
          "Enable/disable hard pipe apply.";
        leaf mode {
          type hard-pipe-mode;
          mandatory true;
          description
            "Hard pipe mode.";
        }
        leaf bandwidth {
          type uint32 {
            range "1..4294967294";
          }
          units "Mbit/s";
          mandatory true;
          description
            "Hard pipe bandwidth.";
        }
      }  
      container channel-adjustment {
      when "../../ifm:class='main-interface'";
        presence "create channel-adjustment";
        description
          "Enable/disable channel network header length adjustment.";
        leaf adjust-value {
          type uint16 {
            range "1..63";
          }
          units "Byte";
          mandatory true;
          description
            "Adjustment value.";
        }
      }
      container user-vlan-profile-applys {
        description
          "List of configure QoS profile on user VLAN.";
        list user-vlan-profile-apply {
          must "./pe-end-vlan-id>=./pe-begin-vlan-id";
          must "./ce-end-vlan-id>=./ce-begin-vlan-id";
          key "direction pe-begin-vlan-id pe-end-vlan-id ce-begin-vlan-id ce-end-vlan-id";
          description
            "Configure QoS profile on user VLAN.";
          leaf direction {
            type qos-direction-type;
            description
              "Direction.";
          }
          leaf pe-begin-vlan-id {
            type uint16 {
              range "0..4094";
            }
            description
              "Pe begin VLAN id.";
          }
          leaf pe-end-vlan-id {
            type uint16 {
              range "0..4094";
            }
            description
              "Pe end VLAN id.";
          }
          leaf ce-begin-vlan-id {
            type uint16 {
              range "1..4094";
            }
            description
              "Ce begin VLAN id.";
          }
          leaf ce-end-vlan-id {
            type uint16 {
              range "1..4094";
            }
            description
              "Ce end VLAN id.";
          }
          leaf profile-name {
            type leafref {
              path "/qos:qos/qos:queue-scheduler-template/qos:profiles/qos:profile/qos:name";
            }
            must "count(/qos:qos/qos:queue-scheduler-template/qos:profiles/qos:profile[qos:name=current()]/qos:cars/qos:car)>=1";
            mandatory true;
            description
              "Qos profile name.";
            ext:operation-exclude update {
              description "After the configuration is created, the node cannot be modified.";
            }
          }
          leaf each-vlan {
            type yes-or-no;
            mandatory true;
            description
              "Qos profile takes effect on the traffic of each VLAN separately or not.";
            ext:operation-exclude update {
              description "After the configuration is created, the node cannot be modified.";
            }
          }
        }
      }
      container service-template-shaping {
        description
          "Configure service template shaping.";
        container all-service-class {
          description
            "Configure shaping for all service class with service template.";
          leaf service-template-name {
            type leafref {
              path "/qos:qos/qos:queue-scheduler-template/qos:service-templates/qos:service-template/qos:name";
            }
            description
              "Service template.";
          }
        }
        container specific-service-classs {
          description
            "List of configure shapings based on class queue with service template.";
          list specific-service-class {
            key "service-class";
            description
              "Configure shaping based on class queue with service template.";
            leaf service-class {
              type qos-service-class;
              description
                "Class of service, some boards do not support this object.";
            }
            leaf service-template-name {
              type leafref {
                path "/qos:qos/qos:queue-scheduler-template/qos:service-templates/qos:service-template/qos:name";
              }
              mandatory true;
              description
                "Service template.";
            }
          }
        }
      }      
      container default-service-class-remote {
        description
          "Configure the upstream traffic to enter the specified queue on the remote AP interface of the master device.";
        leaf service-class {
          type qos-service-class;
          description
            "Service class.";
        }
      }
      container trust-remotes {
        description
          "List of configure BA classification on the interface of the master device and configure the port extension interface to deliver configurations to AP devices.";
        list trust-remote {
          must "(./vlan-mode='false' and ./begin-vlan=0 and ./end-vlan=0) or (./vlan-mode='true' and ./begin-vlan>0)";
          must "./begin-vlan <= ./end-vlan";
          must "./vlan-mode='false' or (./vlan-mode='true' and ../../../ethernet:ethernet/ethernet:main-interface/ethernet:l2-attribute) or ../../../ifm:class='sub-interface'";
          key "type direction vlan-mode begin-vlan end-vlan";
          description
            "Configure BA classification on the interface of the master device and configure the port extension interface to deliver configurations to AP devices.";
          leaf type {
            type remote-trust-type;
            description
              "Trust IP dscp or 8021p.";
          }
          leaf direction {
            type trust-remote-direction-type;
            description
              "Direction.";
          }
          leaf vlan-mode {
            type boolean;
            description
              "Enable/disable VLAN mode.";
          }
          leaf begin-vlan {
            type uint16 {
              range "0..4094";
            }
            description
              "Begin VLAN ID.";
          }
          leaf end-vlan {
            type uint16 {
              range "0..4094";
            }
            description
              "End VLAN ID.";
          }
          leaf diffserv-domain-name {
            when "../type='ip-dscp'";
            type leafref {
              path "/qos:qos/qos:classifier-template/qos:diffserv-domains/qos:diffserv-domain/qos:name";
            }
            mandatory true;
            description
              "Name of a diffserv domain.";
          }
          leaf type-8021p {
            when "../type='8021p'";
            type type-8021p;
            mandatory true;
            description
              "Trust 8021p, inner 8021p or outer 8021p.";
          }
        }
      }
      container wfq-shaping {
        description
          "Configure wfq shaping.";
        choice shaping-parameters {
          description
            "Specify shaping parameters.";
          case shaping {
            description
              "Specify shaping parameters choice case as shaping value.";
            leaf shaping-value {
              type uint32 {
                range "0..4294967294";
              }
              units "Mbit/s";
              description
                "Rate of shaping.";
            }
          }
          case shaping-percent {
            description
              "Specify shaping parameters choice case as shaping percentage value.";
            leaf shaping-percentage {
              type uint8 {
                range "0..100";
              }
              units "%";
              description
                "Percentage of shaping.";
            }
          }
        }
      }
      container source-board-schedule-weights {
        description
          "List of configure weight based scheduling for a source board.";
        list source-board-schedule-weight {
          key "slot-id";
          description
            "Configure weight based scheduling for a source board.";
          leaf slot-id {
            type slot-id;
            description
              "Slot ID.";
          }
          leaf weight-value {
            type uint8 {
              range "1..100";
            }
            mandatory true;
            description
              "Weight value.";
          }
        }
      }
      container deficit-unit {
        presence "Create deficit unit.";
        description
          "Enable/disable the chip scheduling granularity.";
        leaf unit {
          type deficit-unit-type;
          mandatory true;
          description
            "Unit.";
        }
      }
      container default-user-queue {
        must "not(not(./cir) and not(./pir) and not(./cbs) and not(./pbs) and not(./weight))";
        must "not(../../ethernet:ethernet/ethernet:main-interface/ethernet:l2-attribute)";
        presence "Create default user queue.";
        description
          "Enable/disable default user queue. This object must contain at least one parameter in cir/cbs/pir/pbs/weight.";
        leaf direction {
          type out-direction-type;
          mandatory true;
          description
            "Direction.";
        }
        leaf cir {
          type uint32 {
            range "0 | 16..4294967294";
          }
          units "kbit/s";
          description
            "Cir.";
        }
        leaf cbs {
          type uint32 {
            range "1..4194304";
          }
          units "Byte";
          description
            "Cbs.";
        }
        leaf pir {
          type uint32 {
            range "0 | 16..4294967294";
          }
          units "kbit/s";
          must "(not(../cir) and ../pir>=10000) or (../cir and ../pir>=../cir)";
          description
            "Pir.";
        }

        leaf pbs {
          type uint32 {
            range "1..4194304";
          }
          units "Byte";
          must "not(../cbs) or (../cbs and ../pbs>=../cbs)";
          description
            "Pbs.";
        }
        leaf weight {
          type uint8 {
            range "1..63";
          }
          description
            "Weight.";
        }
      }
      container vni-cfg-peers {
        when "../../ifm:type='Nve'";
        description
          "List of configure profile peers.";
        list vni-cfg-peer {
          must "./source-ip !=peer-ip";
          key "direction vni-id source-ip peer-ip";
          description
            "Configure profile peers.";
          leaf direction {
            type qos-direction-type;
            description
              "Direction.";
          }
          leaf vni-id {
            type uint32 {
              range "1..16777215";
            }
            description
              "Vni ID.";
          }
          leaf source-ip {
            type inet:ipv4-address-no-zone;
            description
              "Source IP.";
          }
          leaf peer-ip {
            type inet:ipv4-address-no-zone;
            description
              "Peer IP.";
          }
          leaf profile-name {
            type leafref {
              path "/qos:qos/qos:queue-scheduler-template/qos:profiles/qos:profile/qos:name";
            }
            must "/qos:qos/qos:queue-scheduler-template/qos:profiles/qos:profile[qos:name=current()]/qos:mode='normal'";
            mandatory true;
            description
              "Profile Name.";
            ext:operation-exclude update;
          }
        }
      }
      container qos-lr-outbound {
		presence "Create qos lr outbound.";
        description
          "Configure the traffic shaping rate to limit the rate of data packets sent by an interface.";
        leaf cir {
          type uint32 {
            range "1..800000000";
          }
		  mandatory true;
          description
            "Committed information rate (unit: kbps/mbps/gbps).";
        }
        leaf cir-unit {
          type queue-rate;
          default "kbps";
          description
            "Specify the rate unit for cir.";
        }
        leaf cbs {
          type uint32 {
            range "1..536870912";
          }
          description
           "Committed information rate (unit: bytes/kbytes/mbytes).";
        }
        leaf cbs-unit {
          when "../cbs";
          type queue-burst-size;
          default "bytes";
          description
            "Specify the rate unit for cbs.";
        }
      }
      container wreds {
        description
          "List of configure a WRED drop profile to an interface.";
        list wred{
		  key "drop-profile-name";
		  description
            "Configure wred.";
          leaf drop-profile-name {
            type string {
              length "1..31";
            }
            description
              "Specifies the name of a WRED drop profile.";
          }
        }
      }
      container queue-buffer-monitors {
        description
          "List of configure upper and lower buffer thresholds of queues.";
        list queue-buffer-monitor {
          must "(./service-class and ./enable) or (not(./service-class) and not(./enable))";
          key "service-class";
          max-elements 8;
		  description
		    "Configure the buffer monotors.";
          leaf service-class {
            type uint8{
                  range "0..7";
            }
            description
              "Class of service.";
          }
          leaf enable {
            type switch-type;
            description
              "Enables/Disables.";
          }
        }
        container queue-buffer-monitor-threds {
          description
            "List of configure the buffer monitor thred.";
          list queue-buffer-monitor-thred {
            key "service-class";
            max-elements 8;
            description
              "Configure the buffer monitor thred.";
            leaf service-class {
              type uint8 {
                range "0..7";
              }
              description
                "Class of service.";
            }
            leaf low-limit-percentage {
              type uint8 {
                range "0..99";
              }
              units "%";
              default "10";
              description
                "Low limit percentage.";
            }
            leaf high-limit-percentage {
              type uint8 {
                range "1..100";
              }
              units "%";
              must "../high-limit-percentage>../low-limit-percentage";
              default "90";
              description
                "High limit percentage.";
            }
          }
        }
      }
      container port-priority {
        description
          "Configure the priority for an interface.";
        leaf priority {
          type uint8 {
            range "0..7";
          }
		  default "0";
          description
            "Specifies the priority of an interface.";
        }
      }
      container port-phb-trusts {
        description
          "List of configure the phb remark.";
        list port-phb-trust {
          key "type";
          description
            "Configure the phb remark.";
          ext:generated-by system {
          	description "The instances are created and deleted following the interface.";
          }
          ext:operation-exclude create {
            description "The instances cannot be created.";
          }
          leaf type {
            type qos-phb-type;
            description
              "Port phb trust type.";
          }
          leaf dscp-phb-enable {
            type port-phb-trust;
            mandatory true;
            description
              "Enable/disable phb remark.";
          }
        }
      }
      container queue-schedules {
        description
          "List of configure the scheduling parameters of queues on an interface.";
		list queue-schedule {
		  key "queue-index";
		  description
			"Configure the scheduling parameters of queues.";
		  leaf queue-index {
			type uint8 {
			  range "0..7";
			}
			description
			  "Configure the index of the queue.";
		  }
		  leaf schedule-mode {
			type schedule-type;
			mandatory true;
			description
			  "Configure the mode of schedule.";
		  }
          leaf weight {
			when "../schedule-mode='drr'";
            type uint8 {
              range "1..100";
            }
            default "1";
            description
              "Configure the DRR weight.";
          }
		}
      }
    container burst-mode {
	    description
		  "Configure the burst traffic buffer mode on interface.";   
		leaf mode {
		  type qos:burst-mode-type;
		  description
		   "Mode type.";
		  }
	  }
    container multicast-burst-mode {
	    description
		  "Configure the burst multicast traffic buffer mode on interface.";   
		leaf mode {
		  type qos:burst-mode-type;
		  description
		   "Mode type.";
		  }
	  }
      container trust-upstream {
        description
          "Configure the trust upstream command applies a DiffServ domain.";
        leaf diffserv-domain-name {
          type string {
            length "1..48";
          }
          ext:dynamic-default;
          description
            "Specifies the name of a DiffServ domain.";
        }
      }
      container trust-8021p-dscp {
        description
            "Configure the priority to be mapped for packets.";
        leaf type {
          type type-8021p;
          ext:dynamic-default;
          description
            "Specifies the priority type, the default value varies with the device type and interface service type.";
        }
      }
      container queue-buffers {
        description
          "List of queue buffer for interface.";
        list queue-buffer {
          key "queue-index config-mode";
          description
            "Configure queue buffer.";
          leaf queue-index {
            type uint8 {
              range "0..7";
            }
            description
              "Configure the index of the queue.";
          }
          leaf config-mode {
            type queue-config-mode;
            must "(../config-mode='shape' and (../cir-percent or ../cir-value)) or (../config-mode='buffer' and (../static-value or ../packets-value or ../dynamic-value)) or (../config-mode='shape-buffer' and ((../cir-percent or ../cir-value) and (../static-value or ../packets-value or ../dynamic-value)))";
            description
              "Queue config mode.";
          }
          choice shaping-parameters {
            description
              "Sharping Parameters.";
            case shaping-percent {
              description
                "Case of shaping percent.";
              leaf cir-percent {
                type uint8 {
                  range "1..100";
                }
                units "%";
				mandatory true;
                description
                  "The percentage value of the CIR.";
              }
              leaf pir-percent {
                type uint8 {
                  range "1..100";
                }
                units "%";
                must "../pir-percent>=../cir-percent";
                description
                  "The percentage value of the PIR.";
              }
            }
            case shaping-absolute {
              description
                "Case of shaping absolute.";
              leaf cir-value {
                type uint32 {
                  range "1..800000000";
                }
				mandatory true;
                description
                  "Specify the absolute value of the committed information rate (unit: kbps/mbps/gbps).";
              }
              leaf cir-unit {
                type qos:queue-rate;
                default "kbps";
                description
                  "Specify the rate unit for the cir.";
              }
              leaf cbs-value {
                type uint32 {
                  range "1..268435456";
                }
                description
                  "Specifies the absolute value of cbs (unit: bytes/kbytes/mbytes).";
              }
              leaf cbs-unit {
                type qos:queue-burst-size;
                default "bytes";
                description
                  "Specify the unit for the cbs.";
              }
              leaf pir-value {
                type uint32 {
                  range "1..800000000";
                }
                description
                  "Specifies the absolute value of pir (unit: kbps/mbps/gbps).";
              }
              leaf pir-unit {
                type qos:queue-rate;
                default "kbps";
                description
                  "Specify the unit for the pir.";
              }
              leaf pbs-value {
                type uint32 {
                  range "1..268435456";
                }
                description
                  "Specifies the absolute value of pbs (unit: bytes/kbytes/mbytes).";
              }
              leaf pbs-unit {
                type qos:queue-burst-size;
                default "bytes";
                description
                  "Specify the unit for the pbs.";
              }
            }
          }
          choice queue-buffer-type {
            description
              "Choice of queue buffer value.";
            case static {
              description
                "Value of qos queue buffer static threshold.";
              leaf static-value {
                type uint32 {
                  range "0..4294967295";
                }
                description
                  "Bytes of qos queue buffer static threshold.";
              }
              leaf static-unit {
                type qos:queue-burst-size;
                default "bytes";
                description
                  "Unit of qos queue buffer static threshold.";
              }
              leaf packets-value {
                type uint32 {
                  range "0..104857600";
                }
                description
                  "Packets of qos queue buffer static threshold.";
              }
            }
            case dynamic {
              description
                "Value of qos queue buffer dynamic threshold.";
              leaf dynamic-value {
                type uint32 {
                  range "0..12";
                }
                description
                  "Value of qos queue buffer dynamic threshold.";
              }
            }
          }
        }
      }
      container car-templates {
        description
          "List of qos car template for interface.";
        list car-template {
          key "direction";
          description
            "Configure the qos car template for interface.";
          leaf direction {
            type qos:qos-direction-type;
            description
              "Car direction.";
          }
          leaf name {
            type leafref {
              path "/qos:qos/qos:car-template/qos:templates/qos:template/qos:name";
            }
            mandatory true;
            description
              "Car name.";
          }
          leaf is-decapsulate {
            type boolean;
            default "false";
            description
              "Enable/disable decapsulation.";
          }
        }
      }
      container qos-local-id {
        when "../../ifm:type='Tunnel'";
        description
          "Configure the qos local id on tunnel interface.";	  
        leaf qos-local-id {
          type uint32 {
            range "1..255";
          }
          description
            "Qos local id, set on tunnel interface.";
        }
      }
      container traffic-inloop-enable {
        description
          "Configure the traffic inloop enable command to enable the loopback function after traffic shapping.";
        leaf enable {
          type qos:switch-flag;
          description
            "Traffic inloop enable.";
        }
      }
      container queue-capability-enable {
        description
          "Configure the qos queue-scheduling enable command to enable the queue capability function.";
        leaf enable {
          type qos:switch-flag;
          description
            "Qos queue-scheduling enable.";
        }
      }
      container encapsulation-overhead {
        description
          "Configure the encapsulation overhead.";
        container tunnel-encap-overhead {
          description
            "Configure the tunnel overhead.";
          leaf encap-length {
            type int32 {
              range "1..255";
            }
            must "../../../../ifm:type='Tunnel'";
            description
              "Encapsulation length.";
          }
        }
        container map-to-interface {
          description
            "Configure the tunnel compensation enable on a tunnel interface.";
          leaf interface-name {
            type leafref {
              path "/ifm:ifm/ifm:interfaces/ifm:interface/ifm:name";
            }
            must "../../../../ifm:type='Tunnel'";
            description
              "Interface name.";
          }
        }
      }
      container schedule-profile {
        when "../../ifm:class='main-interface' and (../../ifm:type='Ethernet' or ../../ifm:type='GigabitEthernet' or " +
"../../ifm:type='100GE' or ../../ifm:type='200GE' or ../../ifm:type='40GE' or ../../ifm:type='10GE' or ../../ifm:type='GEBrief' or " +
"../../ifm:type='4x10GE' or ../../ifm:type='10x10GE' or ../../ifm:type='3x40GE' or ../../ifm:type='4x25GE' or ../../ifm:type='25GE' or " +
"../../ifm:type='XGigabitEthernet' or ../../ifm:type='50|100GE' or ../../ifm:type='50GE' or ../../ifm:type='400GE' or ../../ifm:type='1200GE')";
        description
            "Configure the qos schedule profile for interface.";
        leaf name {
          type leafref {
            path "/qos:qos/qos:queue-scheduler-template/qos:schedule-profiles/qos:schedule-profile/qos:name";
          }
          default "default";
          description
            "Specifies the name of a Schedule profile.";
        }
      }
      container queue-ecns {
        description
          "List of configure QoS queue ECN.";
        list queue-ecn {
          key "service-class";
          max-elements 8;
          description
            "Configure QoS queue ECN.";
          leaf service-class {
            type qos-service-class;
            description
              "Class of service.";
          }
          leaf enable {
            type boolean;
            default "false";
            description
              "Enable/disable ECN.";
          }
        }
      }
    }
  }
  augment /ni:network-instance/ni:instances/ni:instance {
    description
      "Adds qos configuration to the instance.";
    container qos {
      description
        "Configure QoS apply.";
      container traffic-policy-vxlans {
        when "not(../../ni:name='_public_')";
        description
          "List of configure application of a traffic policy.";
        list traffic-policy-vxlan {
          key "direction";
          max-elements "2";
          description
            "Configure application of a traffic policy.";
          leaf direction {
            type qos-direction-type;
            description
              "Direction.";
          }
          leaf policy-name {
            type leafref {
              path "/qos:qos/qos:classifier-template/qos:traffic-policys/qos:traffic-policy/qos:name";
            }
            mandatory true;
            description
              "Policy name.";
          }
          leaf layer {
            when "../direction='inbound'";
            type policy-apply-vxlan-layer-type;
            description
              "Classification based on Layer 2 or Layer 3 information.";
          }
        }
      }
    }//augment network-instance/instances/instance/qos
  }//augment network-instance/instances/instance
  augment /lcs:license/lcs:license-items/lcs:license-item {
    description
      "Adds qos configuration to license model.";
    container port-hqoss {
      when "../lcs:name='LCR5S40NHQS0P' or ../lcs:name='LCR5S40XHQS0P' or ../lcs:name='LCR5S40GHQS0P' or ../lcs:name='LCR5S40VHQS0P' or ../lcs:name='LCR5S40YHQS0P' or ../lcs:name='LTNRS69GHQS0P' or ../lcs:name='LTNRS69NHQS0P' or ../lcs:name='LTNRS69VHQS0P' or ../lcs:name='LTNRS69YHQS0P' or ../lcs:name='LTNRS69XHQS0P' or ../lcs:name='LCX6S00HQSN0P' or ../lcs:name='LCX6S00HQSX0P' or ../lcs:name='LCX6S00HQSV0P' or ../lcs:name='LCX6S00HQSY0P' or ../lcs:name='LCX6S00HQSG0P'";
      description
        "List of configure port hqos license.";
      list port-hqos {
        key "position";
        description
          "Configure port hqos license.";
        leaf position {
          type string {
            length "1..32";
          }
          description
            "Port position.";
        }
        leaf active-status {
          type lcs-active-status-type;
          config false;
          description
            "Activated State.";
        }
      }
    }
  }//augment /lcs:license/lcs:license-items/lcs:license-item
  augment /vlan:vlan/vlan:vlans/vlan:vlan {
    description
      "List of configure application of a traffic policy.";
    container traffic-policy-applys {
      description
        "List of configure application of a traffic policy.";
      list traffic-policy-apply {
        key "policy-name direction";
        max-elements 4;
        description
          "Configure policy name.";
        leaf policy-name {
          type leafref {
            path "/qos:qos/qos:classifier-template/qos:traffic-policys/qos:traffic-policy/qos:name";
          }
          description
            "Policy name.";
        }
        leaf direction {
          type qos-direction-type;
          description
            "Direction.";
        }
      }
    }
  }
}//huawei-qos
