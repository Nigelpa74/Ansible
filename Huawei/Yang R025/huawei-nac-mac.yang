/*
Copyright (C) 2020-2025 Huawei Technologies Co., Ltd. All rights reserved.
*/
module huawei-nac-mac {
  yang-version 1.1;
  namespace "urn:huawei:yang:huawei-nac-mac";
  prefix hw-nac-mac;
  import huawei-pub-type {
    prefix pub-type;
  }
  import huawei-extension {
    prefix ext;
  }
  import huawei-aaa {
    prefix aaa;
  }
  organization
    "Huawei Technologies Co., Ltd.";
  contact
    "Huawei Industrial Base
    Bantian, Longgang
    Shenzhen 518129
    People's Republic of China
    Website: http://www.huawei.com
    Email: support@huawei.com";
  description
    "This module contains a collection of YANG definitions for
    configuring NAC implementations.
    Redistribution and use in source and binary forms, with or
    without modification, is permitted pursuant to, and subject
    to the license terms contained in, the Simplified BSD License
    set forth in Section 4.c of the IETF Trust's Legal Provisions
    Relating to IETF Documents.";

  revision 2025-08-09 {
    description
      "1.Add the must condition;
       2.Modify the task-name of the nac-mac node to eap.";
    reference
      "Huawei private";
  }
  revision 2024-12-05 {
    description
      "Add default case to user-name-format and delete unnecessary mandatory definition of mac-address.";
    reference
      "Huawei private";
  }
  revision 2024-03-07 {
    description
      "Modify default value of trigger-packet.";
    reference
      "Huawei private";
  }
  revision 2023-12-22 {
    description
      "Add several nodes for NAC.";
    reference
      "Huawei private";
  }
  revision 2022-07-04 {
    description
      "Modify the description of mac-address-format.";
    reference
      "Huawei private";
  }
  revision 2022-03-24 {
    description
      "Modify MAC Address.";
    reference
      "Huawei private";
  }
  revision 2022-01-08 {
    description
      "Add default trigger-packet.";
    reference
      "Huawei private";
  }
  revision 2021-01-28 {
    description
      "Add container force-domain, and leaf authentication-method.";
    reference
      "Huawei private";
  }
  revision 2020-03-13 {
    description
      "Initial revision.";
    reference
      "Huawei private.";
  }
  ext:task-name "eap";
  container nac-mac {
    description
      "Configuration and state data of MAC access parameters.";
    container global {
      description
        "Configure global MAC access.";
      leaf quiet-period {
        type uint16 {
          range "0..3600";
        }
        units "s";
        default "60";
        description
          "Sets the quiet period for MAC address authentication users who fail to be authenticated.";
      }
      leaf quiet-times {
        type uint8 {
          range "1..10";
        }
        default "10";
        description
          "Specifies the maximum number of authentication failures before a MAC address authentication user enters the quiet state.";
      }
      container force-domains {
        description
          "List of the domain as a forcible domain in MAC authentication.";
        list force-domain {
          key "domain mac";
          description
            "Configure the domain as a forcible domain in MAC authentication.";
          leaf domain {
            type leafref {
              path "/aaa:aaa/aaa:domains/aaa:domain/aaa:name";
            }
            description
              "Specifies the domain-name.";
          }
          leaf mac {
            type pub-type:mac-address {
              pattern
                '[0-9a-f][02468ace][0-9a-f]{2}(-[0-9a-f]{4}){2}';
            }
            description
              "Specifies MAC address.";
          }
          leaf mask {
            type pub-type:mac-address {
              pattern
                '(([8cef][0]{3}|[f][8cef][0]{2}|[f]{2}[8cef][0]|[f]{3}[8cef])(-[0]{4}){2})|([f]{4}(-([8cef][0]{3}|[f][8cef][0]{2}|[f]{2}[8cef][0]|[f]{3}[8cef]))(-[0]{4}){1})|([f]{4}(-[f]{4})(-([8cef][0]{3}|[f][8cef][0]{2}|[f]{2}[8cef][0]|[f]{3}[8cef])))';
            }
            mandatory true;
            description
              "Specifies the MAC address mask.";
          }
        }
      }
    }
    container mac-access-profiles {
      description
        "List of MAC access profile related configuration and state data.";
      list mac-access-profile {
        key "name";
        max-elements "128";
        ext:generated-by "system" {
          ext:filter "name = 'mac_access_profile'";
          description
            "The default mac access profile is generated by system.";
        }
        ext:operation-exclude "delete" {
          ext:filter "name = 'mac_access_profile'";
          description
            "The default mac access profile cannot be deleted.";
        }
        description
          "Configure MAC access profile.";
        leaf name {
          type string {
            length "1..31";
          }
          description
            "Specifies the name of a MAC access profile.";
        }
        leaf get-dhcp-option {
          type uint8 {
            range "82";
          }
          description
            "Specifies the option that the device sends to the authentication server. The value is fixed as 82.";
        }
        leaf off-line-dhcp-release {
          type boolean;
          default "false";
          description
            "Enable/disable the device to clear user entries when receiving DHCP Release packets from MAC address authentication users.";
        }
        leaf authentication-method {
          type enumeration {
            enum "chap" {
              value 0;
              description
                "Specifies MAC authentication using the Challenge Handshake Authentication Protocol (CHAP).";
            }
            enum "pap" {
              value 1;
              description
                "Specifies MAC authentication using the Password Authentication Protocol (PAP).";
            }
          }
          default "pap";
          description
            "Configure the MAC authentication mode.";
        }
        leaf-list trigger-packet {
          type enumeration {
            enum "dhcp" {
              value 0;
              description
                "Triggers MAC address authentication through DHCP packets.";
            }
            enum "arp" {
              value 1;
              description
                "Triggers MAC address authentication through ARP packets.";
            }
            enum "dhcpv6" {
              value 2;
              description
                "Triggers MAC address authentication through DHCPv6 packets.";
            }
            enum "nd" {
              value 3;
              description
                "Triggers MAC address authentication through ND packets.";
            }
            enum "any-l2-packet" {
              value 4;
              description
                "Triggers MAC address authentication through any packets.";
            }
          }
          default "dhcp";
          default "arp";
          default "any-l2-packet";
          default "dhcpv6";
          default "nd";
          description
            "Configure the packet types that can trigger MAC address authentication.";
        }
        choice user-name-format {
          default "mac-address";
          description
            "Configure the user name for MAC address authentication.";
          case fixed-format {
            description
              "Fixed format case.";
            leaf user-name {
              type string {
                length "1..64";
              }
              description
                "Specifies a fixed user name for MAC address authentication.";
            }
            leaf fixed-user-password {
              type pub-type:password-extend {
                length "1..268";
              }
              must "../user-name";
              description
                "The password is a string ranging from 1 to 128 characters for a plain text password and 128 to 268 characters for a cipher text password.";
            }
          }
          case mac-address {
            description
              "Specifies the MAC address as the user name for MAC address authentication.";
            leaf mac-address-format {
              type enumeration {
                enum "with-hyphen" {
                  value 0;
                  description
                    "Indicates that the MAC address contains hyphens (-), for example, 0005-e01c-02e3.";
                }
                enum "with-hyphen-normal" {
                  value 1;
                  description
                    "Indicates that the MAC address contains hyphens (-), for example, XX-XX-XX-XX-XX-XX.";
                }
                enum "with-hyphen-colon" {
                  value 2;
                  description
                    "Indicates that the MAC address contains colons (:), for example, 0005:e01c:02e3.";
                }
                enum "with-hyphen-normal-colon" {
                  value 3;
                  description
                    "Indicates that the MAC address contains colons (:), for example, XX:XX:XX:XX:XX:XX.";
                }
                enum "without-hyphen" {
                  value 4;
                  description
                    "Indicates that the MAC address does not contain hyphens (-) or colons (:), for example, 0005e01c02e3.";
                }
              }
              default "without-hyphen";
              description
                "Specifies the MAC address format.";
            }
            leaf letter {
              type enumeration {
                enum "uppercase" {
                  value 0;
                  description
                    "Indicates that the name of a MAC address authentication user is in uppercase.";
                }
              }
              description
                "Indicates that the name of a MAC address authentication user is in uppercase or lowercase.";
            }
            leaf mac-address-password {
              type pub-type:password-extend {
                length "1..268";
              }
              description
                "The password is a string ranging from 1 to 128 characters for a plain text password and 128 to 268 characters for a cipher text password.";
            }
          }
          case dhcp-option {
            description
              "Specifies the name of the MAC address authentication user to a specified DHCP option.";
            leaf dhcp-option-format {
              type enumeration {
                enum "option82-circuit-id" {
                  value 0;
                  description
                    "Specifies the circuit ID in the DHCP Option82 field as the user name in MAC address authentication.";
                }
                enum "option82-remote-id" {
                  value 1;
                  description
                    "Specifies the remote ID in the DHCP Option82 field as the user name in MAC address authentication.";
                }
                enum "option82-circuit-and-remote-id" {
                  value 2;
                  description
                    "Specifies a character string that is a combination of the circuit-id and remote-id in the DHCP Option82 field as the user name in MAC address authentication.";
                }
                enum "option82-remote-and-circuit-id" {
                  value 3;
                  description
                    "Specifies a character string that is a combination of the remote-id and circuit-id in the DHCP Option82 field as the user name in MAC address authentication.";
                }
              }
              must "../dhcp-option-password";
              description
                "Specifies the name of the MAC address authentication user to a specified DHCP option.";
            }
            leaf separate {
              type string {
                length "1";
              }
              must "../dhcp-option-format";
              description
                "Specifies the delimiter in the user name for MAC address authentication.";
            }
            leaf code-format {
              type enumeration {
                enum "format-hex" {
                  value 0;
                  description
                    "Hexadecimal format.";
                }
              }
              must "../dhcp-option-format";
              description
                "Indicates that the user name for MAC address authentication is in hexadecimal format.";
            }
            leaf dhcp-option-password {
              type pub-type:password-extend {
                length "1..268";
              }
              must "../dhcp-option-format";
              description
                "The password is a string ranging from 1 to 128 characters for a plain text password and 128 to 268 characters for a cipher text password.";
            }
          }
        }
        container mac-re-authenticate {
          description
            "Configure MAC re-authenticate parameters.";
          leaf re-authenticate {
            type boolean;
            default "false";
            description
              "Enable/disable re-authentication for online MAC address authentication users.";
          }
          leaf re-authenticate-period {
            type uint16 {
              range "1..65535";
            }
            units "s";
            default "3600";
            description
              "Specifies the interval for re-authenticating online MAC address authentication users.";
          }
          leaf re-authenticate-dhcp-renew {
            type boolean;
            default "false";
            description
              "Enable/disable the device to re-authenticate the users when receiving DHCP lease renewal packets from MAC address authentication users.";
          }
        }
        container permit-mac-authenticates {
          description
            "List of the MAC address range allowed for MAC address authentication.";
          list permit-mac-authenticate {
            key "mac";
            description
              "Configure the MAC address range allowed for MAC address authentication list.";
            leaf mac {
              type pub-type:mac-address {
                pattern
                  '[0-9a-f][02468ace][0-9a-f]{2}(-[0-9a-f]{4}){2}';
              }
              description
                "Specifies a MAC address for MAC address authentication.";
            }
            choice subnet {
              mandatory true;
              description
                "The subnet choice.";
              case mask-length {
                description
                  "Mask length case.";
                leaf prefix-length {
                  type uint8 {
                    range "0..48";
                  }
                  description
                    "Specifies the MAC address mask length.";
                }
              }
              case mask-address {
                description
                  "Mask address case.";
                leaf net-mask {
                  type pub-type:mac-address {
                    pattern
                      '(([8cef][0]{3}|[f][8cef][0]{2}|[f]{2}[8cef][0]|[f]{3}[8cef])(-[0]{4}){2})|([f]{4}(-([8cef][0]{3}|[f][8cef][0]{2}|[f]{2}[8cef][0]|[f]{3}[8cef]))(-[0]{4}){1})|([f]{4}(-[f]{4})(-([8cef][0]{3}|[f][8cef][0]{2}|[f]{2}[8cef][0]|[f]{3}[8cef])))';
                  }
                  description
                    "Specifies the MAC address mask.";
                }
              }
            }
          }
        }
      }
    }
  }
}
