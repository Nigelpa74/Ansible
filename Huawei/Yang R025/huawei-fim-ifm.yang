/*
Copyright (C) 2020-2025 Huawei Technologies Co., Ltd. All rights reserved.
*/
module huawei-fim-ifm {
  namespace "urn:huawei:yang:huawei-fim-ifm";
  prefix fim-ifm;
  import huawei-pub-type {
    prefix pub-type;
  }
  import huawei-ifm {
    prefix ifm;
  }
  import huawei-extension {
    prefix ext;
  }
  import huawei-ethernet {
    prefix ethernet;
  }
  import huawei-ifm-trunk {
    prefix ifm-trunk;
  }
  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";
  reference
    "Huawei private.";
  revision 2025-08-11 {
    description
      "Tcpv6-mss must condition modify.";
    reference
      "Huawei private.";
  }
  revision 2025-08-01 {
    description
      "Add trunkmem-trigger-down-time and add ve channel info.";
    reference
      "Huawei private.";
  }
  revision 2025-01-26 {
    description
      "Remove the support for tcp6 mss on the cellular interface.";
    reference
      "Huawei private.";
  }
  revision 2024-10-12 {
    description
      "Fix word spelling errors in description statements.";
    reference
      "Huawei private.";
  }
  revision 2024-08-08 {
    description
      "Add ve-mode-type new enum loopback-enhance and add eai down-time.";
    reference
      "Huawei private.";
  }
  revision 2024-06-07 {
    description
      "Add GVE energy-saving and add trunk link-map and add interface 800GE and add eai fault-detection status query.";
    reference
      "Huawei private.";
  }
  revision 2024-03-12 {
    description
      "Change to eai-fault-detection.";
    reference
      "Huawei private.";
  }
  revision 2024-03-07 {
    description
      "Change tcp-mss and mru must condition.";
    reference
      "Huawei private.";
  }
  revision 2024-02-21 {
    description
      "Add Interface 50-100GE.";
    reference
      "Huawei private.";
  }
  revision 2023-10-18 {
    description
      "Add Leaf traffic-fast-switchover.";
    reference
      "Huawei private.";
  }
  revision 2023-08-11 {
    description
      "Add Leaf pst-board-fast-switch.";
    reference
      "Huawei private.";
  }
  revision 2023-03-23 {
    description
      "Change Leaf statistic-accelerate Type.";
    reference
      "Huawei private.";
  }
  revision 2023-03-03 {
    description
      "Add Leaf statistic-accelerate.";
    reference
      "Huawei private.";
  }
  revision 2023-01-20 {
    description
      "Change when to positive.";
    reference
      "Huawei private.";
  }
  revision 2022-11-29 {
    description
      "PW-VE does not support tcp-mss.";
    reference
      "Huawei private.";
  }
  revision 2022-11-28 {
    description
      "GVE and VE support statistic-mode.";
    reference
      "Huawei private.";
  }
  revision 2022-08-24 {
    description
      "Add interface 1200GE.";
    reference
      "Huawei private.";
  }
  revision 2022-03-19 {
    description
      "Qinq support mode-channel.";
    reference
      "Huawei private.";
  }
  revision 2022-03-14 {
    description
      "Add mode channel.";
    reference
      "Huawei private.";
  }
  revision 2022-02-14 {
    description
      "Add slice main.";
    reference
      "Huawei private.";
  }
  revision 2021-07-15 {
    description
      "Add tcp6 mss.";
    reference
      "Huawei private.";
  }
  revision 2020-03-23 {
    description
      "Initial revision.";
    reference
      "Huawei private.";
  }
  ext:task-name "forwarding";
  typedef enable-type {
    type enumeration {
      enum "disable" {
        value 0;
        description
          "Disable.";
      }
      enum "enable" {
        value 1;
        description
          "Enable.";
      }
    }
    description
      "Enable type.";
  }
  typedef statistic-mode-type {
    type enumeration {
      enum "forward" {
        value 1;
        description
          "Forward mode statistics.";
      }
      enum "mac" {
        value 0;
        description
          "MAC mode statistics.";
      }
    }
    description
      "Ip Statistic Mode Type.";
  }
  typedef ve-mode-type {
    type enumeration {
      enum "through" {
        value 1;
        description
          "Software loopback.";
      }
      enum "loopback" {
        value 0;
        description
          "Hardware loopback.";
      }
      enum "half-through" {
        value 3;
        description
          "Software switch hardware loopback.";
      }
      enum "loopback-enhance" {
        value 4;
        description
          "Hardware loopback enhance.";
      }
    }
    description
      "VE Forward Mode Type.";
  }
  typedef ve-interface-type {
    type enumeration {
      enum "L2VE" {
        value 1;
        description
          "Layer 2 Terminate Virtual-Ethernet interface.";
      }
      enum "L3VE" {
        value 2;
        description
          "Layer 3 Access Virtual-Ethernet interface.";
      }
      enum "terminate-ve" {
        value 7;
        description
          "Layer 3 Terminate Virtual-Ethernet interface.";
      }
    }
    description
      "VE Interface Type.";
  }
  typedef local-forward-type {
    type enumeration {
      enum "unicast" {
        value 1;
        description
          "Unicast Local Forward.";
      }
    }
    description
      "Trunk Local Forward Type.";
  }
  typedef reset-ipversion-type {
    type enumeration {
      enum "ipv4" {
        value 1;
        description
          "IPv4 reset.";
      }
      enum "ipv6" {
        value 2;
        description
          "IPv6 reset.";
      }
    }
    description
      "Reset IP version type.";
  }

  typedef reset-dispcard-type {
    type enumeration {
      enum "mac" {
        value 1;
        description
          "MAC reset.";
      }
      enum "mtu" {
        value 2;
        description
          "MTU reset.";
      }
    }
    description
      "Reset discard version type.";
  }
  typedef eai-fault-status-type {
    type enumeration {
      enum "wait-to-protect" {
        value 0;
        description
          "Wait to protect.";
      }
      enum "protection-detecting" {
        value 1;
        description
          "Protection detecting.";
      }
      enum "protection-actived" {
        value 2;
        description
          "Protection actived.";
      }
    }
    description
      "Eai fault status type.";
  }
  rpc rst-macmtu-intf {
    description
      "Clear MAC and MTU error statistics.";
    ext:node-ref "/ifm/interfaces/interface";
    input {
      leaf interface-name {
        type string {
          length "1..63";
        }
        mandatory true;
        description
          "Interface name.";
      }
      leaf discard-type {
        type reset-dispcard-type;
        description
          "Configure the discard type.";
      }
      leaf ip-version {
        type reset-ipversion-type;
        description
          "Configure the discard IP version.";
      }
    }
  }
  rpc rst-macmtu-slot {
    description
      "Clear MAC&MTU error statistics.";
    ext:node-ref "/ifm/interfaces/interface";
    input {
      leaf board-position {
        type string {
          length "1..32";
        }
        mandatory true;
        description
          "Board position.";
      }
      leaf discard-type {
        type reset-dispcard-type;
        description
          "Configure the discard type.";
      }
      leaf ip-version {
        type reset-ipversion-type;
        description
          "Configure the discard IP version.";
      }
    }
  }
  rpc rst-mru-discard {
    description
      "Clear interface MRU discard statistics.";
    ext:node-ref "/ifm/interfaces/interface";
    input {
      leaf interface-name {
        type string {
          length "1..63";
        }
        mandatory true;
        description
          "Interface name of clear interface MRU discard statistics.";
      }
    }
  }
  augment "/ifm:ifm/ifm:interfaces/ifm:interface" {
      description
        "Interface forward configuration to the interface management module.";
    container fim {
      description
        "Configure the function of statistic to main interface.";
      leaf statistic-enable {
        when "../../ifm:class='main-interface' and (../../ifm:type='Ip-Trunk' or ../../ifm:type='Pos' or ../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet')";
        type enable-type;
        default "disable";
        description
          "Enable the function of traffic statistics.";
      }
      leaf statistic-mode {
        when "(../../ifm:class='sub-interface' and ../../ifm:type='PW-VE') or ../../ifm:type='Virtual-Ethernet' or ../../ifm:type='Global-VE' or ../../ifm:type='Ip-Trunk' or ../../ifm:type='Vbdif' or ../../ifm:type='Vlanif' or ../../ifm:type='Pos' or ../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet'";
        type statistic-mode-type;
        default "mac";
        description
          "Configure the traffic statistics mode.";
      }
      leaf mac-statistic-enable {
        when "../../ifm:class='main-interface' and (../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet')";
        type enable-type;
        default "disable";
        description
          "Enable the function of bit per seconds (bps) statistics.";
      }
      leaf statistic-accelerate {
        when "../../ifm:class='main-interface' and (../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet')";
        type empty;
        description
          "Enable the function of traffic statistics accelerate.";
      }
    }
    container fim-ifm-mru {
      description
        "Configure the maximum receive unit.";
      leaf mru {
        when "(../../ifm:class='sub-interface' and (../../ifm:type='Virtual-Ethernet' or ../../ifm:type='Global-VE')) or (../../ifm:type='Vlanif' or ../../ifm:type='Vbdif' or ../../ifm:type='PW-VE' or ../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet')";
        type uint16 {
          range "46..9600";
        }
        units "Byte";
        must "(not(../../fim-ifm:fim-tcp-mss/fim-ifm:tcp-mss) and not(../../fim-ifm:fim-tcp6-mss/fim-ifm:tcp6-mss))";
        description
          "Maximum receive unit of an interface.";
      }
      leaf mru-statistic-enable {
        when "../mru";
        type enable-type;
        default "disable";
        description
          "Enable discard statistics of maximum receive unit of an interface.";
      }
    }
    container fim-tcp-mss{
      description
        "Configure Tcp mss.";
      leaf tcp-mss {
        when "../../ifm:type='Vlanif' or ../../ifm:type='Pos' or ../../ifm:type='Vbdif' or ../../ifm:type='GigabitEthernet' or ../../ifm:type='XGigabitEthernet' or ../../ifm:type='FlexE' or ../../ifm:type='Eth-Trunk' or ../../ifm:type='10GE' or ../../ifm:type='25GE' or ../../ifm:type='40GE' or ../../ifm:type='50GE' or ../../ifm:type='50|100GE' or ../../ifm:type='50-100GE' or ../../ifm:type='100GE' or ../../ifm:type='200GE' or ../../ifm:type='400GE' or ../../ifm:type='800GE' or ../../ifm:type='1200GE' or ../../ifm:type='Ethernet'";
        type uint16 {
          range "32..9500";
        }
        units "Byte";
        must "(not(../../ethernet:ethernet/ethernet:main-interface/ethernet:l2-attribute) and not(../../fim-ifm:fim-ifm-mru/fim-ifm:mru))";
        description
          "Maximum Segment Size of an interface.";
      }
    }
    container fim-tcp6-mss{
      description
        "Configure Tcp6 mss.";
      leaf tcp6-mss {
        when "../../ifm:type!='Virtual-Ethernet' and ../../ifm:type!='NULL' and ../../ifm:type!='LoopBack' and ../../ifm:type!='Global-VE' and ../../ifm:type!='Nve' and ../../ifm:type!='FlexE-200GE' and ../../ifm:type!='FlexE-50G' and ../../ifm:type!='FlexE-100G' and ../../ifm:type!='FlexE-10G' and ../../ifm:type!='FlexE-400G' and ../../ifm:type!='FlexE-50|100G' and ../../ifm:type!='FlexE-50-100G' and ../../ifm:type!='Cellular'";
        type uint16 {
          range "32..9500";
        }
        units "Byte";
        must "(not(../../ethernet:ethernet/ethernet:main-interface/ethernet:l2-attribute) and not(../../fim-ifm:fim-ifm-mru/fim-ifm:mru))";
        description
          "Maximum Segment Size of an interface.";
      }
    }
    container fim-ifm-bdifint{
      when "../ifm:type='Vbdif'";
      description
        "Configure forward configurations to VBDIF interface.";
      leaf vbdif-loopback-enable {
        type boolean;
        default "false";
        description
          "Enable/disable the VBDIF loopback forward mode.";
      }
    }
    container fim-ifm-veint{
      description
        "Configure Virtual-Ethernet interface information.";
      leaf ve-forward-mode {
        when "(../../ifm:type='Virtual-Ethernet' and ../../fim-ifm:ve-group/fim-ifm:type='L2VE') or (../../ifm:type='Global-VE' and ../../fim-ifm:ve-group/fim-ifm:type='L2VE')";
        type ve-mode-type;
        default "loopback";
        description
          "Virtual-Ethernet forward mode type.";
      }
      leaf ve-slot-id {
        when "../../ifm:type='Global-VE' and ../../fim-ifm:ve-group/fim-ifm:type='L2VE'";
        type string {
          length "1..512";
        }
        description
          "Remove boards from a global VE interface.";
      }
    }
    container ve-group {
      when "../ifm:type='Virtual-Ethernet' or ../ifm:type='Global-VE'";
      presence "configure ve-group.";
      description
        "Enable/disable a Virtual-Ethernet Group.";
      leaf type {
        type ve-interface-type;
        mandatory true;
        description
          "Virtual-Ethernet interface type.";
        ext:operation-exclude update {
          description "The node cannot be modified when ve-group is configured.";
        }
      }
      leaf id {
        type uint32 {
          range "1..8192";
        }
        mandatory true;
        description
          "Virtual-Ethernet group ID.";
        ext:operation-exclude update {
          description "The node cannot be modified when ve-group is configured.";
        }
      }
    }
    container mode-channel {
      when "../ifm:class='sub-interface' and (../ethernet:ethernet/ethernet:l3-sub-interface/ethernet:vlan-type-dot1q or ../ethernet:ethernet/ethernet:l3-sub-interface/ethernet:qinq-termination or ../ifm:link-protocol='fr')";
      description
        "Configure the mode Channel sub-interface.";
      leaf mode-channel-enable {
        type enable-type;
        default "disable";
        description
          "Enable or disable mode channel sub-interface.";
      }
      leaf bandwidth {
        when "../mode-channel-enable='enable'";
        type uint32 {
          range "2..1000000000";
        }
        units "Mbit/s";
        default "2";
        description
          "Specify bandwidth of an mode channel sub-interface (Mbit/s).";
      }
    }
    container mru-discard-statistic {
      config false;
      description
        "Statistics of maximum receive unit of an interface.";
      leaf packet {
        type uint64;
        description
          "Display the packets of discarded statistics of maximum receive unit of an interface.";
      }
      leaf byte {
        type uint64;
        units "Byte";
        description
          "Display the bytes of discarded statistics of maximum receive unit of an interface.";
      }
    }
    container macmtu-discard-stat {
      config false;
      description
        "MAC&MTU error statistics.";
      leaf mtu-ipv4 {
        type uint64;
        description
          "IPv4 MTU error statistics.";
      }
      leaf mtu-ipv6 {
        type uint64;
        description
          "IPv6 MTU error statistics.";
      }
      leaf mac-ipv4 {
        type uint64;
        default "0";
        description
          "IPv4 MAC error statistics.";
      }
      leaf mac-ipv6 {
        type uint64;
        description
          "IPv6 MAC error statistics.";
      }
    }
    container slice-main {
      when "(count(/ifm:ifm/ifm:interfaces/ifm:interface/ifm-trunk:trunk/ifm-trunk:members/ifm-trunk:member[ifm-trunk:name=current()/../ifm:name])=0) and (../ifm:type='GigabitEthernet' or ../ifm:type='XGigabitEthernet' or ../ifm:type='FlexE' or ../ifm:type='Eth-Trunk' or ../ifm:type='10GE' or ../ifm:type='25GE' or ../ifm:type='40GE' or ../ifm:type='50GE' or ../ifm:type='50|100GE' or ../ifm:type='50-100GE' or ../ifm:type='100GE' or ../ifm:type='200GE' or ../ifm:type='400GE' or ../ifm:type='800GE' or ../ifm:type='1200GE' or ../ifm:type='Ethernet' or (../ifm:type='Pos' and ../ifm:link-protocol='fr'))";
      config false;
      description
        "Statistics of the main interface that supports sliced sub-interfaces.";
      leaf remain-bandwidth {
      type uint32;
      units "Mbit/s";
      description
        "Remaining bandwidth of the main interface.";
      }
      leaf remain-in-bit-rate {
      type uint64;
      units "bit/s";
      description
        "Remaining rate at which bits are received within the interval.";
      }
      leaf remain-out-bit-rate {
      type uint64;
      units "bit/s";
      description
        "Remaining rate at which bits are sent within the interval.";
      }
    }
    container eai-fault-detection {
      when "../ifm:class='main-interface' and (../ifm:type='GigabitEthernet' or ../ifm:type='XGigabitEthernet' or ../ifm:type='10GE' or ../ifm:type='25GE' or ../ifm:type='40GE' or ../ifm:type='50GE' or ../ifm:type='50|100GE' or ../ifm:type='50-100GE' or ../ifm:type='100GE' or ../ifm:type='200GE' or ../ifm:type='400GE' or ../ifm:type='800GE' or ../ifm:type='1200GE' or ../ifm:type='Ethernet')";
      presence "Configure eai fault detection.";
      description
        "Configure eai fault detection.";
      leaf detect-cycle {
        type uint32 {
          range "3..255";
        }
        default "3";
        description
          "Fast detection period.";
      }
      leaf start-protect-threshold {
        type uint32 {
          range "20..100000";
        }
        units "kpps";
        default "30";
        description
          "Threshold for the packet rate for starting link protection. When the measured traffic is greater than this threshold, the link is considered as having traffic.";
      }
      leaf stop-protect-threshold {
        type uint32 {
          range "10..50000";
        }
        units "kpps";
        must "../start-protect-threshold >= ../stop-protect-threshold * 2";
        default "10";
        description
          "Threshold for the packet rate for stopping link protection. When the collected traffic is less than the threshold, the link is considered as having no traffic.";
      }
      leaf wait-to-start {
        type uint32 {
          range "1000..15000";
        }
        units "ms";
        default "3000";
        description
          "Interval between two switchings.";
      }
      leaf status {
        type eai-fault-status-type;
        config false;
        description
          "Eai fault detection status.";
      }
      leaf down-time {
        type uint32 {
          range "180..1000";
        }
        units "ms";
        default "200";
        description
          "Duration of the down state.";
      }
    }
    container trunk-link-map {
      description
        "Configure the function of link-map for trunk sub-interfaces.";
      choice link-map-type {
        description
          "The type of link-map for trunk sub-interfaces.";
        case link-map-auto {
          description
            "Auto configure the function of link-map for trunk sub-interfaces.";
            leaf auto {
              when "../../ifm:class='sub-interface' and ../../ifm:type='Eth-Trunk'";
              type empty;
              description
                "Configure the function of link-map-auto for trunk sub-interfaces.";
            }
        }
      }
      leaf selected-member {
        type pub-type:if-name;
        config false;
        description
          "Selected member of Eth-Trunk sub-interfaces link-map.";
      }
    }
    container ve-channel-info {
      when "../ifm:class='main-interface' and ../ifm:type='Virtual-Ethernet'";
      config false;
      description
        "Statistics of the channel information of Virtual-Ethernet.";
      leaf tm-id {
        type uint32;
        description
          "Tm id of the Virtual-Ethernet.";
      }
      leaf channel {
        type uint32;
        description
          "Channel of the Virtual-Ethernet.";
      }
    }
  }
  augment "/ifm:ifm/ifm:global" {
      description
        "Global configuration to the interface management module.";
    container fim-ifm-global {
      description
        "Configure FIM global configurations.";
      leaf global-strict-filter {
        type enable-type;
        default "disable";
        description
          "Global filter enable status.";
      }
      leaf dual-stat-enable {
        type enable-type;
        default "disable";
        description
          "Set forward mode statistic for all interfaces.";
      }
      leaf trunk-delaysend-time {
        type uint32 {
          range "1000..300000";
        }
        units "ms";
        default 1500;
        description
          "Configure the delay time for an ETH-Trunk interface to join a member interface in a unicast scenario.";
      }
      leaf trunk-adjust-enable {
        type enable-type;
        default "disable";
        description
          "Enable the function of trunk load-balance dynamic-adjust.";
      }
      leaf qinq-transport-enable {
        type enable-type;
        default "disable";
        description
          "Configures Ethernet interfaces to retain the outer TPID EtherType value in received QinQ packets.";
      }
      leaf pst-board-fast-switch {
        type enable-type;
        default "enable";
        description
          "Configure inter-board heartbeat association with PST.";
      }
      leaf gve-energy-saving {
        type enable-type;
        default "disable";
        description
          "Global-VE energy-saving enable.";
      }
      leaf trunkmem-trigger-down-time {
        type uint32 {
          range "0..10";
        }
        units "min";
        default 5;
        description
          "Configure the maximum recovery time for trigger-down of a trunk member interface.";
      }
    }
    container fim-trunk-localfwd {
      description
        "Configure the function of trunk local forward.";
      leaf enable {
        type enable-type;
        default "disable";
        description
          "Trunk Local Forward enable status.";
      }
    }
    container ve-groups {
      config false;
      description
      "List of the relation of Virtual-Ethernet and ve-group.";
      list ve-group {
        key "ve-group-id slot-id";
        description
          "Operational state of the relation of Virtual-Ethernet and ve-group.";
        leaf ve-group-id {
          type uint32;
          description
            "VE-group id.";
        }
        leaf slot-id {
          type string {
            length "1..24";
          }
          description
            "Slot ID.";
        }
        leaf l2-ve-ifname {
          type pub-type:if-name;
          description
            "Terminate Virtual-Ethernet interface.";
        }
        leaf l3-ve-ifname {
          type pub-type:if-name;
          description
            "Access Virtual-Ethernet interface.";
        }
      }
    }
  }
}
