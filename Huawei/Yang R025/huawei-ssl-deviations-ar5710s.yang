/*
Copyright (C) 2025 Huawei Technologies Co., Ltd. All rights reserved.
*/
module huawei-ssl-deviations-ar5710s {
  namespace "urn:huawei:yang:huawei-ssl-deviations-ar5710s";
  prefix ssl-devs-ar5710s;

  import huawei-ssl {
    prefix ssl;
  }

  organization
    "Huawei Technologies Co., Ltd.";
  contact
    "Huawei Industrial Base
     Bantian, Longgang
     Shenzhen 518129
     People's Republic of China
     Website: http://www.huawei.com
     Email: support@huawei.com";
  description
    "This module defines deviation statements for huawei-ssl module.";

  revision 2025-02-24 {
    description
      "Initial revision.";
    reference "Huawei private.";
  }

  typedef ssl-version-deviations {
    type enumeration {
      enum tls1.1 {
        value 3;
        description
          "SSL version tls1.1.";
      }
      enum tls1.2 {
        value 4;
        description
          "SSL version tls1.2.";
      }
      enum tls1.3 {
        value 5;
        description
          "SSL version tls1.3.";
      }
    }
    description
      "SSL version type list.";
  }

  deviation "/ssl:ssl/ssl:ssl-policys/ssl:ssl-policy/ssl:ecdh-group/ssl:pqc-x25519-mlkem" {
    deviate not-supported;
  }
  deviation "/ssl:ssl/ssl:ssl-policys/ssl:ssl-policy/ssl:cert-loads/ssl:cert-load/ssl:is-cert-file-encrypted" {
    deviate not-supported;
  }
  deviation "/ssl:ssl/ssl:ssl-policys/ssl:ssl-policy/ssl:mini-version" {
    deviate replace {
      type ssl-devs-ar5710s:ssl-version-deviations;
    }
  }
  deviation "/ssl:ssl/ssl:ssl-policys/ssl:ssl-policy/ssl:ecdh-group" {
    deviate delete {
      must "not (./nist='false' and ./curve='false' and ./brainpool='false' and ./pqc-kyber='false' and ./ffdhe='false' and ./curve-sm2='false' and ./pqc-x25519-mlkem='false')";
    }
    deviate add {
      must "not (./nist='false' and ./curve='false' and ./brainpool='false' and ./pqc-kyber='false' and ./ffdhe='false' and ./curve-sm2='false')";
    }
  }
  deviation "/ssl:ssl/ssl:ssl-policys/ssl:ssl-policy/ssl:ecdh-group/ssl:nist" {
    deviate replace {
      default "true";
    }
  }
  deviation "/ssl:ssl/ssl:ssl-policys/ssl:ssl-policy/ssl:signature-alg/ssl:ecdsa-secp256r1-sha256" {
    deviate replace {
      default "true";
    }
  }
  deviation "/ssl:ssl/ssl:ssl-policys/ssl:ssl-policy/ssl:signature-alg/ssl:ecdsa-secp384r1-sha384" {
    deviate replace {
      default "true";
    }
  }
  deviation "/ssl:ssl/ssl:ssl-policys/ssl:ssl-policy/ssl:signature-alg/ssl:ecdsa-secp521r1-sha512" {
    deviate replace {
      default "true";
    }
  }
}
