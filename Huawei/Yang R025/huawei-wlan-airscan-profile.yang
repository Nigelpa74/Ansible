/*
Copyright (C) 2022-2024 Huawei Technologies Co., Ltd. All rights reserved.
*/
module huawei-wlan-airscan-profile {
  yang-version 1;
  namespace "urn:huawei:yang:huawei-wlan-airscan-profile";
  prefix airscan-prof;
  import huawei-extension {
    prefix ext;
  }
  import huawei-wlan-radio-2g-profile {
    prefix radio-2g-prof;
  }
  import huawei-wlan-radio-5g-profile {
    prefix radio-5g-prof;
  }
  organization
    "Huawei Technologies Co., Ltd.";
  contact
    "Huawei Industrial Base
     Bantian, Longgang
     Shenzhen 518129
     People's Republic of China
     Website: http://www.huawei.com
     Email: support@huawei.com";
  description
    "Air scan profile configuration service package.";
  revision 2024-05-14 {
    description
      "The default profile cannot be deleted.";
    reference
      "Huawei private.";
  }
  revision 2024-03-19 {
    description
      "Update profile name pattern.";
    reference
      "Huawei private.";
  }
  revision 2024-03-08 {
    description
      "Add profile name pattern.";
    reference
      "Huawei private.";
  }
  revision 2022-12-19 {
    description
      "Add the scan, scan-channel-set, scan-interval, scan-period set.";
    reference
      "Huawei private.";
  }
  revision 2022-08-06 {
    description
      "Initial revision.";
    reference
      "Huawei private.";
  }
  grouping radio-2g-binding-airscan {
    description
      "Configure airscan profile to radio-2g profile.";
    container radio-2g-profile-binding-airscan {
      leaf binding-airscan-profile {
        type leafref {
          path "/airscan-prof:wlan-airscan-profile/airscan-prof:airscan-profiles/airscan-prof:airscan-profile/airscan-prof:profile-name";
        }
        default "default";
        description
          "Binding airscan profile to radio 2g profile.";
      }
      description
        "Configure airscan profile to radio 2g profile.";
    }
  }
  grouping radio-5g-binding-airscan {
    description
      "Configure airscan profile to radio-5g profile.";
    container radio-5g-profile-binding-airscan {
      leaf binding-airscan-profile {
        type leafref {
          path "/airscan-prof:wlan-airscan-profile/airscan-prof:airscan-profiles/airscan-prof:airscan-profile/airscan-prof:profile-name";
        }
        default "default";
        description
          "Binding airscan profile to radio 5g profile.";
      }
      description
        "Configure airscan profile to radio 5g profile.";
    }
  }
  container wlan-airscan-profile {
    description
      "Configure the airscan profile.";
    container airscan-profiles {
      description
        "List of the airscan profiles.";
      list airscan-profile {
        ext:generated-by "system" {
          description
            "The default profile is generated by system.";
          ext:filter "profile-name='default'";
        }
        ext:operation-exclude "delete" {
          ext:filter "profile-name='default'";
          description
            "The default profile cannot be deleted.";
        }
        key "profile-name";
        leaf profile-name {
          type string {
            length "1..35";
		    pattern '[^\s?]+';
            pattern '[!-~]+';
          }
          description
            "Config airscan profile name.";
        }
		leaf scan {
          type enumeration {
            enum "disable" {
              value 0;
              description
                "Disable the scanning function.";
            }
            enum "enable" {
              value 1;
              description
                "Enable the scanning function.";
            }
          }
          default "enable";
          description
            "Enable or disable the scanning function.
             By default, the scanning function is enabled.";
        }
        leaf scan-enhancement {
          type enumeration {
            enum "disable" {
              value 0;
              description
                "Disable the scanning enhancement function.";
            }
            enum "enable" {
              value 1;
              description
                "Enable the scanning enhancement function.";
            }
          }
          default "disable";
          description
            "Enable or disable the scanning enhancement function.
             By default, the scanning enhancement function is disabled.";
        }
		leaf scan-channel-set {
          type enumeration {
            enum "country-channel" {
              value 0;
              description
                "Specifies an air scan channel set that contains all channels supported by the country code of an AP.";
            }
            enum "dca-channel" {
              value 1;
              description
                "Specifies a calibration channel set as the air scan channel set.";
            }
			enum "work-channel" {
              value 2;
              description
                "Specifies an air scan channel set that contains working channels of APs.";
            }
          }
          default "country-channel";
          description
            "Configure an air scan channel set.
             By default, an air scan channel set contains all channels supported by the country code of an AP.";
        }
		leaf scan-interval {
          type uint32 {
            range "300..600000";
          }
		  units "ms";
          default "10000";
          description
            "Set an air scan interval.
             By default, the air scan interval is 10000 ms.";
        }
		leaf scan-period {
          type uint32 {
            range "60..100";
          }
		  units "ms";
          default "60";
          description
            "Set an air scan period.
             By default, the air scan period is 60 ms.";
        }
        description
          "Configure the airscan profiles.";
      }
    }
  }
  augment "/radio-2g-prof:wlan-radio-2g-profile/radio-2g-prof:radio-2g-profiles/radio-2g-prof:radio-2g-profile" {
    description
      "Bind airscan-profile to radio-2g-profile.";
    uses radio-2g-binding-airscan;
  }
  augment "/radio-5g-prof:wlan-radio-5g-profile/radio-5g-prof:radio-5g-profiles/radio-5g-prof:radio-5g-profile" {
    description
      "Bind airscan-profile to radio-5g-profile.";
    uses radio-5g-binding-airscan {
      description
        "Bind airscan-profile to radio-5g-profile.";
    }
  }
  ext:task-name "wm";
}
