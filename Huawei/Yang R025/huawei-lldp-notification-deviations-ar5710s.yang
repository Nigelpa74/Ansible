/*
Copyright (C) 2025 Huawei Technologies Co., Ltd. All rights reserved.
*/
module huawei-lldp-notification-deviations-ar5710s {
  namespace "urn:huawei:yang:huawei-lldp-notification-deviations-ar5710s";
  prefix lldp-notification-devs-ar5710s;

  import huawei-lldp-notification {
    prefix lldp-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-lldp-notification module.";

  revision 2025-02-24 {
    description
      "Initial revision.";
    reference "Huawei private.";
  }

  deviation "/lldp-notification:lldp-neighbor-changed/lldp-notification:med-manufacturer-name" {
    deviate not-supported;
  }
  deviation "/lldp-notification:lldp-neighbor-changed/lldp-notification:med-model-name" {
    deviate not-supported;
  }
}
