/*
Copyright (C) 2019-2025 Huawei Technologies Co., Ltd. All rights reserved.
*/
submodule huawei-diagnostic-tools-type {
  yang-version 1;
  belongs-to huawei-diagnostic-tools {
    prefix diagnostic-tools;
  }
  organization
    "Huawei Technologies Co., Ltd.";
  contact
    "Huawei Industrial Base
     Bantian, Longgang
     Shenzhen 518129
     People's Republic of China
     Website: http://www.huawei.com
     Email: support@huawei.com";
  description
     "Diagnosis tool types.";

  revision 2025-02-13 {
    description
      "Modify wrong description.";
    reference
      "Huawei private.";
  }
  revision 2022-10-18 {
    description
      "Add path-detect-result-type.";
    reference
      "Huawei private.";
  }
  revision 2022-05-09 {
    description
      "Modify dgntl-evpn-vpws-tunnel-type name.";
    reference
      "Huawei private.";
  }
  revision 2022-04-27 {
    description
      "Modify dgntl-evpn-vpws-tunnel-type.";
    reference
      "Huawei private.";
  }
  revision 2022-03-10 {
    description
      "Add reply-mode-p2mp,ttl-flag-type, p2mp-transmit-type.";
    reference
      "Huawei private.";
  }
  revision 2022-02-28 {
    description
      "Modify reply-mode type for vpls-start-vsi-trace.";
    reference
      "Huawei private.";
  } 
  revision 2021-12-28 {
    description
      "Add dgntl-evpn-vpws-path-type and lspv-return-code.";
    reference
      "Huawei private.";
  }
  revision 2021-05-11 {
    description
      "Add pw-type, reply-mode-pwe3 and pwe3-label-type.";
    reference
      "Huawei private.";
  }
  revision 2021-01-11 {
    description
      "Add reply-mode-vpls-mac.";
    reference
      "Huawei private.";
  }
  revision 2020-07-04 {
    description
      "Add bit-string-len-type.";
    reference
      "Huawei private.";
  }

  revision 2019-12-12 {
    description
      "Add detail-result-type sr-version sr-be-version.";
    reference
      "Huawei private.";
  }
  revision 2019-04-09 {
    description
      "Initial revision.";
    reference
      "Huawei private.";
  }
  typedef dgntl-test-status-type {
    type enumeration {
      enum "processing" {
        value 0;
        description
          "The test is in progress.";
      }
      enum "finished" {
        value 1;
        description
          "The test is finished.";
      }
    }
    description
      "Description of dgntl-test-status-type.";
  }
  typedef dgntl-error-type {
    type enumeration {
      enum "success" {
        value 0;
        description
          "The test succeeded.";
      }
      enum "failed" {
        value 1;
        description
          "The test failed.";
      }
    }
    description
      "Description of dgntl-error-type.";
  } 
  typedef detail-result-type {
    type enumeration {
      enum "success" {
        value 0;
        description
          "The test succeeded.";
      }
      enum "timeout" {
        value 1;
        description
          "The test timeout.";
      }
      enum "failed" {
        value 2;
        description
          "The test failed.";
      }
    }
    description
      "Description of detail-result-type.";
  }
  
  typedef sr-version {
    type enumeration {
      enum "DRAFT2" {
        value 2;
        description
          "Draft2 version.";
      }
      enum "RFC8287" {
        value 3;
        description
          "Rfc8287 version.";
      }
    }
    description
      "Description of sr-version.";
  }
  typedef sr-be-version {
    type enumeration {
      enum "DRAFT2" {
        value 2;
        description
          "Draft2 version.";
      }
    }
    description
      "Description of sr-be-version.";
  }

  typedef transmit-type {
    type enumeration {
      enum "ingress" {
        value 1;
        description
          "Ingress.";
      }
      enum "transit" {
        value 2;
        description
          "Transit node.";
      }
      enum "egress" {
        value 3;
        description
          "Egress.";
      }
    }
    description
      "Description of transmit-type.";
  }
  typedef probe-result-type {
    type enumeration {
      enum "success" {
        value 0;
        description
          "The test succeeded.";
      }
      enum "timeout" {
        value 1;
        description
          "Timeout.";
      }
      enum "failed" {
        value 2;
        description
          "The test failed.";
      }
    }
    description
      "Description of probe-result-type.";
  }
  typedef lsp-type {
    type enumeration {
      enum "te" {
        value 1;
        description
          "TE.";
      }
      enum "srte" {
        value 8;
        description
          "SR-TE.";
      }
      enum "srbe" {
        value 9;
        description
          "SR-BE.";
      }
    }
    description
      "Description of lsp-type.";
  }
  typedef dgntl-lsp-protocol-origin {
    type enumeration {
      enum "pecp" {
        value 10;
        description
          "Pcep.";
      }
      enum "bgp" {
        value 20;
        description
          "Bgp.";
      }
      enum "local" {
        value 30;
        description
          "Local.";
      }
      enum "unknown" {
        value 255;
        description
          "Unknown.";
      }
    }
    description
      "Description of dgntl-lsp-protocol-origin.";
  }
  typedef reply-mode-evpn {
    type enumeration {
      enum "no-reply" {
        value 1;
        description
          "No reply.";
      }
      enum "udp" {
        value 2;
        description
          "UDP.";
      }
      enum "router-alert" {
        value 3;
        description
          "Router-Alert.";
      }
      enum "level-control-channel" {
        value 4;
        description
          "Level-Control-Channel.";
      }
    }
    description
      "Description of reply-mode-evpn.";
  }
  typedef ttl-mode {
    type enumeration {
      enum "uniform" {
        value 1;
        description
          "Uniform.";
      }
      enum "pipe" {
        value 2;
        description
          "Pipe.";
      }
    }
    description
      "Description of ttl-mode.";
  }
  typedef ttl-mode-type {
    type enumeration {
      enum "uniform" {
        value 0;
        description
          "Uniform.";
      }
      enum "pipe" {
        value 1;
        description
          "Pipe.";
      }
    }
    description
      "Description of ttl-mode.";
  }
  typedef trace-ttl-mode {
    type enumeration {
      enum "pipe" {
        value 1;
        description
          "Pipe.";
      }
    }
    description
      "Description of ttl-mode.";
  }
  typedef dgntl-sr-policy-path-type {
    type enumeration {
      enum "unknown" {
        value 0;
        description
          "Unknown.";
      }
      enum "primary" {
        value 1;
        description
          "Primary.";
      }
      enum "backup" {
        value 2;
        description
          "Backup.";
      }
    }
    description
      "Description of dgntl-sr-policy-path-type.";
  }

  typedef reply-mode-te {
    type enumeration {
      enum no-reply {
        value 1;
        description
          "No reply.";
      }
      enum udp {
        value 2;
        description
          "Reply with an IPv4/IPv6 UDP packet.";
      }
      enum level-control-channel {
        value 4;
        description
          "Reply via application level control channel.";
      }
    }
    description
      "Description of reply-mode-te.";
  }  
  typedef reply-mode-auto-te {
    type enumeration {
      enum no-reply {
        value 1;
        description
          "No reply.";
      }
      enum udp {
        value 2;
        description
          "Reply with an IPv4/IPv6 UDP packet.";
      }
    }
    description
      "Description of reply-mode-auto-te.";
  }  

  typedef reply-mode-ip {
    type enumeration {
      enum no-reply {
        value 1;
        description
          "No reply.";
      }
      enum udp {
        value 2;
        description
          "Reply with an IPv4/IPv6 UDP packet.";
      }
    }
    description
      "Description of reply-mode-ip.";
  }

  typedef reply-mode-bgp {
    type enumeration {
      enum no-reply {
        value 1;
        description
          "No reply.";
      }
      enum udp {
        value 2;
        description
          "Reply with an IPv4/IPv6 UDP packet.";
      }
    }
    description
      "Description of reply-mode-bgp.";
  }

  typedef reply-mode-srbe {
    type enumeration {
      enum no-reply {
        value 1;
        description
          "No reply.";
      }
      enum udp {
        value 2;
        description
          "Reply with an IPv4/IPv6 UDP packet.";
      }
    }
    description
      "Description of reply-mode-srbe.";
  }

  typedef reply-mode-vpn {
    type enumeration {
      enum no-reply {
        value 1;
        description
          "No reply.";
      }
    }
    description
      "Description of reply-mode-vpn.";
  }

  typedef reply-mode-srte {
    type enumeration {
      enum no-reply {
        value 1;
        description
          "No reply.";
      }
      enum udp {
        value 2;
        description
          "Reply with an IPv4/IPv6 UDP packet.";
      }
      enum level-control-channel {
        value 4;
        description
          "Reply via application level control channel.";
      }
    }
    description
      "Description of reply-mode-srte.";
  }

  typedef lsp-path {
    type enumeration {
      enum working-path {
        value 0;
        description
          "The working path.";
      }
      enum hot-standby {
        value 2;
        description
          "The hot standby path.";
      }
      enum "primary" {
        value 3;
        description
          "Primary.";
      }
    }
    description
      "Description of lsp-path.";
  }

  typedef lsp-remote-fec-type {
    type enumeration {
      enum LDP {
        value 1;
        description
          "Specify LDP LSP.";
      }
      enum NIL {
        value 2;
        description
          "Specify nil fec.";
      }
    }
    description
      "Description of lsp-remote-fec-type.";
  }
  typedef lsptrace-remote-fec-type {
    type enumeration {
      enum LDP {
        value 1;
        description
          "Specify LDP LSP.";
      }
    }
    description
      "Description of lsptrace-remote-fec-type.";
  }

  typedef vxlan-reply-mode {
    type enumeration {
      enum no-reply {
        value 1;
        description
          "No reply.";
      }
      enum udp {
        value 2;
        description
          "Reply with an IPv4/IPv6 UDP packet.";
      }
      enum overlay-segment {
        value 3;
        description
          "Reply via Overlay Segment.";
      }
    }
    description
      "Description of vxlan-reply-mode.";
  }

  typedef bit-string-len-type {
    type enumeration {
      enum "bsl-64" {
        value 1;
        description
          "64 bit.";
      }
      enum "bsl-128" {
        value 2;
        description
          "128 bit.";
      }
      enum "bsl-256" {
        value 3;
        description
          "256 bit.";
      }
    }
    description
      "Description of bit-string-len-type.";
  } 
  typedef reply-mode-vpls-mac {
    type enumeration {
      enum no-reply {
        value 1;
        description
          "No reply.";
      }
      enum udp {
        value 2;
        description
          "Reply with an IPv4 UDP packet.";
      }
      enum udp-via-vpls {
        value 5;
        description
          "Reply via a VPLS IPv4 UDP packet.";
      }
    }
    description
      "Description of reply-mode-vpls-mac.";
  }
  typedef bierv6-return-code {
    type enumeration {
      enum no-return-code {
        value 0;
        description
          "No return code.";
      }
      enum malformed-echo {
        value 1;
        description
          "Malformed echo request received.";
      }
      enum unknown-tlv {
        value 2;
        description
          "One or more of the TLVs was not understood.";
      }
      enum only-bfer {
        value 3;
        description
          "Replying BFR is the only BFER in header bitstring.";
      }
      enum one-of-bfer {
        value 4;
        description
          "Replying BFR is one of the BFERs in header bitstring.";
      }
      enum packet-forward-success {
        value 5;
        description
          "Packet forwards success.";
      }
      enum invalid-multipath {
        value 6;
        description
          "Invalid multipath info request.";
      }
      enum forward-fail {
        value 8;
        description
          "No matching entry in forwarding table.";
      }
      enum si-mismatch {
        value 9;
        description
          "Set identifier mismatch.";
      }
      enum ddmap-mismatch {
        value 10;
        description
          "DDMAP mismatch.";
      }
    }
    description
      "Description of bierv6-return-code.";
  }
  typedef bier-transmit-type {
    type enumeration {
      enum "ingress" {
        value 1;
        description
          "Ingress node.";
      }
      enum "transit" {
        value 2;
        description
          "Transit node.";
      }
      enum "bud" {
        value 3;
        description
          "Bud node.";
      }
      enum "egress" {
        value 4;
        description
          "Egress node.";
      }
    }
    description
      "Description of bier-transmit-type.";
  }
  typedef pw-type {
    type enumeration {
      enum "atm-aal5-sdu" {
        value 2;
        description
          "ATM AAL5 SDU encapsulation.";
      }
      enum "atm-trans-cell" {
        value 3;
        description
          "ATM transparent cell transport.";
      }
      enum "vlan" {
        value 4;
        description
          "VLAN encapsulation.";
      }
      enum "ethernet" {
        value 5;
        description
          "Ethernet encapsulation.";
      }
      enum "hdlc" {
        value 6;
        description
          "HDLC encapsulation.";
      }
      enum "ppp" {
        value 7;
        description
          "PPP encapsulation.";
      }
      enum "atm-nto1-vcc" {
        value 9;
        description
          "ATM n-to-one VCC cell transport.";
      }
      enum "atm-nto1-vpc" {
        value 10;
        description
          "ATM n-to-one VPC cell transport.";
      }
      enum "ip-layer2" {
        value 11;
        description
          "IP-layer2 encapsulation.";
      }
      enum "atm-1to1-vcc" {
        value 12;
        description
          "ATM one-to-one VCC Cell Mode.";
      }
      enum "atm-1to1-vpc" {
        value 13;
        description
          "ATM one-to-one VPC Cell Mode.";
      }
      enum "cep" {
        value 16;
        description
          "CEP encapsulation.";
      }
      enum "satop-e1" {
        value 17;
        description
          "Structure-agnostic E1 over Packet.";
      }
      enum "cesopsn-basic" {
        value 21;
        description
          "CESoPSN basic mode.";
      }
      enum "ip-interworking" {
        value 64;
        description
          "MPLS L2VPN IP interworking.";
      }
    }
    description
      "Description of pw type.";
  }
  typedef reply-mode-pwe3 {
    type enumeration {
      enum "no-reply" {
        value 1;
        description
          "No reply.";
      }
      enum "udp" {
        value 2;
        description
          "Reply with an IPv4/IPv6 UDP packet.";
      }
      enum "level-control-channel" {
        value 4;
        description
          "Reply through an application level control channel.";
      }
    }
    description
      "Description of reply mode.";
  }
  typedef pwe3-label-type {
    type enumeration {
      enum "label-alert" {
        value 1;
        description
          "Specify router alert for label option type.";
      }
      enum "control-word" {
        value 2;
        description
          "Specify control word for label option type.";
      }
      enum "normal" {
        value 3;
        description
          "Specify normal for label option type.";
      }
    }
    description
      "Description of PWE3 label type.";
  }
  typedef vpls-label-type {
    type enumeration {
      enum "control-word" {
        value 2;
        description
          "Specify control word for label option type.";
      }
    }
    description
      "Description of VPLS label type.";
  }
  typedef reply-mode-vpls {
    type enumeration {
      enum "no-reply" {
        value 1;
        description
          "No reply.";
      }
      enum "udp" {
        value 2;
        description
          "UDP.";
      }
      enum "router-alert" {
        value 3;
        description
          "Router-Alert.";
      }
      enum "level-control-channel" {
        value 4;
        description
          "Level-Control-Channel.";
      }
    }
    description
      "Description of reply-mode-vpls.";
  }
  typedef reply-mode-vpls-trace {
    type enumeration {
      enum "no-reply" {
        value 1;
        description
          "No reply.";
      }
      enum "udp" {
        value 2;
        description
          "UDP.";
      }
      enum "level-control-channel" {
        value 4;
        description
          "Level-Control-Channel.";
      }
    }
    description
      "Description of reply-mode-vpls.";
  }
  typedef service-class-value {
    type enumeration {
      enum "be" {
        value 0;
        description
          "Specify BE.";
      }
      enum "af1" {
        value 1;
        description
          "Specify AF1.";
      }
      enum "af2" {
        value 2;
        description
          "Specify AF2.";
      }
      enum "af3" {
        value 3;
        description
          "Specify AF3.";
      }
      enum "af4" {
        value 4;
        description
          "Specify AF4.";
      }
      enum "ef" {
        value 5;
        description
          "Specify EF.";
      }
      enum "cs6" {
        value 6;
        description
          "Specify CS6.";
      }
      enum "cs7" {
        value 7;
        description
          "Specify CS7.";
      }
    }
    description
      "Description of service class.";
  }
  typedef lsp-sr-policy-path {
    type enumeration {
      enum "unknown" {
        value 0;
        description
          "UNKNOWN.";
      }
      enum "main-path" {
        value 1;
        description
          "MAIN-PATH.";
      }
      enum "backup-path" {
        value 2;
        description
          "BACK-PATH.";
      }
    }
    description
      "LSP SR-TE policy path.";
  }
  typedef lsp-protocol-origin {
    type enumeration {
      enum "pecp" {
        value 10;
        description
          "PECP.";
      }
      enum "bgp" {
        value 20;
        description
          "BGP.";
      }
      enum "local" {
        value 30;
        description
          "LOCAL.";
      }
      enum "unknown" {
        value 255;
        description
          "UNKNOWN.";
      }
    }
    description
      "LSP protocol origin.";
  }
  typedef ip-ping-detail-error-code {
    type enumeration {
      enum "no-route" {
        value 1;
        description
          "Unroutable.";
      }
      enum "no-arp" {
        value 2;
        description
          "No ARP.";
      }
      enum "out-if-down" {
        value 3;
        description
          "Outgoing interface down.";
      }
      enum "send-fail" {
        value 4;
        description
          "Send packet fail.";
      }
      enum "icmp-id-error" {
        value 5;
        description
          "Icmp_id is not the expected value.";
      }
      enum "sequence-error" {
        value 6;
        description
          "Sequence is not the expected value.";
      }
      enum "mtu-error" {
        value 7;
        description
          "Interface MTU is too small and packets are forcibly not fragmented.";
      }
      enum "network-unreachable" {
        value 8;
        description
          "Network unreachable.";
      }
      enum "host-unreachable" {
        value 9;
        description
          "Host unreachable.";
      }
      enum "protocol-unreachable" {
        value 10;
        description
          "Protocol unreachable.";
      }
      enum "port-unreachable" {
        value 11;
        description
          "Port unreachable.";
      }
      enum "fragmentation-need" {
        value 12;
        description
          "Fragmentation needed.";
      }
      enum "source-routing-failed" {
        value 13;
        description
          "Source routing failed.";
      }
      enum "destination-network-unknown" {
        value 14;
        description
          "Destination network unknown.";
      }
      enum "destination-host-unknown" {
        value 15;
        description
          "Destination host unknown.";
      }
      enum "ttl-exceeded-transit" {
        value 16;
        description
          "TTL equals 0 during transit.";
      }
      enum "ttl-exceeded-reassembly" {
        value 17;
        description
          "TTL equals 0 during reassembly.";
      }
      enum "ip-header-bad" {
        value 18;
        description
          "IP header bad (catchall error).";
      }
      enum "other-icmp-error" {
        value 200;
        description
          "Other ICMP errors carried in ICMP packets.";
      }
    }
    description
      "Description of ip-ping-detail-error-code.";
  }
  typedef ip6-ping-detail-error-code {
    type enumeration {
      enum "no-route6" {
        value 1;
        description
          "Unroutable.";
      }
      enum "no-nd" {
        value 2;
        description
          "No ND.";
      }
      enum "out-if-down" {
        value 3;
        description
          "Outgoing interface down.";
      }
      enum "send-fail" {
        value 4;
        description
          "Send packet fail.";
      }
      enum "icmp-id-error" {
        value 5;
        description
          "Icmp_id is not the expected value.";
      }
      enum "sequence-error" {
        value 6;
        description
          "Sequence is not the expected value.";
      }
      enum "noroute-unreachable" {
        value 7;
        description
          "No route to destination.";
      }
      enum "prohibited" {
        value 8;
        description
          "Communication with destination administratively prohibited.";
      }
      enum "addr-unreachable" {
        value 9;
        description
          "Address unreachable.";
      }
      enum "port-unreachable" {
        value 10;
        description
          "Port unreachable.";
      }
      enum "packet-too-big" {
        value 11;
        description
          "Packet too big.";
      }
      enum "hop-limit" {
        value 12;
        description
          "Hop limit exceeded in transit.";
      }
      enum "reassembly-timeout" {
        value 13;
        description
          "Fragment reassembly time exceeded.";
      }
      enum "erroneous-header" {
        value 14;
        description
          "Erroneous header field encountered.";
      }
      enum "unrecognized-header" {
        value 15;
        description
          "Unrecognized next header type encountered.";
      }
      enum "unrecognized-option" {
        value 16;
        description
          "Unrecognized option encountered.";
      }
      enum "other-icmp-error" {
        value 200;
        description
          "Other ICMP errors carried in ICMP packets.";
      }
    }
    description
      "Description of ip6-ping-detail-error-code.";
  }
  typedef dgntl-evpn-tunnel-type {
    type enumeration {
      enum "unknown" {
        value 0;
        description
          "Unknown.";
      }
      enum "mpls" {
        value 1;
        description
          "MPLS.";
      }
      enum "srv6-be" {
        value 2;
        description
          "SRv6 BE.";
      }
      enum "srv6-te-policy" {
        value 3;
        description
          "SRv6 TE Policy.";
      }
      enum "srv6-flow-group" {
        value 4;
        description
          "SRv6 Flow Group.";
      }
      enum "vxlan" {
        value 5;
        description
          "Vxlan.";
      }
      enum "vxlan6" {
        value 6;
        description
          "Vxlan6.";
      }
    }
    description
      "Description of evpn vpws tunnel type.";
  }
  typedef dgntl-evpn-vpws-path-type {
    type enumeration {
      enum "unknown" {
        value 0;
        description
          "Unknown.";
      }
      enum "primary" {
        value 1;
        description
          "Primary.";
      }
      enum "backup" {
        value 2;
        description
          "Backup.";
      }
    }
    description
      "Description of evpn vpws path type.";
  }
  typedef lspv-return-code {
    type enumeration {
      enum none {
        value 0;
        description
          "No return code.";
      }
      enum malformed {
        value 1;
        description
          "Malformed echo request received.";
      }
      enum unknown {
        value 2;
        description
          "One or more of the TLVs was not understood.";
      }
      enum egress {
        value 3;
        description
          "Replying router is an egress for the FEC at stack-depth.";
      }
      enum no-mapping {
        value 4;
        description
          "Replying router has no mapping for the FEC at stack-depth.";
      }
      enum ds-mismatch {
        value 5;
        description
          "Downstream mapping mismatch.";
      }
      enum no-up-interface {
        value 6;
        description
          "Upstream interface index unknown.";
      }
      enum reserved {
        value 7;
        description
          "Reserved.";
      }
      enum label-switch {
        value 8;
        description
          "Label switched at stack-depth.";
      }
      enum no-mpls-forwarding {
        value 9;
        description
          "Label switched but no MPLS forwarding at stack-depth.";
      }
      enum no-mapping-label {
        value 10;
        description
          "Mapping for this FEC is not the given label at stack-depth.";
      }
      enum no-entry {
        value 11;
        description
          "No label entry at stack-depth.";
      }
      enum no-protocol {
        value 12;
        description
          "Protocol not associated with interface at FEC stack-depth.";
      }
      enum premature-termination {
        value 13;
        description
          "Premature termination of ping due to label stack shrinking to a single label.";
      }
      enum see-ddmap-tlv {
        value 14;
        description
          "See DDMAP tlv.";
      }
      enum fec-change {
        value 15;
        description
          "Fec change.";
      }
    }
    description
      "Description of return code type.";
  }
  typedef reply-mode-p2mp {
    type enumeration {
      enum no-reply {
        value 1;
        description
          "No reply.";
      }
      enum udp {
        value 2;
        description
          "Reply with an IPv4/IPv6 UDP packet.";
      }
    }
    description
      "Description of reply-mode-p2mp.";
  }
  typedef ttl-flag-type {
    type enumeration {
      enum disable {
        value 0;
        description
          "Disable ttl-flag.";
      }
      enum enable {
        value 1;
        description
          "Enable ttl-flag.";
      }
    }
    description
      "Description of ttl-flag-type.";
  }
  typedef p2mp-transmit-type {
    type enumeration {
      enum "ingress" {
        value 1;
        description
          "Ingress node.";
      }
      enum "transit" {
        value 2;
        description
          "Transit node.";
      }
      enum "bud" {
        value 3;
        description
          "Bud node.";
      }
      enum "branch" {
        value 4;
        description
          "Branch node.";
      }
      enum "egress" {
        value 5;
        description
          "Egress node.";
      }
    }
    description
      "Description of P2MP transmit-type.";
  }
  typedef path-detect-result-type {
    type enumeration {
      enum "path-not-found" {
        value 1;
        description
          "Path not found.";
      }
    }
    description
      "Description of path-detect-result-type.";
  }
}
