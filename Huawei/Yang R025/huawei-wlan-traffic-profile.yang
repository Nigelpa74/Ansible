/*
Copyright (C) 2022-2025 Huawei Technologies Co., Ltd. All rights reserved.
*/
module huawei-wlan-traffic-profile {
  yang-version 1;
  namespace "urn:huawei:yang:huawei-wlan-traffic-profile";
  prefix wlan-traffic-prof;
  import huawei-extension {
    prefix ext;
  }
  import huawei-wlan-vap-profile {
    prefix vap-prof;
  }
  organization
    "Huawei Technologies Co., Ltd.";
  contact
    "Huawei Industrial Base
     Bantian, Longgang
     Shenzhen 518129
     People's Republic of China
     Website: http://www.huawei.com
     Email: support@huawei.com";
  description
    "WLAN traffic profile Configureuration service package.";
  revision 2025-01-10 {
    description
      "Add bcmc-unicast-mdns.";
    reference
      "Huawei private.";
  }
  revision 2024-12-18 {
    description
      "Add traffic-filter-statistics-switch.";
    reference
      "Huawei private.";
  }
  revision 2024-09-12 {
    description
      "The client-up and client-down leaf add mandatory.";
    reference
      "Huawei private.";
  }
  revision 2024-08-27 {
    description
      "Add time-range pattern.";
    reference
      "Huawei private.";
  }
  revision 2024-06-13 {
    description
      "Add mld-snooping.";
    reference
      "Huawei private.";
  }
  revision 2024-06-11 {
    description
      "Fix word spelling problems.";
    reference
      "Huawei private.";
  }
  revision 2024-06-01 {
    description
      "Fix word spelling problems.";
    reference
      "Huawei private.";
  }
  revision 2024-05-16 {
    description
      "The default profile cannot be deleted.";
    reference
      "Huawei private.";
  }
  revision 2024-03-19 {
    description
      "Update profile name pattern.";
    reference
      "Huawei private.";
  }
  revision 2024-03-08 {
    description
      "Add profile name pattern.";
    reference
      "Huawei private.";
  }
  revision 2024-01-13 {
    description
      "Add user-l2-lan-isolate.";
    reference
      "Huawei private.";
  }
  revision 2023-12-16 {
    description
      "Modify IPv6 ACL for traffic filter.";
    reference
      "Huawei private.";
  }
  revision 2023-06-02 {
    description
      "Modify bcmc-deny.";
    reference
      "Huawei private.";
  }
  revision 2023-02-17 {
    description
      "Modify task-name.";
    reference
      "Huawei private.";
  }
  revision 2023-01-04 {
    description
      "Modify igmp-snooping-report-suppress.";
    reference
      "Huawei private.";
  }
  revision 2022-12-28 {
    description
      "Add dynamic rate, bcmc traffic optimize, tcp adjust mss.";
    reference
      "Huawei private.";
  }
  revision 2022-12-22 {
    description
      "Add igmp-mld-snooping/traffic-filters. Modify traffic-remarks.";
    reference
      "Huawei private.";
  }
  revision 2022-12-07 {
    description
      "Add default for binding-traffic-profile.";
    reference
      "Huawei private.";
  }
  revision 2022-06-13 {
    description
      "Initial revision.";
    reference
      "Huawei private.";
  }
  grouping vap-binding-traffic-profile {
    description
      "Binding traffic profile.";
    container binding-traffic-profile {
      description
        "Configure binding traffic profile.";
      leaf binding-traffic-profile {
        type leafref {
          path "/wlan-traffic-prof:wlan-traffic-profile/wlan-traffic-prof:traffic-profiles/wlan-traffic-prof:traffic-profile/wlan-traffic-prof:profile-name";
        }
        default "default";
        description
          "Configure binding traffic profile.";
      }
    }
  }
  container wlan-traffic-profile {
    description
      "Configure WLAN traffic profiles.";
    container traffic-profiles {
      description
        "List of wlan-traffic-profile.";
      list traffic-profile {
        ext:generated-by system {
          ext:filter "profile-name='default'";
          description
            "The default profile is generated by system.";
        }
        ext:operation-exclude "delete" {
          ext:filter "profile-name='default'";
          description
            "The default profile cannot be deleted.";
        }
        key "profile-name";
        description
          "Configure WLAN traffic profiles.";
        leaf profile-name {
          type string {
            length "1..35";
            pattern '[^\s?]+';
            pattern '[!-~]+';
          }
          description
            "WLAN traffic profile name.";
        }
        leaf user-isolate {
          type enumeration {
            enum "l2" {
              value 0;
              description
                "Configure user-isolate l2.";
            }
            enum "all" {
              value 1;
              description
                "Configure user-isolate all.";
            }
          }
          description
            "Configure user-isolate.";
        }
        container rate-limit {
          description
            "Configure rate-limit.";
          leaf client-up {
            type uint32 {
              range "64..4294967295";
            }
            default "4294967295";
            description
              "Configure client up limits.";
          }
          leaf client-down {
            type uint32 {
              range "64..4294967295";
            }
            default "4294967295";
            description
              "Configure client down limits.";
          }
          leaf vap-up {
            type uint32 {
              range "64..4294967295";
            }
            default "4294967295";
            description
              "Configure vap up limits.";
          }
          leaf vap-down {
            type uint32 {
              range "64..4294967295";
            }
            default "4294967295";
            description
              "Configure vap down limits.";
          }
        }
        container time-range-up-rate-limits {
          description
            "List of time-range-up-rate-limit.";
          list time-range-up-rate-limit {
            key "time-range";
            max-elements 8;
            leaf time-range {
              type string {
                length "1..32";
                pattern '([a-zA-Z]([^\s]*))';
              }
              description
                "Configure time-range.";
            }
            leaf client-up {
              type uint32 {
                range "64..4294967295";
              }
              mandatory true;
              description
                "Configure client up limits.";
            }

            description
              "Configure time-range-rate-limits.";
          }
        }
        container time-range-down-rate-limits {
          description
            "List of time-range-down-rate-limit.";
          list time-range-down-rate-limit {
            key "time-range";
            max-elements 8;
            leaf time-range {
              type string {
                length "1..32";
                pattern '([a-zA-Z]([^\s]*))';
              }
              description
                "Configure time-range.";
            }
            leaf client-down {
              type uint32 {
                range "64..4294967295";
              }
              mandatory true;
              description
                "Configure client up limits.";
            }

            description
              "Configure time-range-down-rate-limits.";
          }
        }
        container traffic-optimize {
          description
            "Configure traffic optimize.";
          leaf sta-bridge-forward {
            type enumeration {
              enum "disabled" {
                value 0;
                description
                  "Configure disabled mode.";
              }
              enum "enable" {
                value 1;
                description
                  "Configure enable mode.";
              }
            }
            default "enable";
            description
              "Configure sta-bridge-forward.";
          }
          leaf dynamic-rate-limit {
            type boolean;
            default true;
            description
              "Enable/disable dynamic rate limie of wireless client.";
          }
          leaf broadcast-suppression {
            type uint32 {
              range "0..14881000";
            }
            units "pps";
            description
              "Configure broadcast-suppression.";
          }
          leaf multicast-suppression {
            type uint32 {
              range "0..14881000";
            }
            units "pps";
            description
              "Configure multicast-suppression.";
          }
          leaf unicast-suppression {
            type uint32 {
              range "0..14881000";
            }
            units "pps";
            description
              "Configure unicast-suppression.";
          }
          leaf multicast-unicast {
            type boolean;
            default false;
            description
              "Enable/disable converting multicast packets to unicast packets.";
          }
          leaf bcmc-unicast-arp {
            type boolean;
            default true;
            description
              "Enable/disable converting arp packets to unicast packets.";
          }
          leaf bcmc-unicast-dhcp {
            type boolean;
            default true;
            description
              "Enable/disable converting dhcp packets to unicast packets.";
          }
          leaf bcmc-unicast-nd {
            type boolean;
            default true;
            description
              "Enable/disable converting nd packets to unicast packets.";
          }
          leaf bcmc-unicast-mdns {
            type boolean;
            default false;
            description
              "Enable/disable converting mDNS packets to unicast packets.";
          }
          leaf bcmc-unicast-mismatch-drop {
            type boolean;
            default true;
            description
              "Enable/disable dropping packets when failed to be converted into unicast packets.";
          }

          container bcmc-deny {
            description
              "Configure denying downstream broadcast or multicast packets.";
            leaf deny-all {
              type boolean;
              default false;
              description
                "Enable/disable denying all downstream broadcast or multicast packets.";
            }
            leaf except-mdns {
              when "../deny-all = 'true'";
              type boolean;
              default false;
              description
                "Enable/disable denying all downstream broadcast or multicast packets except MDNS.";
            }
          }

          leaf tcp-adjust-mss {
            type uint16 {
              range "128..2048";
            }
            description
              "Configure the MSS of TCP packets.";
          }
        }
        container traffic-remarks {
          presence "Create traffic remark policy";
          description
            "List of traffic remark.";
          list traffic-remark {
            must "((./ipv4-acl-number != 0 or ./l2-acl-number != 0) and ./ipv6-acl-number = 0) or (./ipv4-acl-number = 0 and ./l2-acl-number = 0 and ipv6-acl-number != 0)";
            key "direction ipv4-acl-number l2-acl-number ipv6-acl-number";
            unique "direction priority";
            description
              "Configure traffic remark.";
            leaf direction {
              type enumeration {
                enum "inbound" {
                  value 0;
                  description
                    "Filtering package in incoming.";
                }
                enum "outbound" {
                  value 1;
                  description
                    "Filtering package in outgoing.";
                }
              }
              description
                "Direction of traffic remark Configure.";
            }
            leaf ipv4-acl-number {
              type uint32 {
                range "0|3000..3031|6000..6031";
              }
              description
                "IPv4 ACL.";
            }
            leaf l2-acl-number {
              type uint32 {
                range "0|4000..4031";
              }
              description
                "L2 ACL.";
            }
            leaf ipv6-acl-number {
              type uint32 {
                range "0|3000..3031";
              }
              description
                "IPv6 ACL.";
            }
            leaf priority {
              type uint8 {
                range "0..7";
              }
              mandatory true;
              description
                "Specifies the sequence in which ACLs take effect.";
            }
            leaf dscp-or-dot11e {
              type enumeration {
                enum "dscp" {
                  value 0;
                  description
                    "Configure dscp type.";
                }
                enum "dot11e" {
                  value 1;
                  description
                    "Configure dot11e type.";
                }
              }
              description
                "Configure dscp-or-dot11e.";
            }
            leaf dscp {
              when "../dscp-or-dot11e = 'dscp'";
              type uint16 {
                range "0..63";
              }
              description
                "Configure dscp value.";
            }
            leaf dot11e {
              when "../dscp-or-dot11e = 'dot11e'";
              type uint16 {
                range "0..7";
              }
              description
                "Configure dot11e value.";
            }
          }
        }
        container igmp-mld-snooping {
          description
            "Configure IGMP/MLD snooping.";
          leaf igmp-snooping {
            type boolean;
            default "false";
            description
              "Enable/disable IGMP snooping function.";
          }
          leaf igmp-snooping-report-suppress {
            when "../igmp-snooping = 'true'";
            type boolean;
            default "false";
            description
              "Enable/disable IGMP Report and Leave message suppression function.";
          }
          leaf mld-snooping {
            type boolean;
            default "false";
            description
              "Enable/disable MLD snooping function.";
          }
        }
        container traffic-filters {
          presence "Create traffic filter policy";
          description
            "List of traffic filter.";
          list traffic-filter {
            must "((./ipv4-acl-number != 0 or ./l2-acl-number != 0) and ./ipv6-acl-number = 0) or (./ipv4-acl-number = 0 and ./l2-acl-number = 0 and ipv6-acl-number != 0)";
            key "direction ipv4-acl-number l2-acl-number ipv6-acl-number";
            unique "direction priority";
            description
              "Configure traffic filter.";
            leaf direction {
              type enumeration {
                enum "inbound" {
                  value 0;
                  description
                    "Filtering package in incoming.";
                }
                enum "outbound" {
                  value 1;
                  description
                    "Filtering package in outgoing.";
                }
              }
              description
                "Direction of traffic filter configure.";
            }
            leaf ipv4-acl-number {
              type uint32 {
                range "0|3000..3031|6000..6031";
              }
              description
                "IPv4 ACL.";
            }
            leaf l2-acl-number {
              type uint32 {
                range "0|4000..4031";
              }
              description
                "L2 ACL.";
            }
            leaf ipv6-acl-number {
              type uint32 {
                range "0|3000..3031";
              }
              description
                "IPv6 ACL.";
            }
            leaf priority {
              type uint8 {
                range "0..7";
              }
              mandatory true;
              description
                "Specifies the sequence in which ACLs take effect.";
            }
          }
        }
        leaf traffic-filter-statistics-switch {
            type boolean;
            default false;
            description "Enable/disable traffic-filter statistics.";
        }
        leaf user-l2-lan-isolate {
            type boolean;
            default false;
            description "Enable/disable gateway-based Layer 2 isolation.";
        }
      }
    }
  }
  augment "/vap-prof:wlan-vap-profile/vap-prof:vap-profiles/vap-prof:vap-profile" {
    description
      "Configure binding traffic profile to vap profile.";
    uses wlan-traffic-prof:vap-binding-traffic-profile;
  }
  ext:task-name "lcm";
}
