/*
Copyright (C) 2021-2024 Huawei Technologies Co., Ltd. All rights reserved.
*/
module huawei-lldp-notification {
  yang-version 1;
  namespace "urn:huawei:yang:huawei-lldp-notification";
  prefix lldp-notification;
  import huawei-extension {
    prefix ext;
  }
  import huawei-pub-type {
    prefix pub-type;
  }
  import huawei-lldp {
    prefix lldp;
  }
  organization
    "Huawei Technologies Co., Ltd.";
  contact
    "Huawei Industrial Base
    Bantian, Longgang
    Shenzhen 518129
    People's Republic of China
    Website: http://www.huawei.com
    Email: support@huawei.com";
  description
    "Notification of LLDP.";
  revision 2024-04-08 {
    description
      "Add notification node med-manufacturer-name and med-model-name.";
    reference
      "Huawei private.";
  }
  revision 2022-02-26 {
    description
      "Modify name of local-port and type of chassis-id-sub-type, port-id-sub-type and management-address-type.";
    reference
      "Huawei private.";
  }
  revision 2021-10-16 {
    description
      "Init revision.";
    reference
      "Huawei private.";
  }
  ext:task-name "lldp";
  typedef lldp-remote-change-type {
    type enumeration {
      enum "added" {
        value 1;
        description
          "Interface neighbors are added.";
      }
      enum "deleted" {
        value 2;
        description
          "Interface neighbors are deleted.";
      }
      enum "updated" {
        value 3;
        description
          "Interface neighbors are updated.";
      }
    }
    description
      "Neighbor change type.";
  }
  notification lldp-mdn-port-neighbor-changed {
    description
      "MDN Neighbor information of the interface was changed.";
    leaf interface-name {
      type string {
        length "1..256";
      }
      description
        "Interface name.";
    }
    leaf event-type {
      type lldp-remote-change-type;
      description
        "Whether interface neighbors are added or deleted.";
    }
    leaf remote-index {
      type int32;
      description
        "Neighbor index.";
    }
    leaf remote-device-id {
      type string {
        length "1..256";
      }
      description
        "Remote device ID.";
    }
    leaf remote-interface {
      type string {
        length "1..256";
      }
      description
        "Remote interface name.";
    }
    leaf mac-address {
      type pub-type:mac-address;
      description
        "Remote device MAC address.";
    }
  }
  notification lldp-neighbor-changed {
    description
      "Neighbor information of the interface was changed.";
    leaf remote-index {
      type uint32;
      description
        "Remote index.";
    }
    leaf event-type {
      type lldp-remote-change-type;
      description
        "Whether interface neighbors are added or deleted.";
    }
    leaf local-port {
      type string {
        length "1..256";
      }
      description
        "Local interface name.";
    }
    leaf chassis-id-sub-type {
      type lldp:chassis-id-sub-type;
      description
        "Remote chassis type.";
    }
    leaf chassis-id {
      type string {
        length "1..256";
      }
      description
        "Remote chassis ID.";
    }
    leaf port-id-sub-type {
      type lldp:port-id-sub-type;
      description
        "Remote port ID type.";
    }
    leaf port-id {
      type string {
        length "1..256";
      }
      description
        "Remote port ID.";
    }
    leaf system-name {
      type string {
        length "1..256";
      }
      description
        "Remote system name.";
    }
    leaf system-description {
      type string {
        length "1..256";
      }
      description
        "Remote system description.";
    }
    leaf system-capabilities-supported {
      type string {
        length "1..256";
      }
      description
        "Remote system capabilities supported.";
    }
    leaf system-capabilities-enabled {
      type string {
        length "1..256";
      }
      description
        "Remote system capabilities enabled.";
    }
    leaf management-address-type {
      type lldp:management-address-type;
      description
        "Remote management address type.";
    }
    leaf management-address {
      type string {
        length "1..256";
      }
      description
        "Remote management address.";
    }
    leaf med-manufacturer-name {
      type string {
        length "1..33";
      }
      description
        "Remote manufacturer name.";
    }
    leaf med-model-name {
      type string {
        length "1..33";
      }
      description
        "Remote model name.";
    }
  }
}
