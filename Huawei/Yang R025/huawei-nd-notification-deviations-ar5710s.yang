/*
Copyright (C) 2025 Huawei Technologies Co., Ltd. All rights reserved.
*/
module huawei-nd-notification-deviations-ar5710s {
  namespace "urn:huawei:yang:huawei-nd-notification-deviations-ar5710s";
  prefix nd-notification-devs-ar5710s;

  import huawei-nd-notification {
    prefix nd-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-nd-notification module.";

  revision 2025-02-24 {
    description
      "Initial revision.";
    reference "Huawei private.";
  }

  deviation "/nd-notification:dad-not-finished" {
    deviate not-supported;
  }
  deviation "/nd-notification:duplicate-ipv6" {
    deviate not-supported;
  }
  deviation "/nd-notification:duplicate-ipv6-resume" {
    deviate not-supported;
  }
}
