/*
Copyright (C) 2019-2025 Huawei Technologies Co., Ltd. All rights reserved.
*/
module huawei-evpn {
  namespace "urn:huawei:yang:huawei-evpn";
  prefix evpn;
  import huawei-acl {
    prefix acl;
  }
  import huawei-network-instance {
    prefix ni;
  }
  import huawei-l3vpn {
    prefix l3vpn;
  }
  import huawei-bd {
    prefix bd;
  }
  import huawei-ifm {
    prefix ifm;
  }
  import huawei-pub-type {
    prefix pub-type;
  }
  import huawei-routing-policy {
    prefix rtp;
  }
  import ietf-inet-types {
    prefix inet;
  }
  import huawei-extension {
    prefix ext;
  }
  import huawei-evpl {
    prefix evpl;
  }
  import huawei-bfd {
    prefix bfd;
  }
  import huawei-bgp {
    prefix bgp;
  }
  import huawei-tunnel-management {
    prefix tnlm;
  }
  import huawei-l2vpn {
    prefix l2vpn;
  }
  import huawei-nvo3 {
    prefix nvo3;
  }
  import ietf-yang-types {
    prefix yang;
  }
  import huawei-xpl {
    prefix xpl;
  }
  include huawei-evpn-type;
  organization
    "Huawei Technologies Co., Ltd.";
  contact
    "Huawei Industrial Base
     Bantian, Longgang
     Shenzhen 518129
     People's Republic of China
     Website: http://www.huawei.com
     Email: support@huawei.com";
  description
    "EVPN configuration.";
  revision 2025-08-01 {
    description
      "Modify the when condition of esi, es-recovery-timer, track-bfd-name. Fix a typo.";
    reference
      "Huawei private.";
  }
  revision 2024-11-08 {
    description
      "Add leaf track-umr-route for attribute.";
    reference
      "Huawei private.";
  }
  revision 2024-08-30 {
    description
      "Modify the when conditions for esi, es-recovery-timer, and track-bfd-name.";
    reference
      "Huawei private.";
  }
  revision 2024-08-29 {
    description
      "Modify the must condition of evpn-overlay and instance.";
    reference
      "Huawei private.";
  }
  revision 2024-07-30 {
    description
      "Support for FlexE interface types.";
    reference
      "Huawei private.";
  }
  revision 2024-06-05 {
    description
      "Modify the must condition of evpl-id.";
    reference
      "Huawei private.";
  }
  revision 2024-04-30 {
    description
      "Modify the must condition of esi.";
    reference
      "Huawei private.";
  }
  revision 2024-04-16 {
    description
      "Add leaf mac-flapping-alarm-enable.";
    reference
      "Huawei private.";
  }
  revision 2024-04-15 {
    description
      "Add leaf pw-extend-private for attribute.";
    reference
      "Huawei private.";
  }
  revision 2024-03-22 {
    description
      "Add leaf conflict-interface-name for sticky-mac-confliction-info.";
    reference
      "Huawei private.";
  }
  revision 2024-02-21 {
    description
      "Add leaf acl-name-or-id for global mac-duplication.";
    reference
      "Huawei private.";
  }  
  revision 2024-02-19 {
    description
      "Modify the must condition of flow-label leaf.";
    reference
      "Huawei private.";
  }  
  revision 2024-02-05 {
    description
      "Modify the must condition of the evpn container under the augment node.";
    reference
    "Huawei private.";
  }
  revision 2024-01-31 {
    description
      "Modify df-extcommunity-check-multi leaf.";
    reference
      "Huawei private.";
  }
  revision 2024-01-12 {
    description
      "Add nodes for EVPN traffic statistics.";
    reference
      "Huawei private.";
  }
  revision 2024-01-10 {
    description
      "Modify the expression of control-word node.";
    reference
      "Huawei private.";
  }
  revision 2023-12-21 {
    description
      "Delete xsec policy container.";
    reference
      "Huawei private.";
  }
  revision 2023-12-09 {
    description
      "Add export-policy-add-ert-first node.";
    reference
      "Huawei private.";
  }
  revision 2023-11-28 {
    description
      "Add ccc leaf.";
    reference
      "Huawei private.";
  }
  revision 2023-11-27 {
    description
      "Add ccc-service-id and ccc-out-service-id leaf.";
    reference
      "Huawei private.";
  }
  revision 2023-11-23 {
    description
      "Modify the description of macip-remote-suppress-local leaf.";
    reference
      "Huawei private.";
  }
  revision 2023-11-20 {
    description
      "Modify description of evpl-info list.";
    reference
      "Huawei private.";
  }
  revision 2023-11-15 {
    description
      "Modify description of macip-remote-suppress-local leaf.";
    reference
      "Huawei private.";
  }
  revision 2023-11-09 {
    description
      "Add macip-remote-suppress-local leaf.";
    reference
      "Huawei private.";
  }
  revision 2023-11-07 {
    description
      "Add the container for EVPL DF information and modify EVPL UPE.";
    reference
      "Huawei private.";
  }
  revision 2023-11-03 {
    description
      "Add the container for L3 static ESI and sourceAddress.";
    reference
      "Huawei private.";
  }
  revision 2023-10-07 {
    description
      "Add the container for EVPL UPE.";
    reference
      "Huawei private.";
  }
  revision 2023-09-27 {
    description
      "Add the leaf for sticky-mac info.";
    reference
      "Huawei private.";
  }
  revision 2023-09-02 {
    description
      "Modify es recovery timer.";
    reference
      "Huawei private.";
  }
  revision 2023-08-31 {
    description
      "Add the leaf for pw-sticky-mac.";
    reference
      "Huawei private.";
  }
  revision 2023-08-25 {
    description
      "Modify the range of bdtag.";
    reference
      "Huawei private.";
  }
  revision 2023-08-14 {
    description
      "Add the container for track-df-state.";
    reference
      "Huawei private.";
  }
  revision 2023-08-09 {
    description
      "Modify the range of EVPL instance ID and service ID.";
    reference
      "Huawei private.";
  }
  revision 2023-04-23 {
    description
      "Add the container for track-evpl-state.";
    reference
      "Huawei private.";
  }
  revision 2023-04-20 {
    description
      "Add flow-label leaf.";
    reference
      "Huawei private.";
  }
  revision 2023-04-10 {
    description
      "Add the rpc for resetting all EVPN VPN SID.";
    reference
      "Huawei private.";
  }
  revision 2023-03-20 {
    description
      "Modify behavior type.";
    reference
      "Huawei private.";
  }
  revision 2023-03-15 {
    description
      "Add the leaf for MAC redirect compatible.";
    reference
      "Huawei private.";
  }
  revision 2023-03-10 {
    description
      "Add the leaf for DF extcommunity check.";
    reference
      "Huawei private.";
  }
  revision 2023-02-23 {
    description
      "Modify mac-duplication.";
    reference
      "Huawei private.";
  }
  revision 2023-02-17 {
    description
      "Modify dampened-times type.";
    reference
      "Huawei private.";
  }
  revision 2023-02-16 {
    description
      "Add remote label and remote SID.";
    reference
      "Huawei private.";
  }
  revision 2023-02-10 {
    description
      "Add sid-structure leaf.";
    reference
      "Huawei private.";
  }
  revision 2022-11-30 {
    description
      "Modify the must condition for new interface type.";
    reference
      "Huawei private.";
  }
  revision 2022-11-14 {
    description
      "Add container port-control.";
    reference
      "Huawei private.";
  }
  revision 2022-11-10 {
    description
      "Add the leaf for global v4v6 route priority selection.";
    reference
      "Huawei private.";
  }
  revision 2022-11-07 {
    description
      "Delete evpl-ccc related nodes.";
    reference
      "Huawei private.";
  }
  revision 2022-10-31 {
    description
      "Add leaf behavior and bypass-behavior.";
    reference
      "Huawei private.";
  }
  revision 2022-10-22 {
    description
      "Modify the length of relay tunnel name.";
    reference
      "Huawei private.";
  }
  revision 2022-09-24 {
    description
      "Add nodes for evpl ccc.";
    reference
      "Huawei private.";
  }
  revision 2022-09-19 {
    description
      "Add leaf mac-policy-name in container bd-evpn.";
    reference
      "Huawei private.";
  }
  revision 2022-08-29 {
    description
      "Modify the range of global-suppressed-statistics.";
    reference
      "Huawei private.";
  }
  revision 2022-08-19 {
    description
      "Add leaf tunnel-id for route control.";
    reference
      "Huawei private.";
  }
  revision 2022-07-22 {
    description
      "Modify evpn tunnel policy must conditions.";
    reference
      "Huawei private.";
  }
  revision 2022-07-19 {
    description
      "Modify evpl-peer-info container.";
    reference
      "Huawei private.";
  }
  revision 2022-07-15 {
    description
      "Add new srv6-mode type.";
    reference
      "Huawei private.";
  }
  revision 2022-07-11 {
    description
      "Add leaf nexthop-resolve-aigp for route selection.";
    reference
      "Huawei private.";
  }
  revision 2022-06-20 {
    description
      "Delete mac-learn-style qualify must condition under umr-originate.";
    reference
      "Huawei private.";
  }
  revision 2022-06-06 {
    description
      "Add leaf qualify-compatible to evpn contianer under BD.";
    reference
      "Huawei private.";
  }
  revision 2022-05-27 {
    description
      "Add rollback L2VPN and delay switch to EVPL for VLL EVPL migration.";
    reference
      "Huawei private.";
  }
  revision 2022-05-07 {
    description
      "Add leaf acl-name-or-id for mac-duplication.";
    reference
      "Huawei private.";
  }
  revision 2022-03-18 {
    description
      "Yang must condition modify.";
    reference
      "Huawei private.";
  }
  revision 2022-02-15 {
    description
      "Add a augment for bridge domain profile.";
    reference
      "Huawei private.";
  }
  revision 2022-01-28 {
    description
      "Add constriants to container es-recover under evpn container.";
    reference
      "Huawei private.";
  }
  revision 2022-01-21 {
    description
      "Add container route-control in conatiner site, bd-evpn and vpws-evpn.";
    reference
      "Huawei private.";
  }
  revision 2021-12-13 {
    description
      "Delete the must condition for srv6-mode and control-word.";
    reference
      "Huawei private.";
  }
  revision 2021-12-08 {
    description
      "Add container es-recover with leaf timer under evpn container.";
    reference
      "Huawei private.";
  }
  revision 2021-08-12 {
    description
      "Add leaf nexthop-priority in container vpws-evpn.";
    reference
      "Huawei private.";
  }
  revision 2020-05-04 {
    description
      "Add container evpl-peer-info, add leaf local-ctrl-word in container evpl-info.";
    reference
      "Huawei private.";
  }
  revision 2020-04-20 {
    description
      "Add node tunnel-policy-name, modify descriptions of YANG module.";
    reference
      "Huawei private.";
  }
  revision 2019-03-22 {
    description
      "Initial revision.";
    reference
      "Huawei private.";
  }
  ext:task-name "evpnbgp";
  grouping mac-duplication-infos-type {
    description
      "Information aggregation about MAC addresses that are duplicate in an EVPN instance.";
    list mac-duplication-info {
      key "mac-address bd-id";
      description
        "Operational state of information about MAC addresses that are duplicate in an EVPN instance.";
      leaf mac-address {
        type pub-type:mac-address;
        description
          "MAC address.";
      }
      leaf bd-id {
        type uint32 {
          range "1..16777215";
        }
        description
          "Bridge domain ID.";
      }
      leaf bd-tag {
        type uint32 {
          range "1..16384";
        }
        description
          "Bridge domain label.";
      }
      leaf dampened-times {
        type uint16;
        description
          "Number of times that MAC duplication occurs.";
      }
      leaf suppress-flag {
        type boolean;
        description
          "Flag indicating whether MAC duplication is suppressed.";
      }
      leaf last-source {
        type string {
          length "1..100";
        }
        description
          "Source port.";
      }
      leaf peer-ip {
        type inet:ipv4-address-no-zone;
        description
          "Peer IP address of a PW.";
      }
      leaf vc-id {
        type uint32 {
          range "1..4294967295";
        }
        description
          "PW ID used to uniquely identify a VC.";
      }
      leaf vc-type {
        type evpn:l2vpn-encapsulate-type;
        description
          "Encapsulation type of a PW.";
      }
      leaf suppress-time {
        type yang:date-and-time;
        description
          "Date and time when MAC duplication was suppressed.";
      }
    }
  }
  grouping label-stacks-type {
    description
      "Label stack.";
    list label-stack {
      key "label-stack level";
      description
        "Operational data of the EVPN label stack.";
      leaf label-stack {
        type uint32 {
          range "1..4294967295";
        }
        description
          "Label stack index.";
      }
      leaf level {
        type uint32 {
          range "1..4294967295";
        }
        description
          "Label level.";
      }
      leaf type {
        type string {
          length "1..20";
        }
        description
          "Label type.";
      }
      leaf label {
        type string {
          length "1..20";
        }
        description
          "Label value.";
      }
      leaf out-interface {
        type leafref {
          path "/ifm:ifm/ifm:interfaces/ifm:interface/ifm:name";
        }
        description
          "Outbound interface name.";
      }
    }
  }
  grouping routing-table-type {
    description
      "Routing table information.";
    leaf nexthop {
      type inet:ip-address-no-zone;
      description
        "Next-hop address to which packets are sent.";
    }
    leaf local-preference {
      type uint32;
      description
        "Local priority. The attribute is only fit for the routes from IBGP peer, not suit for which of EBGP peer.";
    }
    leaf protocol-preferred-value {
      type uint32 {
        range "0..4294967295";
      }
      description
        "Preferred value of a protocol.";
    }
    leaf route-preference {
      type uint8 {
        range "0..255";
      }
      description
        "Preference of a route.";
    }
    leaf route-worse-reason {
      type string {
        length "1..50";
      }
      description
        "Reason why a route is not selected.";
    }
    leaf as-path {
      type string {
        length "1..300";
      }
      description
        "List of the ASs that packets pass through.";
    }
    leaf origin {
      type evpn:bgp-origin-type;
      description
        "Origin of a route.";
    }
    leaf med {
      type uint32 {
        range "0..4294967295";
      }
      description
        "Route MED in the attribute node. The attribute is only fit for the routes from EBGP peer, not suit for which of IBGP peer.";
    }
    leaf route-flag {
      type string {
        length "1..100";
      }
      description
        "Route flag that contains a string of characters.";
    }
    leaf advertised-peers {
      type string {
        length "1..300";
      }
      description
        "List of sending peers.";
    }
    leaf route-duration-time {
      type uint32;
      description
        "Time stamp of a route.";
    }
    leaf pmsi {
      type string {
        length "1..300";
      }
      description
        "PMSI attribute.";
    }
    leaf other-attribute {
      type string {
        length "1..300";
      }
      description
        "Other attribute.";
    }
    leaf private-route {
      type string {
        length "1..300";
      }
      description
        "Private route attribute.";
    }
    leaf outbound-interface {
      type string {
        length "1..63";
      }
      description
        "Name of the outbound interface of a route.";
    }
    leaf remote-route-id {
      type inet:ipv4-address-no-zone;
      description
        "Router ID of a peer.";
    }
    leaf community {
      type string {
        length "1..300";
      }
      description
        "Community attribute.";
    }
    leaf ext-community {
      type string {
        length "1..300";
      }
      description
        "Extended community attribute.";
    }
    leaf ipv6-ext-community {
      type string {
        length "1..300";
      }
      description
        "IPv6 extended community attribute.";
    }
    leaf large-community {
      type string {
        length "1..200";
      }
      description
        "Large-community attribute information.";
    }
    leaf cluster-list {
      type string {
        length "1..300";
      }
      description
        "List of Cluster IDs.";
    }
    leaf relay-nexthop {
      type inet:ip-address-no-zone;
      description
        "Iterated next hop.";
    }
    leaf relay-tunnel-name {
      type string {
        length "1..256";
      }
      description
        "Name of an iteration tunnel.";
    }
    leaf in-label {
      type uint32 {
        range "0..4294967295";
      }
      description
        "In-label.";
    }
    leaf out-label {
      type uint32 {
        range "0..4294967295";
      }
      description
        "Out-label.";
    }
    leaf originator {
      type inet:ipv4-address-no-zone;
      description
        "Router ID of the route initiator.";
    }
    leaf relay-aigp {
      type uint32;
      description
        "AIGP attribute information of route.";
    }
  }
  container evpn {
    description
      "Configure of EVPN.";
    container base-process {
      description
        "Configure of EVPN base process.";
      leaf redundancy-mode {
        type redundancy-mode;
        default "all-active";
        description
          "Redundancy mode.";
      }
      leaf source-address {
        ext:operation-exclude update;
        type inet:ipv4-address-no-zone;
        description
          "Source address.";
      }
      leaf evpn-overlay {
        type boolean;
        default "false";
        description
          "Enable/disable EVPN overlay.";
      }
      leaf evpn-origin-igp {
        type boolean;
        default "true";
        description
          "Enable/disable EVPN route origin IGP.";
      }
      leaf auto-rd-ip {
        type inet:ipv4-address-no-zone;
        description
          "IPv4 address used to compose autoRD.";
      }
    }
    container site {
      presence "evpn view";
      description
        "Enable/disable global EVPN configuration.";
      leaf df-election-mode {
        type df-election-mode;
        default "per-interface";
        description
          "Global configuration DF election mode.";
      }
      leaf vpws-df-election-mode {
        type vpws-df-election-mode;
        default "per-interface";
        description
          "VPWS DF select mode.";
      }
      leaf ac-influnced-enable {
        type boolean;
        default "false";
        description
          "Enable/disable AC state influenced DF mode.";
      }
      leaf ad-per-es-split {
        type ad-per-es-route-divmode;
        default "dont-divide-rt";
        description
          "EVPN AD per ES route split.";
      }
      leaf irb-reoriginated {
        type boolean;
        default "false";
        description
          "Enable/disable IRB reoriginated without bridge domain.";
      }
      leaf vlan-extend-private-enable {
        type boolean;
        default "false";
        description
          "Enable/disable VLAN extend extcommunity to carry VLAN in MAC routes.";
      }
      leaf vlan-extend-redirect-enable {
        type boolean;
        default "false";
        description
          "Enable/disable VLAN extend extcommunity to redirect to the same ESI interface.";
      }
      leaf local-remote-frr-enable {
        type boolean;
        default "false";
        description
          "Enable/disable local MAC and remote MAC to form FRR.";
      }
      leaf bypass-vxlan-enable {
        type boolean;
        default "false";
        description
          "Enable/disable bypass VXLAN extcommunity, use for allow all-active device to form bypass VXLAN.";
      }
      leaf alm-threshold {
        type uint32 {
          range "1..4294967295";
        }
        description
          "Specify the alarm route threshold.";
      }
      leaf recovery-percentage {
        when "../alm-threshold";
        type uint32 {
          range "1..95";
        }
        units "%";
        default "80";
        description
          "Specify the alarm route recovery percentage.";
      }
      leaf local-remote-vpws-frr-enable {
        type boolean;
        default "false";
        description
          "Enable/disable the local and remote FRR for EVPN VPWS.";
      }
      leaf remote-vpws-frr-enable {
        type boolean;
        default "false";
        description
          "Enable/disable the remote FRR for EVPN VPWS.";
      }
      leaf irb-split-group {
        type boolean;
        default "true";
        description
          "Enable/disable IRB advertise under split group.";
      }
      leaf compatible {
        type boolean;
        default "false";
        description
          "Enable/disable IRB routing rebirth into ARP routing and prefix routing.";
      }
      leaf advertising-vxlan-tunnel-mac {
        type boolean;
        default "false";
        description
          "Enable/disable advertising MAC routes learned by VXLAN tunnel.";
      }
      leaf advertise-suppressed-route {
        type boolean;
        default "false";
        description
          "Enable/disable advertising suppressed detail route.";
      }
      leaf routerid-extend-private-enable {
        type boolean;
        default "false";
        description
          "Enable/disable router ID extend extcommunity for carrying router ID in EVPN routes.";
      }
      leaf nexthop-recursive-lookup-restrain {
        type boolean;
        default "true";
        description
          "Enable/disable EVPN nexthop recursive lookup restrain.";
      }
      leaf adv-dci-local-rt-to-mpls {
        type boolean;
        default "false";
        description
          "Enable/disable advertising DCI local route to MPLS peer.";
      }
      leaf mac-duplication-enable {
        type boolean;
        default "true";
        description
          "Enable/disable mac-duplication.";
      }
      leaf l3-reoriginate-diff-split-grp {
        type boolean;
        default "false";
        description
          "Enable/disable L3 route reorigination is effected by split group.";
      }
      leaf reflect-same-split-group {
        type boolean;
        default "false";
        description
          "Enable/disable of allowing route reflection at same split group.";
      }
      leaf l3-source-address { 
        type inet:ipv4-address-no-zone; 
        description 
          "Source address for L3.";
      }
      leaf unique-source-mac {
        type boolean;
        default "false";
        description
          "Enable/disable the advertisement of MAC routes using unique-source as the next hop.";
      }
      container attribute {
        description
          "Configure EVPN system attribute.";
        leaf migrate-delay-time {
          type uint16 {
            range "0..1800";
          }
          units "s";
          default "300";
          description
            "Configuring the delay time for the migration from VLL to EVPL.";
        }
        leaf mac-redirect-compatible {
          type boolean;
          must "((../mac-redirect-compatible='true') and (../../vlan-extend-redirect-enable='false')) or (../mac-redirect-compatible='false')";
          default "false";
          description
            "Enable/disable MAC redirect compatible.";
        }
        leaf macip-remote-suppress-local {
          type boolean;
          default "false";
          description
            "Enable/disable fast withdrawal of local non-preferred MAC/IP routes in an EVPN System.";
        }
        leaf pw-extend-private {
          type boolean;
          default "false";
          description
            "Enable/disable PW extend private.";
        }
        leaf mac-flapping-alarm-enable {
          type boolean;
          default "false";
          description
            "Enable/disable MAC flapping alarm.";
        }
      }
      container route-control {
        description
          "Configure about route control.";
        leaf vpws-srv6-advertise-mpls {
          type boolean;
          default "false";
          description
            "Enable/disable ELINE srv6 local route advertise to MPLS.";
        }
        leaf vpls-srv6-advertise-mpls {
          type boolean;
          default "false";
          description
            "Enable/disable ELAN SRv6 local route advertise to MPLS.";
        }
        leaf tunnel-id {
          type inet:ipv6-address-no-zone;
          description
            "Tunnel ID in the PMSI attribute of an inclusive route.";
        }
        leaf nexthop-priority {
          type evpn:nexthop-priority-type;
          description
            "Enable/disable route selection priority based on the global next-hop priority.";
        }
        leaf df-extcommunity-check {
          type boolean;
          default "false";
          description
            "Enable/disable AC influence DF election negotiation.";
        }
        leaf df-extcommunity-check-multi {
          when "../df-extcommunity-check='true'";
          type boolean;
          default "false";
          description
              "Enable/disable the extended community attribute of multi-DF election affects DF election negotiation.";
        }
      }
      container mac-duplication {
        description
          "Configure MAC duplication.";
        leaf period {
          type uint8 {
            range "3..10";
          }
          default "5";
          description
            "Number of times that MAC duplication is detected in a period.";
        }
        leaf cycle {
          type uint16 {
            range "60..900";
          }
          units "s";
          must "../cycle mod 10 = 0";
          default "180";
          description
            "Interval at which MAC duplication is detected.";
        }
        leaf recycle {
          type uint16 {
            range "120..43200";
          }
          units "s";
          must "../recycle mod 10 = 0";
          default "540";
          description
            "Period after which suppression on MAC duplication is removed.";
        }
        leaf acl-name-or-id {
          type acl:acl4-identity;
          must "/acl:acl/acl:groups/acl:group[acl:identity=current()] or /acl:acl/acl:groups/acl:group[acl:number=number(current())]";
          description
          "The Name or number of a LinkEth ACL is used by a filtering policy to avoid the specific mac address being detected as mac duplication. The number ranges from 4000 to 4999, and the name must start with a letter.";
        }
      }
      container static-esis {
        description
          "List of static ESI.";
        list static-esi {
          key "esi";
          description
            "Configure instance of static ESI.";
          leaf esi {
            type esi;
            description
              "Static ESI, in the format of 00xx.xxxx.xxxx.xxxx.xxxx, in which x ranges from 0 to F. A static ESI cannot be all 0s.";
          }
          leaf redundancy-mode {
            type esi-redundancy-mode;
            default "none";
            description
              "Redundancy mode.";
          }
          leaf df-election-type {
            type df-election-type;
            default "default";
            description
              "The DF election type of ESI.";
          }
          leaf preference {
            when "../df-election-type='preference-based'";
            type uint16 {
              range "0..65535";
            }
            default "32767";
            description
              "The preference of ESI.";
          }
          leaf non-revertive {
            when "../df-election-type='preference-based'";
            type boolean;
            default "false";
            description
              "Enable/disable non-revertive mode.";
          }
          leaf df-election {
            when "../redundancy-mode='single-active'";
            type boolean;
            must "(current()='true' and (not(/ifm:ifm/ifm:interfaces/ifm:interface[evpn:evpn/evpn:esi=current()/../esi]/ifm:type) or (/ifm:ifm/ifm:interfaces/ifm:interface[evpn:evpn/evpn:esi=current()/../esi]/ifm:type!='Virtual-Ethernet'))) or current()='false'";
            default "false";
            description
              "Enable/disable DF election mode.";
          }
        }
      }
      container dynamic-esis {
        description
          "List of dynamic ESI.";
        list dynamic-esi {
          key "esi-name";
          description
            "Configure instance of dynamic ESI.";
          leaf esi-name {
            type string {
              length "1..31";
            }
            description
              "Dynamic ESI name is a string of 1 to 31 characters, which begins with a-z or A-Z.";
          }
          leaf redundancy-mode {
            type esi-redundancy-mode;
            default "none";
            description
              "Redundancy mode.";
          }
          leaf df-election-type {
            type df-election-type;
            default "default";
            description
              "The DF election type of ESI.";
          }
          leaf preference {
            when "../df-election-type='preference-based'";
            type uint16 {
              range "0..65535";
            }
            default "32767";
            description
              "The preference of ESI.";
          }
          leaf non-revertive {
            when "../df-election-type='preference-based'";
            type boolean;
            default "false";
            description
              "Enable/disable non-revertive mode.";
          }
        }
      }
      container l3-static-esis {
        description
          "List of L3 static ESI.";
        list l3-static-esi {
          key "esi";
          unique "alias-name";
          description
            "Configure instance of L3 static ESI.";
          leaf esi {
            type l3esi;
            description
              "L3 Static ESI, in the format of 04xx.xxxx.xx00.0000.0000, in which x ranges from 0 to F.";
          }
          leaf alias-name {
            type string {
              length "1..31";
            }
            mandatory true;
            description
              "Specifies alias name of esi.";
            ext:operation-exclude update {
              description "The node cannot be modified, when node is already configured.";
            }
          }
        }
      }
    }
    container global-suppressed-statistics {
      config false;
      description
        "Statistics of all EVPN instances mac-duplication suppressed number.";
      leaf suppressed-num-all {
        type uint32 {
          range "0..4294967295";
        }
        description
          "Statistics of all suppressed mac-duplication.";
      }
    }
    container instances {
      description
        "List of EVPN instance.";
      list instance {
        must "/evpn:evpn/evpn:base-process/evpn:evpn-overlay='true'";
        key "name";
        unique "normal-evpn/rd";
        unique "b-evpn/rd";
        unique "bd-evpn/rd";
        unique "vpws-evpn/rd";
        description
          "Configure EVPN instance.";
        leaf name {
          type name-type {
            length "1..31";
          }
          must "../name!='_public_'";
          description
            "EVPN instance name.";
        }
        leaf type {
          ext:operation-exclude update|delete;
          type evpn-type;
          default "normal";
          description
            "The value specifies the type of EVPN instance.";
        }
        leaf label-policy {
          type evpn-apply-label-mode;
          config false;
          description
            "Label policy of the EVPN instance.";
        }
        leaf effected-rd {
          type string {
            length "0..21";
          }
          config false;
          description
            "The RD has taken effect.";
        }
        container normal-evpn{
          when "../type = 'normal'";
          description
            "Configure normal mode of EVPN instance.";
          leaf description {
            type string {
              length "1..63";
              pattern '([^?]*)';
            }
          description
            "The description for EVPN instance.";
          }
          leaf rd {
            type string {
              length "3..21";
            }
            description
              "An EVPN instance address family takes effect only after it is configured with an RD. The RD can be in any of the following formats:
1. 16-bit AS number:32-bit user-defined number, 101:3 for example. A 16-bit AS number ranges from 0 to 65535, and a user-defined number ranges from 0 to 4294967295. The AS number and user-defined number cannot be both 0s. This means that the RD value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
          }
          leaf tunnel-policy-name {
            when "../rd or /evpn:evpn/evpn:base-process/evpn:auto-rd-ip";
            type leafref {
              path "/tnlm:tunnel-management/tnlm:tunnel-policys/tnlm:tunnel-policy/tnlm:name";
            }
            must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='gre6']) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-policy']) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-flow-group'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='colored-sr-te']))";
            description
              "Tunnel policy name.";
          }
          leaf import-policy-name {
            when "../rd or /evpn:evpn/evpn:base-process/evpn:auto-rd-ip";
            type leafref {
              path "/rtp:routing-policy/rtp:policy-definitions/rtp:policy-definition/rtp:name";
            }
            description
              "The name of specify import route policy.";
          }
          leaf export-policy-name {
            when "../rd or /evpn:evpn/evpn:base-process/evpn:auto-rd-ip";
            type leafref {
              path "/rtp:routing-policy/rtp:policy-definitions/rtp:policy-definition/rtp:name";
            }
            description
              "The name of specify export route policy.";
          }
          leaf local-remote-frr {
            type local-remote-frr-enable-type;
            default "default";
            description
              "Enable/disable local MAC and remote MAC to form FRR.";
          }
          leaf mac-balance-enable {
            type boolean;
            default "false";
            description
              "Enable/disable MAC balance.";
          }
          leaf isolate-spoken {
            type isolate-spoken-type;
            default "default";
            description
              "Forwarding isolation between AC interfaces under EVPN.";
          }
          leaf export-acl-name-or-id {
            type acl:acl4-identity;
            must "/acl:acl/acl:groups/acl:group[acl:identity=current()] or /acl:acl/acl:groups/acl:group[acl:number=number(current())]";
            description
              "Name or number of an IPv4 ACL used by a filtering policy to filter the routes to be advertised to a specified peer. The number ranges from 4000 to 4999, and the name must start with a letter.";
          }
          leaf import-acl-name-or-id {
            type acl:acl4-identity;
            must "/acl:acl/acl:groups/acl:group[acl:identity=current()] or /acl:acl/acl:groups/acl:group[acl:number=number(current())]";
            description
              "Name or number of an IPv4 ACL used by a filtering policy to filter the routes received from a specified peer. The number ranges from 4000 to 4999, and the name must start with a letter. By default, no ACL-based filtering policy is configured, and therefore all EVN BGP routes can be accepted.";
          }
          leaf etree-enable {
            type boolean;
            default "false";
            description
              "Enable/disable EVPN E-Tree.";
          }
          leaf control-word {
            type boolean;
            default "false";
            description
              "Enable/disable EVPN control word.";
          }
          leaf nexthop-recursive-lookup-restrain {
            type boolean;
            default "true";
            description
              "Enable/disable EVPN nexthop recursive lookup restrain.";
          }
          leaf mac-duplication-switch {
            type boolean;
            default "true";
            description
              "Enable/disable MAC duplication.";
          }
          container rts {
            when "../rd or /evpn:evpn/evpn:base-process/evpn:auto-rd-ip";
            description "List of RTs.";
            list rt {
              key "vrf-rt-type vrf-rt-value";
              description
                "Configure RTs to control route advertisement between network nodes. Before sending a VPN route to a PE, the local PE adds an Export RT to the route. After receiving a route from another PE, the local PE compares the local Import RT and the Export RT carried in the VPN route and adds the route to the VPN instance only when the two RTs are the same.";
              leaf vrf-rt-type {
                type vrf-rt-type;
                description
                  "RT type (export-extcommunity or import-extcommunity)
export-extcommunity: Specifies the value of the extended community attribute of the route from an outbound interface to the destination VPN. 
import-extcommunity: Specifies the value of the extended community attribute. Routes with such an extended community value can be accepted.";
              }
              leaf vrf-rt-value {
                type string {
                  length "3..21";
                }
                description
                  "RT value, in any of the following formats:
1. 16-bit AS number:32-bit user-defined number, 1:3 for example. A 16-bit AS number ranges from 0 to 65535, and a user-defined number ranges from 0 to 4294967295. The AS number and user-defined number cannot be both 0s. This means that the VPN Target value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
              }
            }
          }
          container mac-duplication {
            must "((./period and ./cycle) and (./cycle mod 10 = 0)) or (not(./period) and not(./cycle))";
            presence "normal MAC duplication";
            description
              "Enable/disable MAC duplication.";
            leaf period {
              type uint8 {
                range "3..10";
              }
              description
                "Number of times that MAC duplication is detected in a period.";
            }
            leaf cycle {
              type uint16 {
                range "60..900";
              }
              units "s";
              description
                "Interval at which MAC duplication is detected. The value must be a multiple of 10.";
            }
            leaf recycle {
              type uint16 {
                range "120..43200";
              }
              units "s";
              must "../recycle mod 10 = 0";
              description
                "Period after which suppression on MAC duplication is removed. The value must be a multiple of 10.";
            }
            leaf blackhole {
              type boolean;
              default "false";
              description
                "Enable/disable a blackhole flag.";
            }
            leaf acl-name-or-id {
              type acl:acl4-identity;
              must "/acl:acl/acl:groups/acl:group[acl:identity=current()] or /acl:acl/acl:groups/acl:group[acl:number=number(current())]";
              description
              "The Name or number of a LinkEth ACL is used by a filtering policy to avoid the specific mac address being detected as mac duplication. The number ranges from 4000 to 4999, and the name must start with a letter.";
            }
          }
          container mac-duplication-infos {
            config false;
            description
              "Operational state of information aggregation about MAC addresses that are duplicate in an EVPN instance.";
            uses mac-duplication-infos-type;
          }
        }
        container b-evpn{
          when "../type = 'b-evpn'";
          description
            "Configure backbone mode of EVPN instance.";
          leaf description {
            type string {
              length "1..63";
              pattern '([^?]*)';
            }
            description
              "The description for EVPN instance.";
            }
          leaf rd {
            type string {
              length "3..21";
            }
            description
              "An EVPN instance address family takes effect only after it is configured with an RD. The RD can be in any of the following formats:
1. 16-bit AS number:32-bit user-defined number, 101:3 for example. A 16-bit AS number ranges from 0 to 65535, and a user-defined number ranges from 0 to 4294967295. The AS number and user-defined number cannot be both 0s. This means that the RD value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
          }
          leaf bmac {
            when "../rd";
            type pub-type:mac-address {
              length "0..255";
            }
            description
              "Backbone bridging source MAC.";
          }
          leaf tunnel-policy-name {
            when "../rd";
            type leafref {
              path "/tnlm:tunnel-management/tnlm:tunnel-policys/tnlm:tunnel-policy/tnlm:name";
            }
            must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='gre6']) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-policy']) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-flow-group'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='bgp']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='colored-sr-te']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='sr-te-policy']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='flex-algo-lsp']))";
            description
              "Tunnel policy name.";
          }
          leaf nexthop-recursive-lookup-restrain {
            type boolean;
            default "true";
            description
              "Enable/disable EVPN nexthop recursive lookup restrain.";
          }
          container rts {
            when "../rd";
            description "List of RTs.";
            list rt {
              key "vrf-rt-type vrf-rt-value";
              description
                "Configure RTs to control route advertisement between network nodes. Before sending a VPN route to a PE, the local PE adds an Export RT to the route. After receiving a route from another PE, the local PE compares the local Import RT and the Export RT carried in the VPN route and adds the route to the VPN instance only when the two RTs are the same.";
              leaf vrf-rt-type {
                type vrf-rt-type;
                description
                  "RT type (export-extcommunity or import-extcommunity)
export-extcommunity: Specifies the value of the extended community attribute of the route from an outbound interface to the destination VPN. 
import-extcommunity: Specifies the value of the extended community attribute. Routes with such an extended community value can be accepted.";
              }
              leaf vrf-rt-value {
                type string {
                  length "3..21";
                }
                description
                  "RT value, in any of the following formats:
1. 16-bit AS number:32-bit user-defined number, 1:3 for example. A 16-bit AS number ranges from 0 to 65535, and a user-defined number ranges from 0 to 4294967295. The AS number and user-defined number cannot be both 0s. This means that the VPN Target value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
              }
            }
          }
        }
        container i-evpn {
          when "../type = 'i-evpn'";
          description
            "Configure PBB EVPN instance.";
          leaf description {
            type string {
              length "1..63";
              pattern '([^?]*)';
            }
            description
              "The description for EVPN instance.";
          }
          leaf tag {
            ext:operation-exclude update;
            type uint32 {
              range "0..16777215";
            }
            description
              "Specify an I-SID.";
          }
          leaf b-evpn-name {
            ext:operation-exclude update;
            when "../tag";
            type leafref {
              path "/evpn:evpn/evpn:instances/evpn:instance/evpn:name";
            }
            must "/evpn:evpn/evpn:instances/evpn:instance[evpn:name=current()]/evpn:type='b-evpn'";
            description
              "Binding an I-EVPN instance with a B-EVPN instance.";
          }
          leaf bmac {
            when "../tag";
            type pub-type:mac-address {
              length "0..255";
            }
            description
              "Backbone bridging source MAC.";
          }
        }
        container bd-evpn {
          when "../type = 'bd-evpn'";
          description
            "Configure BD exclusive mode of EVPN instance.";
          leaf description {
            type string {
              length "1..63";
              pattern '([^?]*)';
            }
            description
              "The description for EVPN instance.";
          }
          leaf rd {
            type string {
              length "3..21";
            }
            description
              "An EVPN instance address family takes effect only after it is configured with an RD. The RD can be in any of the following formats:
1. 16-bit AS number:32-bit user-defined number, 101:3 for example. A 16-bit AS number ranges from 0 to 65535, and a user-defined number ranges from 0 to 4294967295. The AS number and user-defined number cannot be both 0s. This means that the RD value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
          }
          leaf import-policy-name {
            when "../rd or /evpn:evpn/evpn:base-process/evpn:auto-rd-ip";
            type leafref {
              path "/rtp:routing-policy/rtp:policy-definitions/rtp:policy-definition/rtp:name";
            }
            description
              "The name of specify import route policy.";
          }
          leaf export-policy-name {
            when "../rd or /evpn:evpn/evpn:base-process/evpn:auto-rd-ip";
            type leafref {
              path "/rtp:routing-policy/rtp:policy-definitions/rtp:policy-definition/rtp:name";
            }
            description
              "The name of specify export route policy.";
          }
          leaf mac-policy-name {
            when "../rd or /evpn:evpn/evpn:base-process/evpn:auto-rd-ip";
            type leafref {
              path "/rtp:routing-policy/rtp:policy-definitions/rtp:policy-definition/rtp:name";
            }
            description
              "The name of specify mac route policy.";
          }
          leaf tunnel-policy-name {
            when "../rd or /evpn:evpn/evpn:base-process/evpn:auto-rd-ip";
            type leafref {
              path "/tnlm:tunnel-management/tnlm:tunnel-policys/tnlm:tunnel-policy/tnlm:name";
            }
            must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-flow-group']) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='gre6'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='colored-sr-te']))";
            description
              "Tunnel policy name.";
          }
          leaf local-remote-frr {
            type local-remote-frr-enable-type;
            default "default";
            description
              "Enable local MAC and remote MAC to form FRR.";
          }
          leaf remote-frr {
            type local-remote-frr-enable-type;
            default "default";
            description
              "Enable remote MAC to form FRR.";
          }
          leaf default-color {
            when "../rd or /evpn:evpn/evpn:base-process/evpn:auto-rd-ip";
            type uint32 {
            range "0..4294967295";
            }
            description
              "Set default color for nexthop iteration.";
          }
          leaf mac-balance-enable {
            type boolean;
            default "false";
            description
              "Enable/disable MAC balance.";
          }
          leaf export-acl-name-or-id {
            type acl:acl4-identity;
            must "/acl:acl/acl:groups/acl:group[acl:identity=current()] or /acl:acl/acl:groups/acl:group[acl:number=number(current())]";
            description
              "Name or number of an IPv4 ACL used by a filtering policy to filter the routes to be advertised to a specified peer. The number ranges from 4000 to 4999, and the name must start with a letter. By default, no ACL-based filtering policy is configured, and therefore all EVN BGP routes can be advertised.";
          }
          leaf import-acl-name-or-id {
            type acl:acl4-identity;
            must "/acl:acl/acl:groups/acl:group[acl:identity=current()] or /acl:acl/acl:groups/acl:group[acl:number=number(current())]";
            description
              "Name or number of an IPv4 ACL used by a filtering policy to filter the routes received from a specified peer. The number ranges from 4000 to 4999, and the name must start with a letter. By default, no ACL-based filtering policy is configured, and therefore all EVN BGP routes can be accepted.";
          }
          leaf bypass-vxlan {
            type bypass-vxlan-enable-type;
            default "default";
            description
              "Enable bypass VXLAN capability.";
          }
          leaf etree-enable {
            type boolean;
            must "(../etree-enable='true' and not(../inclusive-provider-tunnel)) or (../etree-enable='false')";
            default "false";
            description
              "Enable/disable EVPN E-Tree.";
          }
          leaf srv6-mode {
            when "../rd or /evpn:evpn/evpn:base-process/evpn:auto-rd-ip";
            type srv6-mode;
            description
              "SRv6 iteration mode.";
          }
          leaf down-switch {
            when "(../rd or /evpn:evpn/evpn:base-process/evpn:auto-rd-ip) and ../srv6-mode='te'";
            type boolean;
            default "false";
            description
              "Enable/disable switch TE to BE if the associated TE tunnel goes down.";
          }
          leaf control-word {
            type boolean;
            default "false";
            description
              "Enable/disable EVPN control word.";
          }
          leaf mac-route-advertise {
            type mac-route-no-advertise-type;
            default "enable";
            description
              "Enable/disable local MAC routes from being advertised.";
          }
          leaf arp-route-generate-mac {
            type mac-route-no-advertise-type;
            default "disable";
            description
              "Enable/disable MAC/IP route to generate MAC.";
          }
          leaf mac-only-route-generate {
            type mac-route-no-advertise-type;
            default "enable";
            description
              "Enable/disable the function of generating EVPN MAC routes when both MAC address entries and ARP/ND entries contain local MAC addresses.";
          }
          leaf mac-frr-keep {
            type boolean;
            default "true";
            description
              "Enable/disable the function of keeping MAC to form FRR.";
          }
          leaf nexthop-priority {
            type nexthop-priority-address-type;
            description
              "Routes with next-hop IPv4 addresses and routes with next-hop IPv6 addresses coexist. If the next-hop address type is set to IPv4, routes with next-hop IPv4 addresses have a higher priority. If the next-hop address type is set to IPv6, routes with next-hop IPv6 addresses have a higher priority.";
          }
          leaf soo-check {
            type boolean;
            default "false";
            description
              "Enable/disable SoO attribute check.";
          }
          leaf sbfd-discriminator-advertise {
            type boolean;
            default "false";
            description
              "Enable/disable sbfd discriminator advertisement.";
          }
          leaf nexthop-recursive-lookup-restrain {
            type boolean;
            default "true";
            description
              "Enable/disable EVPN nexthop recursive lookup restrain.";
          }
          leaf timer-revert-delay {
            when "../rd or /evpn:evpn/evpn:base-process/evpn:auto-rd-ip";
            type uint32 {
              range "0..3600";
            }
            units "s";
            default "0";
            description
              "Set delay time of selecting routes in production.";
          }
          leaf mac-duplication-switch{
            type boolean;
            default "true";
            description
              "Enable/disable MAC duplication.";
          }
          leaf flow-label {
            type boolean;
            must "(../flow-label='true' and not(../srv6-mode='te') and not(../srv6-mode='be') and not(../inclusive-provider-tunnel) and not(/bd:bd/bd:instances/bd:instance[evpn:evpn/evpn:name=current()/../../evpn:name]/nvo3:nvo3/nvo3:vni-list[nvo3:split-horizon='true']/nvo3:vni)) or ../flow-label!='true'";
            default "false";
            description
              "Enable/disable EVPN flow label.";
          }
          leaf traffic-statistics {
            when "../rd or /evpn:evpn/evpn:base-process/evpn:auto-rd-ip";
            type boolean;
            must "(../traffic-statistics='true' and ../peer-traffic-statistics='false' and not(/bd:bd/bd:instances/bd:instance[evpn:evpn/evpn:name=current()/../../evpn:name]/nvo3:nvo3/nvo3:vni-list[nvo3:split-horizon='true']/nvo3:vni)) or ../traffic-statistics='false'";
            default "false";
            description
              "Enable/disable EVPN traffic statistics.";
          }
          leaf peer-traffic-statistics {
            when "../rd or /evpn:evpn/evpn:base-process/evpn:auto-rd-ip";
            type boolean;
            must "(../peer-traffic-statistics='true' and ../traffic-statistics='false' and not(../srv6-mode='te') and not(../srv6-mode='be') and not(/bd:bd/bd:instances/bd:instance[evpn:evpn/evpn:name=current()/../../evpn:name]/nvo3:nvo3/nvo3:vni-list[nvo3:split-horizon='true']/nvo3:vni)) or ../peer-traffic-statistics='false'";
            default "false";
            description
              "Enable/disable EVPN peer traffic statistics.";
          }
          container route-control {
            description "Configure about route control.";
            leaf srv6-advertise-mpls {
              type srv6-advertise-mpls-type;
              default "default";
              description
                "Configure SRv6 local route send to MPLS.";
            }
            leaf nexthop-resolve-aigp {
              type boolean;
              default "false";
              description
                "Enable/disable route with AIGP attribute for route selection.";
            }
            leaf mac-redirect-compatible {
              type inst-enable-type;
              default "default";
              description
                "Configure MAC redirect compatible.";
            }
            leaf macip-remote-suppress-local {
              type inst-enable-type;
              default "default";
              description
                "Enable/disable fast withdrawal of local non-preferred MAC/IP routes in an EVPN instance.";
            }
          }
          container rts {
            when "../rd or /evpn:evpn/evpn:base-process/evpn:auto-rd-ip";
            description "List of RTs.";
            list rt {
              key "vrf-rt-type vrf-rt-value";
              description
                "Configure RTs to control route advertisement between network nodes. Before sending a VPN route to a PE, the local PE adds an Export RT to the route. After receiving a route from another PE, the local PE compares the local Import RT and the Export RT carried in the VPN route and adds the route to the VPN instance only when the two RTs are the same.";
              leaf vrf-rt-type {
                type vrf-rt-type;
                description
                  "RT type (export-extcommunity or import-extcommunity)
export-extcommunity: Specifies the value of the extended community attribute of the route from an outbound interface to the destination VPN. 
import-extcommunity: Specifies the value of the extended community attribute. Routes with such an extended community value can be accepted.";
              }
              leaf vrf-rt-value {
                type string {
                  length "3..21";
                }
                description
                  "RT value, in any of the following formats:
1. 16-bit AS number:32-bit user-defined number, 1:3 for example. A 16-bit AS number ranges from 0 to 65535, and a user-defined number ranges from 0 to 4294967295. The AS number and user-defined number cannot be both 0s. This means that the VPN Target value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
              }
            }
          }
          container mac-duplication {
            must "((./period and ./cycle) and (./cycle mod 10 = 0)) or (not(./period) and not(./cycle))";
            presence "bd MAC duplication";
            description
              "Enable/disable MAC duplication.";
            leaf period {
              type uint8 {
                range "3..10";
              }
              description
                "Number of times that MAC duplication is detected in a period.";
            }
            leaf cycle {
              type uint16 {
                range "60..900";
              }
              units "s";
              description
                "Interval at which MAC duplication is detected. The value must be a multiple of 10.";
            }
            leaf recycle {
              type uint16 {
                range "120..43200";
              }
              units "s";
              must "../recycle mod 10 = 0";
              description
                "Period after which suppression on MAC duplication is removed. The value must be a multiple of 10.";
            }
            leaf blackhole {
              type boolean;
              default "false";
              description
                "Enable/disable a blackhole flag.";
            }
            leaf source-blackhole {
              when "../blackhole='true'";
              type boolean;
              default "false";
              description
                "Enable/disable blackhole flag. After MAC duplication is suppressed, if a blackhole flag is set, the source port is blocked. If no blackhole flag is set, the source port is not blocked.";
            }
            leaf acl-name-or-id {
              type acl:acl4-identity;
              must "/acl:acl/acl:groups/acl:group[acl:identity=current()] or /acl:acl/acl:groups/acl:group[acl:number=number(current())]";
              description
              "The Name or number of a LinkEth ACL is used by a filtering policy to avoid the specific mac address being detected as mac duplication. The number ranges from 4000 to 4999, and the name must start with a letter.";
            }
          }
          container mac-duplication-statistics {
            config false;
            description
              "Statistics of EVPN instance mac-duplication suppressed number.";
            leaf suppressed-num {
              type uint32 {
              range "1..4294967295";
            }
              description
                "Statistics of suppressed mac-duplication.";
            }
          }
          container mac-duplication-infos {
            config false;
            description
              "Operational state of information aggregation about MAC addresses that are duplicate in an EVPN instance.";
            uses mac-duplication-infos-type;
          }
          container inclusive-provider-tunnel {
            must "(../control-word!='true' and ../etree-enable!='true' and not(../srv6-mode)) or not(../inclusive-provider-tunnel)";
            presence "EVI-IPMSI view";
            description
                "Enable/disable mLDP P2MP configuration.";
            container root {
              presence "EVI-IPMSI view";
              description
                "Enable/disable mLDP P2MP root configuration.";
              leaf data-switch-disable {
                type boolean;
                default "false";
                description
                  "Enable/disable data switch configuration.";
              }
              leaf data-delay-time {
                type uint32 {
                  range "1..300";
                }
                units "s";
                description
                  "Set a hold-off time for an mLDP P2MP tunnel to go Up.";
              }
              container p2mp {
                presence "MLDP P2MP view";
                description
                  "Enable/disable mLDP P2MP configuration.";
                leaf root-ip {
                  type inet:ipv4-address-no-zone;
                  description
                  "Root address of P2MP tunnel.";
                }
                leaf opaque-value {
                  type string {
                    length "1..4096";
                  }
                  config false;
                  description
                    "Opaque value (in the TLV format) that is carried in packets and is not decoded.";
                }
                leaf state {
                  type evpn-state;
                  config false;
                  description
                    "P2MP tunnel status.";
                }
              }
            }
            container leaf {
              presence "EVI-IPMSI view";
              description
                "Enable/disable mLDP P2MP leaf configuration.";
              leaf opaque-value {
                type string {
                  length "1..4096";
                }
                config false;
                description
                  "Original opaque value in a message. The value is displayed in the format of TLV.";
              }
              leaf state {
                type evpn-state;
                config false;
                description
                  "P2MP tunnel status.";
              }
              container use-next-hops {
                description
                "List of root addresses for leaf node.";
                list use-next-hop {
                  key "root-ip";
                  description
                  "Configure root address for leaf node.";
                  leaf root-ip {
                    type inet:ipv4-address-no-zone;
                    description
                      "Root address for leaf node.";
                  }
                }
              }
            }
          }
          container remote-label-infos {
            description "List of remote peer label.";
            list remote-label-info {
              key "peer-ip label mode";
              config false;
              description "Operational data of remote peer label info.";
              leaf peer-ip {
                type inet:ip-address-no-zone;
                description "Peer IP address of remote peer.";
              }
              leaf label {
                type uint32;
                description "Remote label.";
              }
              leaf mode {
                type evpn-peer-mode;
                description "EVPN peer mode.";
              }
              leaf entries-num {
                type uint32;
                description "Remote label number.";
              }
            }
          }
          container remote-sid-infos {
            description "List of remote SID info.";
            list remote-sid-info {
              key "peer-ip sid mode";
              config false;
              description "Operational data of remote SID info.";
              leaf peer-ip {
                type inet:ip-address-no-zone;
                description "Peer IP address of remote peer.";
              }
              leaf sid {
                type inet:ip-address-no-zone;
                description "Remote SID.";
              }
              leaf mode {
                type evpn-peer-mode;
                description "EVPN peer mode.";
              }
              leaf entries-num {
                type uint32;
                description "Remote SID number.";
              }
            }
          }
          container traffic-statistics-info {
            config false;
            description
              "Operational data of traffic statistics.";
            leaf last-clear-time {
              type yang:date-and-time;
              description
                "Time when traffic statistics were cleared last time.";
            }
            leaf in-bytes-rate {
              type uint64;
              description
                "Rate of bytes received.";
            }
            leaf out-bytes-rate {
              type uint64;
              description
                "Rate of bytes sent.";
            }
            leaf in-packets-rate {
              type uint64;
              description
                "Rate of packets received.";
            }
            leaf out-packets-rate {
              type uint64;
              description
                "Rate of packets sent.";
            }
            leaf in-bytes {
              type uint64;
              description
                "Number of bytes received.";
            }
            leaf out-bytes {
              type uint64;
              description
                "Number of bytes sent.";
            }
            leaf in-packets {
              type uint64;
              description
                "Number of packets received.";
            }
            leaf out-packets {
              type uint64;
              description
                "Number of packets sent.";
            }
            leaf in-unicast-packets {
              type uint64;
              description
                "Number of unicast packets received.";
            }
            leaf out-unicast-packets {
              type uint64;
              description
                "Number of unicast packets sent.";
            }
            leaf in-multicast-packets {
              type uint64;
              description
                "Number of multicast packets received.";
            }
            leaf out-multicast-packets {
              type uint64;
              description
                "Number of multicast packets sent.";
            }
            leaf in-broadcast-packets {
              type uint64;
              description
                "Number of broadcast packets received.";
            }
            leaf out-broadcast-packets {
              type uint64;
              description
                "Number of broadcast packets sent.";
            }
          }
          container peer-traffic-statistics-infos {
            config false;
            description
              "List of peer traffic statistics.";
            list peer-traffic-statistics-info {
              key "peer-ip";
              config false;
              description
                "Operational data of peer traffic statistics.";
              leaf peer-ip {
                type inet:ipv4-address-no-zone;
                description
                  "IPv4 address of remote peer.";
              }
              leaf last-clear-time {
                type yang:date-and-time;
                description
                  "Time when peer traffic statistics were cleared last time.";
              }
              leaf out-bytes-rate {
                type uint64;
                description
                  "Rate of bytes sent.";
              }
              leaf out-packets-rate {
                type uint64;
                description
                  "Rate of packets sent.";
              }
              leaf out-bytes {
                type uint64;
                description
                  "Number of bytes sent.";
              }
              leaf out-packets {
                type uint64;
                description
                  "Number of packets sent.";
              }
              leaf out-unicast-packets {
                type uint64;
                description
                  "Number of unicast packets sent.";
              }
              leaf out-multicast-packets {
                type uint64;
                description
                  "Number of multicast packets sent.";
              }
              leaf out-broadcast-packets {
                type uint64;
                description
                  "Number of broadcast packets sent.";
              }
            }
          }
        }
        container vpws-evpn{
          when "../type = 'vpws-evpn'";
          description
            "Configure VPWS mode of EVPN instance.";
          leaf description {
            type string {
              length "1..63";
              pattern '([^?]*)';
            }
            description
              "The description for EVPN instance.";
          }
          leaf rd {
            type string {
              length "3..21";
            }
            description
              "An EVPN instance address family takes effect only after it is configured with an RD. The RD can be in any of the following formats:
1. 16-bit AS number:32-bit user-defined number, 101:3 for example. A 16-bit AS number ranges from 0 to 65535, and a user-defined number ranges from 0 to 4294967295. The AS number and user-defined number cannot be both 0s. This means that the RD value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
          }
          leaf import-policy-name {
            when "../rd or /evpn:evpn/evpn:base-process/evpn:auto-rd-ip";
            type leafref {
              path "/rtp:routing-policy/rtp:policy-definitions/rtp:policy-definition/rtp:name";
            }
            description
              "The name of specify import route policy.";
          }
          leaf export-policy-name {
            when "../rd or /evpn:evpn/evpn:base-process/evpn:auto-rd-ip";
            type leafref {
              path "/rtp:routing-policy/rtp:policy-definitions/rtp:policy-definition/rtp:name";
            }
            description
              "The name of specify export route policy.";
          }
          leaf tunnel-policy-name {
            when "../rd or /evpn:evpn/evpn:base-process/evpn:auto-rd-ip";
            type leafref {
              path "/tnlm:tunnel-management/tnlm:tunnel-policys/tnlm:tunnel-policy/tnlm:name";
            }
            must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='gre6'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='colored-sr-te']))";
            description
              "Tunnel policy name.";
          }
          leaf local-remote-frr {
            type local-remote-frr-enable-type;
            default "default";
            description
              "Enable local MAC and remote MAC to form FRR.";
          }
          leaf remote-frr {
            type local-remote-frr-enable-type;
            default "default";
            description
              "Enable remote MAC to form FRR.";
          }
          leaf default-color {
            when "../rd or /evpn:evpn/evpn:base-process/evpn:auto-rd-ip";
            type uint32 {
            range "0..4294967295";
            }
            description
              "Set default color for nexthop iteration.";
          }
          leaf export-acl-name-or-id {
            type acl:acl4-identity;
            must "/acl:acl/acl:groups/acl:group[acl:identity=current()] or /acl:acl/acl:groups/acl:group[acl:number=number(current())]";
            description
              "Name or number of an IPv4 ACL used by a filtering policy to filter the routes to be advertised to a specified peer. The number ranges from 4000 to 4999, and the name must start with a letter. By default, no ACL-based filtering policy is configured, and therefore all EVN BGP routes can be advertised.";
          }
          leaf import-acl-name-or-id {
            type acl:acl4-identity;
            must "/acl:acl/acl:groups/acl:group[acl:identity=current()] or /acl:acl/acl:groups/acl:group[acl:number=number(current())]";
            description
              "Name or number of an IPv4 ACL used by a filtering policy to filter the routes received from a specified peer. The number ranges from 4000 to 4999, and the name must start with a letter. By default, no ACL-based filtering policy is configured, and therefore all EVN BGP routes can be accepted.";
          }
          leaf timer-revert-delay {
            when "../rd or /evpn:evpn/evpn:base-process/evpn:auto-rd-ip";
            type uint32 {
              range "0..3600";
            }
            units "s";
            default "0";
            description
              "Set delay time of selecting routes in production.";
          }
          leaf srv6-mode {
            when "../rd or /evpn:evpn/evpn:base-process/evpn:auto-rd-ip";
            type srv6-mode;
            description
              "SRv6 iteration mode.";
          }
          leaf down-switch {
            when "(../rd or /evpn:evpn/evpn:base-process/evpn:auto-rd-ip) and ../srv6-mode='te'";
            type boolean;
            default "false";
            description
              "Enable/disable TE to BE if the associated TE tunnel goes down.";
          }
          leaf nexthop-recursive-lookup-restrain {
            type boolean;
            default "true";
            description
              "Enable/disable EVPN nexthop recursive lookup restrain.";
          }
          leaf nexthop-priority {
            type nexthop-priority-address-type;
            description
              "Routes with next-hop IPv4 addresses and routes with next-hop IPv6 addresses coexist. If the next-hop address type is set to IPv4, routes with next-hop IPv4 addresses have a higher priority. If the next-hop address type is set to IPv6, routes with next-hop IPv6 addresses have a higher priority.";
          }
          leaf soo-check {
            type boolean;
            default "false";
            description
              "Enable/disable SoO attribute check.";
          }
          leaf sbfd-discriminator-advertise {
            type boolean;
            default "false";
            description
              "Enable/disable sbfd discriminator advertisement.";
          }
          container route-control {
            description "Configure about route control.";
            leaf srv6-advertise-mpls {
              type srv6-advertise-mpls-type;
              default "default";
              description
                "Configure SRv6 local route send to MPLS.";
            }
            leaf nexthop-resolve-aigp {
              type boolean;
              default "false";
              description
                "Enable/disable route with AIGP attribute for route selection.";
            }
          }
          container rts {
            when "../rd or /evpn:evpn/evpn:base-process/evpn:auto-rd-ip";
            description "List of RTs.";
            list rt {
              key "vrf-rt-type vrf-rt-value";
              description
                "Configure RTs to control route advertisement between network nodes. Before sending a VPN route to a PE, the local PE adds an Export RT to the route. After receiving a route from another PE, the local PE compares the local Import RT and the Export RT carried in the VPN route and adds the route to the VPN instance only when the two RTs are the same.";
              leaf vrf-rt-type {
                type vrf-rt-type;
                description
                  "RT type (export-extcommunity or import-extcommunity)
export-extcommunity: Specifies the value of the extended community attribute of the route from an outbound interface to the destination VPN. 
import-extcommunity: Specifies the value of the extended community attribute. Routes with such an extended community value can be accepted.";
              }
              leaf vrf-rt-value {
                type string {
                  length "3..21";
                }
                description
                  "RT value, in any of the following formats:
1. 16-bit AS number:32-bit user-defined number, 1:3 for example. A 16-bit AS number ranges from 0 to 65535, and a user-defined number ranges from 0 to 4294967295. The AS number and user-defined number cannot be both 0s. This means that the VPN Target value cannot be 0:0.
2. 32-bit IP address:16-bit user-defined number, 192.168.122.15:1 for example. The IP address ranges from 0.0.0.0 to 255.255.255.255, and the user-defined number ranges from 0 to 65535.
3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
              }
            }
          }
          container remote-label-infos {
            description "List of remote peer label.";
            list remote-label-info {
              key "peer-ip label mode";
              config false;
              description "Operational data of remote peer label info.";
              leaf peer-ip {
                type inet:ip-address-no-zone;
                description "Peer IP address of remote peer.";
              }
              leaf label {
                type uint32;
                description "Remote label.";
              }
              leaf mode {
                type evpn-peer-mode;
                description "EVPN peer mode.";
              }
              leaf entries-num {
                type uint32;
                description "Remote label number.";
              }
            }
          }
          container remote-sid-infos {
            description "List of remote SID info.";
            list remote-sid-info {
              key "peer-ip sid mode";
              config false;
              description "Operational data of remote SID info.";
              leaf peer-ip {
                type inet:ip-address-no-zone;
                description "Peer IP address of remote peer.";
              }
              leaf sid {
                type inet:ip-address-no-zone {
                }
                description "Remote SID.";
              }
              leaf mode {
                type evpn-peer-mode;
                description "EVPN peer mode.";
              }
              leaf entries-num {
                type uint32;
                description "Remote SID number.";
              }
            }
          } 
        }
        container tunnel-infos {
          config false;
          description
            "List of tunnel informations.";
          list tunnel-info {
            key "type peer-ip id";
            description
              "Operational state of tunnel informations.";
            leaf type {
              type tunnel-type;
              description
                "Tunnel's type.";
            }
            leaf peer-ip {
              type inet:ip-address-no-zone;
              description
                "Nexthop address through which the packet has to be sent.";
            }
            leaf id {
              type uint32 {
                range "0..4294967295";
              }
              description
                "Tunnel's ID.";
            }
            leaf color {
              type uint32 {
                range "0..4294967295";
              }
              description
                "Color information for tunnel.";
            }
            leaf name {
              type string {
                length "0..256";
              }
              description
                "Tunnel's name.";
            }
          }
        }
        container per-instance-label {
          config false;
          description
            "Operational data of label shared by all private network routes in the EVPN instance.";
          leaf unicast-label {
            type uint32;
            description
              "Label shared by unicast routes in the EVPN instance.";
          }
          leaf bum-label {
            type uint32;
            description
              "Label shared by bum routes in the EVPN instance.";
          }
          leaf bypass-label {
            type uint32;
            description
              "Label shared by bypass routes in the EVPN instance.";
          }
        }
        container df-infos {
          config false;
          description
            "List of DF info.";
          list df-info {
            key "esi";
            description
              "Operational data of the Df information.";
            leaf esi {
              type esi;
              description
                "ESI, in the format of 00xx.xxxx.xxxx.xxxx.xxxx or 01xx.xxxx.xxxx.xxxx.xxxx, in which x ranges from 0 to F. A static ESI cannot be all 0s.";
            }
            leaf df-result {
              type df-result;
              description
                "DF result.";
            }
            container pref-elec-infos {
              config false;
              description
                "List of information about DF election.";
              list pref-elec-info {
                key "origin-ip";
                description
                  "Operational data of DF election information.";
                leaf origin-ip {
                  type inet:ip-address-no-zone;
                  description
                    "Source IP address of a PE.";
                }
                leaf df-result {
                  type df-election-result;
                  description
                    "DF election result, which can be DF or backup DF.";
                }
                leaf preference {
                  type uint16 {
                    range "0..65535";
                  }
                  default "32767";
                  description
                    "Preference of ESI.";
                }
                leaf dp {
                  type uint8;
                  description
                    "The non-preemption mode is used for DF election.";
                }
                leaf ac-df {
                  type uint8;
                  description
                    "The AC status affects DF election.";
                }
              }
            }
          }
        }
        container interface-df-infos {
          config false;
          description
            "List of DF info of a interface.";
          list interface-df-info {
            key "esi interface-name";
            description
              "Operational data of the Df information of a interface.";
            leaf esi {
              type esi;
              description
                "ESI, in the format of 00xx.xxxx.xxxx.xxxx.xxxx or 01xx.xxxx.xxxx.xxxx.xxxx, in which x ranges from 0 to F. A static ESI cannot be all 0s.";
            }
            leaf interface-name {
              type leafref {
                path "/ifm:ifm/ifm:interfaces/ifm:interface/ifm:name";
              }
              description
                "The interface name.";
            }
            leaf df-result {
              type df-result;
              description
                "DF result.";
            }
            container pref-elec-infos {
              config false;
              description
                "List of information about DF election.";
              list pref-elec-info {
                key "origin-ip";
                description
                  "Operational data of DF election information.";
                leaf origin-ip {
                  type inet:ip-address-no-zone;
                  description
                    "Source IP address of a PE.";
                }
                leaf df-result {
                  type df-election-result;
                  description
                    "DF election result, which can be DF or backup DF.";
                }
                leaf preference {
                  type uint16 {
                    range "0..65535";
                  }
                  default "32767";
                  description
                    "Preference of ESI.";
                }
                leaf dp {
                  type uint8;
                  description
                    "The non-preemption mode is used for DF election.";
                }
                leaf ac-df {
                  type uint8;
                  description
                    "The AC status affects DF election.";
                }
              }
            }
          }
        }
        container pw-df-infos {
          config false;
          description
            "List of DF info of a PW.";
          list pw-df-info {
            key "esi";
            description
              "Operational data of the Df information of a PW.";
            leaf esi {
              type esi;
              description
                "ESI, in the format of 00xx.xxxx.xxxx.xxxx.xxxx or 01xx.xxxx.xxxx.xxxx.xxxx, in which x ranges from 0 to F. A static ESI cannot be all 0s.";
            }
            leaf peer-ip {
              type inet:ipv4-address-no-zone;
              description
                "Peer IP address of a PW.";
            }
            leaf vc-id {
              type uint32 {
                range "1..4294967295";
              }
              description
                "VC ID.";
            }
            leaf vc-type {
              type evpn:l2vpn-encapsulate-type;
              description
                "Encapsulation type of a PW.";
            }
            leaf df-result {
              type df-result;
              description
                "DF result.";
            }
          }
        }
        container df-timer-info {
          config false;
          description
            "Operational data of Df timer information.";
          container esi-infos { 
            description
              "List of displaying the information of the ESI Df timer.";
            list esi-info {
              key "esi";
              description
                "Operational data of the ESI Df timer information.";
              leaf esi {
                type esi;
                description
                  "ESI, in the format of 00xx.xxxx.xxxx.xxxx.xxxx or 01xx.xxxx.xxxx.xxxx.xxxx, in which x ranges from 0 to F. A static ESI cannot be all 0s.";
              }
              leaf timer-type {
                type df-timer-type;
                description
                  "Timer type.";
              }
              leaf timer-state {
                type df-timer-mode;
                description
                  "DF timer status.";
              }
              leaf time-left {
                type uint32;
                description
                  "Remaining time in second before the DF timer expires.";
              }
            }
          }
          container interface-infos {
            config false;
            description
              "List of displaying the information of the interface Df timer.";
            list interface-info {
              key "interface-name";
              description
                "Operational data of the interface Df timer information.";
              leaf interface-name {
                type leafref {
                  path "/ifm:ifm/ifm:interfaces/ifm:interface/ifm:name";
                }
                description
                  "The interface name.";
              }
              leaf bd-id {
                type uint32;
                description
                 "BD ID.";
              }
              leaf timer-type {
                type df-timer-type;
                description
                  "Timer type.";
              }
              leaf timer-state {
                type df-timer-mode;
                description
                  "DF timer status.";
              }
              leaf time-left {
                type uint32;
                description
                  "Remaining time in second before the DF timer expires.";
              }
            }
          }
           container pw-infos {
            config false;
            description
              "List of displaying the information of the PW Df timer.";
            list pw-info {
              key "peer-ip vc-id vc-type";
              description
                "Operational data of the PW Df timer information.";
              leaf peer-ip {
                type leafref {
                  path "/l2vpn:l2vpn/l2vpn:instances/l2vpn:instance/l2vpn:vpls/l2vpn:ldp-signaling/l2vpn:pws/l2vpn:pw/l2vpn:peer-ip";
                }
                description
                  "Peer IP address.";
              }
              leaf vc-id {
                type leafref {
                  path "/l2vpn:l2vpn/l2vpn:instances/l2vpn:instance/l2vpn:vpls/l2vpn:ldp-signaling/l2vpn:pws/l2vpn:pw/l2vpn:negotiation-vc-id";
                }
                description
                  "PW ID used to uniquely identify a VC.";
              }
              leaf vc-type {
                type leafref {
                  path "/l2vpn:l2vpn/l2vpn:instances/l2vpn:instance/l2vpn:vpls/l2vpn:ldp-signaling/l2vpn:pws/l2vpn:pw/l2vpn:encapsulation-type";
                }
                description
                  "Encapsulation type of a VPLS PW.";
              }
              leaf timer-type {
                type df-timer-type;
                description
                  "Timer type.";
              }
              leaf timer-state {
                type df-timer-mode;
                description
                  "DF timer status.";
              }
              leaf time-left {
                type uint32;
                description
                  "Remaining time in second before the DF timer expires.";
              }
            }
          }
          container evpl-infos {
            config false;
            description
              "List of displaying the information of the EVPL Df timer.";
            list evpl-info {
              key "evpl-id";
              description
                "Operational data of the EVPL Df timer information.";
              leaf evpl-id {
                  type uint32 {
                    range "1..4294967295";
                  }
                  description
                    "The identification of the EVPL instance.";
                }
              leaf bd-id {
                type uint32;
                description
                 "The identification of the BD.";
              }
              leaf timer-type {
                type df-timer-type;
                description
                  "Timer type.";
              }
              leaf timer-state {
                type df-timer-mode;
                description
                  "DF timer status.";
              }
              leaf time-left {
                type uint32;
                description
                  "Remaining time in second before the DF timer expires.";
              }
            }
          }
        }
        container esi-advance {
          config false;
          description
            "Operational data of the advanced information of an ESI.";
          container locals {
            description
              "List of displaying the advanced information for a local ESI.";
            list local {
              key "esi";
              description
                "Operational data of the advanced information of a local ESI.";
              leaf esi {
                type esi;
                description
                  "ESI, in the format of 00xx.xxxx.xxxx.xxxx.xxxx or 01xx.xxxx.xxxx.xxxx.xxxx, in which x ranges from 0 to F. A static ESI cannot be all 0s.";
              }
              leaf topology {
                type topology;
                description
                  "Network topology identified by an ESI.";
              }
            }
          }
          container remotes {
            description
              "List of displaying the advanced information for a remote ESI.";
            list remote {
              key "esi remote-peer";
              description
                "Operational data of the advanced information of a remote ESI.";
              leaf esi {
                type esi;
                description
                  "ESI, in the format of 00xx.xxxx.xxxx.xxxx.xxxx or 01xx.xxxx.xxxx.xxxx.xxxx, in which x ranges from 0 to F. A static ESI cannot be all 0s.";
              }
              leaf remote-peer {
                type inet:ip-address-no-zone;
                description
                  "IP address of a peer PE.";
              }
              leaf topology {
                type topology;
                description
                  "Network topology identified by an ESI.";
              }
            }
          }
        }
        container mac-routes {
          config false;
          description
            "List of MAC routes.";
          list mac-route {
            key "prefix rd from route-type-flag";
            config false;
            description
              "Statistics of MAC routes.";
            leaf prefix {
              type mac-prefix;
              description
                "MAC route prefix.";
            }
            leaf rd {
              type string {
                length "3..21";
              }
              description
                "Route distinguisher.";
            }
            leaf from {
              type inet:ip-address-no-zone;
              description
                "Source peer that sends a route.";
            }
            leaf route-type-flag {
              type best-flag-type;
              description
                "Route type.";
            }
            leaf source-address-family {
              type evpn:address-family-type;
              description
                "Source address family.";
            }
            leaf mpls-label1 {
              type uint32 {
                range "0..4294967295";
              }
              description
                "Label1, it means L2 VNI for MAC Route and L3 VNI for Prefix Route.";
            }
            leaf mpls-label2 {
              type uint32 {
                range "0..4294967295";
              }
              description
                "Label2, it means L3 VNI for MAC Route.";
            }
            leaf frr-out-interface {
              type string {
                length "1..64";
              }
              description
                "Local-remote frr direct out-interface.";
            }
            leaf frr-nexthop {
              type inet:ip-address-no-zone;
              description
                "Local-remote frr nexthop.";
            }
            leaf frr-out-tunnel-name {
              type string {
                length "1..256";
              }
              description
                "Local-Remote Frr Tunnel Out-Interface.";
            }
            leaf prefix-sid {
              type inet:ipv6-address-no-zone;
              description
                "Prefix-SID attribute.";
            }
            leaf bypass-prefix-sid {
              type inet:ipv6-address-no-zone;
              description
                "Bypass Prefix-SID attribute.";
            }
            leaf effect-nexthop {
              type inet:ip-address-no-zone;
              description
                "Effective nexthop.";
            }
            leaf redirect-out-interface {
              type string {
                length "1..64";
              }
              description
                "Redirect out-interface.";
            }
            uses routing-table-type {
              description
                "Routing table information.";
            }
            leaf behavior {
              when "../prefix-sid";
              type string {
                length "1..32";
              }
              description
                "Endpoint behavior.";
            }
            leaf bypass-behavior {
              when "../bypass-prefix-sid";
              type string {
                length "1..32";
              }
              description
                "Bypass endpoint behavior.";
            }
            leaf prefix-sid-structure {
              type string {
                length "1..36";
              }
              description
                "Prefix-SID structure attribute.";
            }
            leaf bypass-prefix-sid-structure {
              type string {
                length "1..36";
              }
              description
                "Bypass Prefix-SID structure attribute.";
            }
            container direct-pw-info {
              description
                "Operational data of direct outbound interface.";
              leaf peer-ip {
                type inet:ipv4-address-no-zone;
                description
                  "Peer IP address of a PW.";
              }
              leaf vc-id {
                type uint32 {
                  range "1..4294967295";
                }
                description
                  "VC ID.";
              }
              leaf vc-type {
                type evpn:l2vpn-encapsulate-type;
                description
                  "Encapsulation type of a PW.";
              }
            }
          }
        }
        container ad-routes {
          config false;
          description
            "List of AD routes.";
          list ad-route {
            key "prefix rd from route-type-flag";
            config false;
            description
              "Statistics of AD routes.";
            leaf prefix {
              type ad-prefix;
              description
                "AD route prefix.";
            }
            leaf rd {
              type string {
                length "3..21";
              }
              description
                "Route distinguisher.";
            }
            leaf from {
              type inet:ip-address-no-zone;
              description
                "Source peer that sends a route.";
            }
            leaf route-type-flag {
              type best-flag-type;
              description
                "Route type.";
            }
            leaf prefix-sid {
              type inet:ipv6-address-no-zone;
              description
                "Prefix-SID attribute.";
            }
            leaf bypass-prefix-sid {
              type inet:ipv6-address-no-zone;
              description
                "Bypass Prefix-SID attribute.";
            }
            uses routing-table-type {
              description
                "Routing table information.";
            }
            leaf behavior {
              when "../prefix-sid";
              type string {
                length "1..32";
              }
              description
                "Endpoint behavior.";
            }
            leaf bypass-behavior {
              when "../bypass-prefix-sid";
              type string {
                length "1..32";
              }
              description
                "Bypass endpoint behavior.";
            }
            leaf prefix-sid-structure {
              type string {
                length "1..36";
              }
              description
                "Prefix-SID structure attribute.";
            }
            leaf bypass-prefix-sid-structure {
              type string {
                length "1..36";
              }
              description
                "Bypass Prefix-SID structure attribute.";
            }
          }
        }
        container es-routes {
          config false;
          description
            "List of ES routes.";
          list es-route {
            key "prefix rd from route-type-flag";
            config false;
            description
              "Statistics of ES routes.";
            leaf prefix {
              type es-prefix;
              description
                "ES route prefix.";
            }
            leaf rd {
              type string {
                length "3..21";
              }
              description
                "Route distinguisher.";
            }
            leaf from {
              type inet:ip-address-no-zone;
              description
                "Source peer that sends a route.";
            }
            leaf route-type-flag {
              type best-flag-type;
              description
                "Route type.";
            }
            uses routing-table-type {
              description
                "Routing table information.";
            }
          }
        }
        container inclusive-routes {
          config false;
          description
            "List of inclusive routes.";
          list inclusive-route {
            key "prefix rd from route-type-flag";
            config false;
            description
              "Statistics of inclusive routes.";
            leaf prefix {
              type inclusive-prefix;
              description
                "Inclusive route prefix.";
            }
            leaf rd {
              type string {
                length "3..21";
              }
              description
                "Route distinguisher.";
            }
            leaf from {
              type inet:ip-address-no-zone;
              description
                "Source peer that sends a route.";
            }
            leaf route-type-flag {
              type best-flag-type;
              description
                "Route type.";
            }
            leaf prefix-sid {
              type inet:ipv6-address-no-zone;
              description
                "Prefix-SID attribute.";
            }
            uses routing-table-type {
              description
                "Routing table information.";
            }
            leaf behavior {
              when "../prefix-sid";
              type string {
                length "1..32";
              }
              description
                "Endpoint behavior.";
            }
            leaf prefix-sid-structure {
              type string {
                length "1..36";
              }
              description
                "Prefix-SID structure attribute.";
            }
          }
        }
        container mac-route-infos {
          config false;
          description
            "List of MAC routes.";
          list mac-route-info {
            key "prefix";
            description
              "Statistics of of MAC routes.";
            leaf prefix {
              type mac-prefix;
              description
                "MAC route prefix.";
            }
            container label-stacks {
              description
                "Statistics of EVPN label stacks.";
              uses evpn:label-stacks-type;
            }
          }
        }
        container evpl-df-infos {
          config false;
          description
            "List of EVPL DF info.";
          list evpl-df-info {
            key "esi evpl-id";
            description
              "Operational data of the EVPL Df information.";
            leaf esi {
              type esi;
              description
                "ESI, in the format of 00xx.xxxx.xxxx.xxxx.xxxx or 01xx.xxxx.xxxx.xxxx.xxxx, in which x ranges from 0 to F. A static ESI cannot be all 0s.";
            }
            leaf evpl-id {
              type uint32 {
                range "1..4294967295";
              }
              description
                "The identification of the EVPL instance.";
            }
            leaf df-result {
              type df-result;
              description
                "DF result.";
            }
            container pref-elec-infos {
              config false;
              description
                "List of information about EVPL DF election.";
              list pref-elec-info {
                key "origin-ip";
                description
                  "Operational data of EVPL DF election information.";
                leaf origin-ip {
                  type inet:ip-address-no-zone;
                  description
                    "Source IP address of a PE.";
                }
                leaf df-result {
                  type df-election-result;
                  description
                    "DF election result, which can be DF or backup DF.";
                }
                leaf preference {
                  type uint16 {
                    range "0..65535";
                  }
                  default "32767";
                  description
                    "Preference of ESI.";
                }
                leaf dp {
                  type uint8;
                  description
                    "The non-preemption mode is used for DF election.";
                }
                leaf ac-df {
                  type uint8;
                  description
                    "The AC status affects DF election.";
                }
              }
            }
          }
        }
      }
    }
    container remote-sids {
      config false;
      description
        "List of remote SID.";
      list remote-sid {
        key "remote-sid";
        description
            "Operational data of remote SID.";
        leaf remote-sid {
            type inet:ipv6-address-no-zone;
            description
              "Remote SID attribute.";
        }
        leaf locator-sid {
            type inet:ipv6-address-no-zone;
            description
              "Locator SID.";
        }
        leaf locator-mask-length {
            type uint8 {
              range "0..128";
            }
            description
              "Specify the mask length of a locator SID.";
        }
        leaf evpn-type {
            type evpn-type;
            description
              "The value specifies the Type of EVPN instance. The value must be normal/i-evpn/b-evpn/bd-evpn/vpws-evpn.";
        }
        leaf evpn-name {
            type name-type {
              length "1..31";
            }
            description
              "EVPN instance name.";
        }
        leaf bd-id {
            type uint32 {
              range "0..16777215";
            }
            description
              "The identification of the BD.";
        }
        leaf evpl-id {
            type uint32 {
              range "1..4294967295";
            }
            description
              "The identification of the EVPL instance.";
        }
      }
    }
    container default-parameter {
      config false;
      description
        "Operational data of EVPN initial configuration information.";
      leaf access-mode {
        type access-mode;
        description
          "EVPN access Mode.";
      }
      leaf service-mode {
        type service-mode;
        description
          "EVPN interface service Mode.";
      }
      leaf apply-label-mode {
        type apply-label-mode;
        description
          "EVPN apply label Mode.";
      }
    }
    container recover-timers {
      config false;
      description
        "List of EVPN recover timer informations.";
      list recover-timer {
        key "name";
        description
          "Operational state of EVPN recover timer informations.";
        leaf name {
          type leafref {
            path "/ifm:ifm/ifm:interfaces/ifm:interface/ifm:name";
          }
          description
            "The interface name.";
        }
        leaf mode {
          type timer-mode;
          description
            "Mode of EVPN recover timer.";
        }
        leaf begin-time {
          type yang:date-and-time;
          description
            "Begin time of EVPN recover timer.";
        }
        leaf end-time {
          type yang:date-and-time;
          description
            "End time of EVPN recover timer.";
        }
        leaf time-left {
          type uint32;
          units "s";
          description
            "Time left of EVPN recover timer.";
        }
      }
    }
    container track-peer-timer-infos {
      config false;
      description
        "List of EVPN track peer timer informations.";
      list track-peer-timer-info {
        key "esi";
        description
          "Operational state of EVPN track peer timer informations.";
        leaf esi {
          type esi;
          description
            "ESI, in the format of 00xx.xxxx.xxxx.xxxx.xxxx or 01xx.xxxx.xxxx.xxxx.xxxx, in which x ranges from 0 to F. A static ESI cannot be all 0s.";
        }
        leaf timer-type {
          type timer-type;
          description
            "Timer type.";
        }
        leaf timer-state {
          type timer-mode;
          description
            "Timer status.";
        }
        leaf time-left {
          type uint32;
          units "s";
          description
            "Remaining time.";
        }
      }
    }
    container sticky-mac-confliction-infos {
      config false;
      description
        "List of EVPN sticky/static mac conflicting informations.";
      list sticky-mac-confliction-info {
        key "mac-address bd-id vid";
        description
          "Operational data of EVPN sticky/static mac conflicting informations.";
        leaf mac-address {
          type pub-type:mac-address;
          description
            "MAC address.";
        }
        leaf bd-id {
            type uint32 {
              range "1..16777215";
            }
            description
              "The identification of the BD.";
        }
        leaf vid {
            type uint16 {
              range "0..4094";
            }
            description
              "VLAN ID.";
        }
        leaf interface-name {
          type leafref {
            path "/ifm:ifm/ifm:interfaces/ifm:interface/ifm:name";
          }
          description
            "Interface name.";
        }
        leaf peer-ip {
          type inet:ip-address-no-zone;
          description
            "Peer IP address.";
        }
        leaf pw-ip {
          type inet:ipv4-address-no-zone;
          description
            "PW IP address.";
        }
        leaf conflict-interface-name {
          type leafref {
            path "/ifm:ifm/ifm:interfaces/ifm:interface/ifm:name";
          }
          description
            "Conflict interface name.";
        }
      }
    }
  }
  rpc reset-evpn-mac-duplication {
    description
      "Reset EVPN MAC duplication.";
    ext:node-ref "/evpn:evpn/evpn:instances/evpn:instance/evpn:normal-evpn/evpn:mac-duplication-infos";
    ext:node-ref "/evpn:evpn/evpn:instances/evpn:instance/evpn:bd-evpn/evpn:mac-duplication-infos";
    input {
      leaf name {
        type name-type {
          length "1..31";
        }
        mandatory true;
        description
          "EVPN instance name.";
      }
      leaf bd-id {
        type uint32 {
          range "1..16777215";
        }
        description
         "BD ID.";
      }
      leaf mac-address {
        type pub-type:mac-address {
          length "1..255";
        }
        description
          "MAC address.";
      }
      leaf vlan-id {
        type uint32 {
          range "1..4094";
        }
        description
         "VLAN ID.";
      }
    }
  }
  rpc reset-all-evpn-mac-duplication {
    description
      "Reset all EVPN mac-duplication.";
    ext:node-ref "/evpn:evpn/evpn:instances/evpn:instance/evpn:bd-evpn/evpn:mac-duplication-infos";
  }
  rpc reset-all-evpn-vpn-sid {
    description
      "Reset all EVPN VPN SID in the slow-delete state.";
  }
  rpc reset-evpn-traffic-statistics {
    description
      "To clear traffic statistics of the specified EVPN instance.";
    ext:node-ref "/evpn:evpn/evpn:instances/evpn:instance/evpn:bd-evpn/evpn:traffic-statistics-info";
    input {
      leaf name {
        type name-type {
          length "1..31";
        }
        mandatory true;
        description
          "EVPN instance name.";
      }
    }
  }
  rpc reset-all-evpn-traffic-statistics {
    description
      "To clear traffic statistics of all EVPN instances.";
    ext:node-ref "/evpn:evpn/evpn:instances/evpn:instance/evpn:bd-evpn/evpn:traffic-statistics-info";
  }
  rpc reset-evpn-peer-traffic-statistics {
    description
      "To clear peer traffic statistics of the specified EVPN instance.";
    ext:node-ref "/evpn:evpn/evpn:instances/evpn:instance/evpn:bd-evpn/evpn:peer-traffic-statistics-infos";
    input {
      leaf name {
        type name-type {
          length "1..31";
        }
        mandatory true;
        description
          "EVPN instance name.";
      }
      leaf peer-ip {
        type inet:ipv4-address-no-zone;
        description
          "IPv4 address of remote peer.";
      }
    }
  }
  rpc reset-all-evpn-peer-traffic-statistics {
    description
      "To clear peer traffic statistics of all EVPN instances.";
    ext:node-ref "/evpn:evpn/evpn:instances/evpn:instance/evpn:bd-evpn/evpn:peer-traffic-statistics-infos";
  }
  rpc reset-evpl-traffic-statistics {
    description
      "To clear traffic statistics of the specified EVPL instance.";
    ext:node-ref "/evpl:evpl/evpl:instances/evpl:instance/evpn:evpn/evpn:traffic-statistics-info";
    input {
      leaf evpl-id {
        type uint32 {
          range "1..4294967295";
        }
        mandatory true;
        description
          "EVPL instance ID.";
      }
    }
  }
  rpc reset-all-evpl-traffic-statistics {
    description
      "To clear traffic statistics of all EVPL instances.";
    ext:node-ref "/evpl:evpl/evpl:instances/evpl:instance/evpn:evpn/evpn:traffic-statistics-info";
  }
  rpc reset-evpl-peer-traffic-statistics {
    description
      "To clear peer traffic statistics of the specified EVPL instance.";
    ext:node-ref "/evpl:evpl/evpl:instances/evpl:instance/evpn:evpn/evpn:peer-traffic-statistics-infos";
    input {
      leaf evpl-id {
        type uint32 {
          range "1..4294967295";
        }
        mandatory true;
        description
          "EVPL instance ID.";
      }
      leaf peer-ip {
        type inet:ipv4-address-no-zone;
        description
          "IPv4 address of remote peer.";
      }
    }
  }
  rpc reset-all-evpl-peer-traffic-statistics {
    description
      "To clear peer traffic statistics of all EVPL instances.";
    ext:node-ref "/evpl:evpl/evpl:instances/evpl:instance/evpn:evpn/evpn:peer-traffic-statistics-infos";
  }
  augment "/bd:bd/bd:instances/bd:instance" {
    description
    "BD bound to an EVPN instance.";
    container evpn {
      description
        "Configure BD bound to an EVPN instance.";
      leaf name {
        type leafref {
          path "/evpn:evpn/evpn:instances/evpn:instance/evpn:name";
        }
        must "(/evpn:evpn/evpn:instances/evpn:instance[evpn:name = current()]/evpn:type='bd-evpn') and not(/bd:bd/bd:instances/bd:instance[bd:id != current()/../../bd:id]/evpn:evpn[evpn:name = current()] and /bd:bd/bd:instances/bd:instance[bd:id != current()/../../bd:id]/evpn:evpn[evpn:tag = current()/../evpn:tag])";
        description
          "Configure BD instances bound to an BD exclusive mode EVPN instance.";
      }
      leaf esi {
        when "../name";
        type esi {
          length "1..24";
        }
        must "(../../nvo3:nvo3/nvo3:vni-list/nvo3:vni[../nvo3:split-horizon='true']) or (../df-result-spread='true') or ((../umr-originate='true') and not(/evpn:evpn/evpn:site/evpn:static-esis/evpn:static-esi[evpn:esi = current()]/evpn:redundancy-mode ='single-active'))";
        description
          "Static ESI, in the format of 00xx.xxxx.xxxx.xxxx.xxxx, in which x ranges from 0 to F. A static ESI cannot be all 0s.";
      }
      leaf tag {
        when "../name";
        type uint16 {
          range "1..16384";
        }
        ext:operation-exclude update;
        must "../../bd:mac-learn-style!='qualify'";
        description
          "Specify the BD tag.";
      }
      leaf umr-originate {
        when "../name";
        type boolean;
        must "(../umr-originate='true' and not(../../nvo3:nvo3/nvo3:vni-list/nvo3:vni) and not(../df-result-spread='true') and not(/l2vpn:l2vpn/l2vpn:instances/l2vpn:instance/l2vpn:vpls/l2vpn:bds/l2vpn:bd[l2vpn:id=current()/../../bd:id])) or (../umr-originate='false')";
        default "false";
        description
          "Enable/disable originate Unknown-MAC-Route.";
      }
      leaf detail-suppressed {
        when "../umr-originate ='true'";
        type boolean;
        default "false";
        description
          "Enable/disable suppresse detail MAC route.";
      }
      leaf evpnmac-high-priority {
        when "../detail-suppressed ='true'";
        type boolean;
        default "false";
        description
          "Enable/disable making remote MAC route higher priority than MAC route learned from local.";
      }
      leaf umr-forward {
        when "../name";
        type boolean;
        default "false";
        description
          "Enable/disable process all-0 MAC route as Unknown-MAC-Route.";
      }
      leaf df-result-spread {
        when "../name";
        type boolean;
        must "(../df-result-spread='true' and not(../../nvo3:nvo3/nvo3:vni-list/nvo3:vni) and not(../umr-originate='true') and not(/l2vpn:l2vpn/l2vpn:instances/l2vpn:instance/l2vpn:vpls/l2vpn:bds/l2vpn:bd[l2vpn:id=current()/../../bd:id])) or (../df-result-spread='false')";
        default "false";
        description
          "Enable/disable df-result spread to all ACs.";
      }
      leaf dci-ac-access {
        when "../name";
        type boolean;
        must "(../dci-ac-access='true' and ../../nvo3:nvo3/nvo3:vni-list/nvo3:vni[../nvo3:split-horizon='true']) or (../dci-ac-access='false')";
        default "false";
        description
          "Enable/disable evpn-dci support ac-access.";
      }
      leaf qualify-compatible {
        when "../name";
        type boolean;
        must "(../qualify-compatible='true' and ../../bd:mac-learn-style='qualify') or (../qualify-compatible='false')";
        default "false";
        description
          "Enable/disable EVPN qualify compatible.";
      }
      container interface-track-peers {
        when "(../name and ../../nvo3:nvo3/nvo3:vni-list/nvo3:vni[../nvo3:split-horizon='true'])";
        description "List of track peer.";
        list interface-track-peer {
          key "es-track-address";
          description "Configure track peer information.";
          leaf es-track-address {
            type leafref {
              path "/ni:network-instance/ni:instances/ni:instance/bgp:bgp/bgp:base-process/bgp:peers/bgp:peer/bgp:address";
            }
            must "/ni:network-instance/ni:instances/ni:instance/bgp:bgp/bgp:base-process/bgp:peers/bgp:peer[bgp:address=current()]/bgp:afs/bgp:af[bgp:type='evpn']";
            description
              "Track peer address.";
          }
        }
      }
      container es-recover {
        when "(../name)";
        description
          "Configure ES recovery timer for BD vac interface.";
        leaf timer {
          type uint32 {
            range "3..1200";
          }
          units "s";
          must "(../../df-result-spread='true')";
          description
            "ES recovery timer.";
        }
      }
    }
  }
  augment "/bd:bd/bd:instances/bd:instance" {
    description
    "BD bound to an EVPL instance.";
    container evpl-upes {
      description
        "List of EVPL UPEs.";
      list evpl-upe {
        key "evpl-id";
        description "Configure EVPL UPE that a bridge domain corresponds.";
        leaf evpl-id {
          type leafref {
            path "/evpl:evpl/evpl:instances/evpl:instance/evpl:id";
          }
          must "(/evpl:evpl/evpl:instances/evpl:instance[evpl:id=current()]/evpl:mode!='vxlan-mode') and (/evpl:evpl/evpl:instances/evpl:instance[evpl:id=current()]/evpl:mode!='static-mode') and not(../../../evpn:evpn/evpn:df-result-spread='true') and not(../../../nvo3:nvo3/nvo3:vni-list/nvo3:vni) and not(/evpl:evpl/evpl:instances/evpl:instance[evpl:id=current()]/evpl:ccc/evpl:interface)";
          description
            "The identification of the EVPL instance.";
        }
      }
    }
  }
  augment "/bd:bd/bd:instances/bd:instance/bd:service-points/bd:service-point" {
    description
    "Configure the E-Tree leaf attribute of BD.";
    container evpn {
      description
        "Configure the E-Tree leaf attribute of BD.";
      leaf e-tree-leaf {
        type boolean;
        must "(../e-tree-leaf = 'true' and ../../../../evpn:evpn/evpn:name and /evpn:evpn/evpn:instances/evpn:instance[evpn:name=current()/../../../../evpn:evpn/evpn:name]/evpn:bd-evpn/evpn:etree-enable = 'true') or (../e-tree-leaf = 'false')";
        default false;
        description
            "Enable/disable the E-Tree leaf attribute of BD.";
      }
    }
  }
  augment "/ni:network-instance/ni:instances/ni:instance/l3vpn:afs/l3vpn:af" {
    description
      "Configure EVPN.";
    container evpn {
      when "../../../ni:name!='_public_' and (../l3vpn:route-distinguisher or ../../../../../ni:global/ni:route-distinguisher-auto-ip)";
      description
        "Configure EVPN.";
      choice import-policy-type {
        description
          "Set route policy or filter.";
        case rtp-ref {
          description
            "Route policy.";
          leaf import-policy-name {
            type leafref {
              path "/rtp:routing-policy/rtp:policy-definitions/rtp:policy-definition/rtp:name";
            }
            description
              "Specifies the name of an import routing policy.";
          }
        }
        case xpl-ref {
          description
            "Route filter.";
          container import-filter {
            description
              "Configure an import route-filter with the current VPN instance.";
            leaf name {
              type leafref {
                path "/xpl:xpl/xpl:route-filters/xpl:route-filter/xpl:name";
              }
              description
                "Specify an import route-filter name.";
            }
            leaf parameter {
              when "../name";
              type xpl:filter-parameter-type;
              description
                "Specify an import route-filter parameter.";
            }
          }
        }
      }
      choice export-policy-type {
        description
          "Set route policy or filter.";
        case rtp-ref {
          description
            "Route policy.";
          leaf export-policy-name {
            type leafref {
              path "/rtp:routing-policy/rtp:policy-definitions/rtp:policy-definition/rtp:name";
            }
            description
              "Specifies the name of an export routing policy.";
          }
        }
        case xpl-ref {
          description
            "Route filter.";
          container export-filter {
            description
              "Configure an export route-filter with the current VPN instance.";
            leaf name {
              type leafref {
                path "/xpl:xpl/xpl:route-filters/xpl:route-filter/xpl:name";
              }
              description
                "Specify an export route-filter name.";
            }
            leaf parameter {
              when "../name";
              type xpl:filter-parameter-type;
              description
                "Specify an export route-filter parameter.";
            }
          }
        }
      }
      leaf mpls-routing {
        type boolean;
        default "false";
        description
          "Enable/disable the EVPN MPLS layer 3 routing function.";
      }
      leaf tunnel-policy-name {
        type leafref {
          path "/tnlm:tunnel-management/tnlm:tunnel-policys/tnlm:tunnel-policy/tnlm:name";
        }
        description
          "Specify tunnel policy name for EVPN.";
      }
      leaf default-color {
        type uint32 {
          range "0..4294967295";
        }
        description
          "Set default color for nexthop iteration.";
      }
      leaf irb2ip {
        type irb2ip-enable-type;
        default "default";
        description
          "Enable/disable IRB routing rebirth into prefix routing.";
      }
      leaf label-mode {
        when "../../l3vpn:type = 'ipv4-unicast'";
        type label-mode-type;
        default "per-instance";
        description
          "Method of distributing labels to VPN instance routes.";
      }
      leaf export-policy-add-ert-first {
        when "../export-policy-name or ../export-filter/name";
        type boolean;
        default "false";
        description
          "Enable/disable advertise routes to EVPN add ERT first.";
      }
      container extend-vpn-targets {
        description
          "List of extended RTs.";
        list extend-vpn-target {
          key "vrf-rt-value vrf-rt-type";
          description
            "Configure RT (VPN Target) to control route advertisement between network nodes. Before sending a VPN route to a PE, the local PE adds an Export RT to the route. After receiving a route from another PE, the local PE determines whether the route will be added to the VPN instance based on the local Import RT and the Export RT that is added to the VPN route.";
          leaf vrf-rt-value {
            type string {
              length "3..21";
            }
            description
              "The formats of a VPN target value are as follows:
(1) 16-bit AS number : 32-bit user-defined number, for example, 1:3. An AS number ranges from 0 to 65535, and a user-defined number ranges from 0 to 4294967295. The AS number and user-defined number cannot be both 0s. This means that the VPN Target value cannot be 0:0.
(2) 32-bit IP address: 16-bit user-defined number, for example: 192.168.122.15:1.The IP address ranges from 0.0.0.0 to 255.255.255.255, and the user-defined number ranges from 0 to 65535.
(3) 32-bit AS number :16-bit user-defined number, for example, 10.11:3. An AS number ranges from 0.0 to 65535.65535 or 0 to 4294967295, and a user-defined number ranges from 0 to 65535. The AS number and user-defined number cannot be both 0s. This means that the VPN Target value cannot be 0.0:0.";
          }
          leaf vrf-rt-type {
            type vrf-rt-type;
            description
              "RT types are as follows:
export-extcommunity: Specifies the value of the extended community attribute of the route from an outbound interface to the destination VPN. import-extcommunity: Receives routes that carry the specified extended community attribute value.";
          }
        }
      }
      container state {
        config false;
        description
          "Operational state of EVPN attribute.";
        leaf label {
          type uint32;
          config false;
          description
            "EVPN label of the VPN instance address family.";
        }
      }
    }
  }
  augment "/evpl:evpl/evpl:instances/evpl:instance" {
    description
      "EVPL instance bound to an EVPN instance.";
    container evpn {
      description
        "Configure EVPL instance bound to an EVPN instance.";
      leaf name {
        type leafref {
          path "/evpn:evpn/evpn:instances/evpn:instance/evpn:name";
        }
        must "/evpn:evpn/evpn:instances/evpn:instance[name=current()]/evpn:type='vpws-evpn' and (/evpn:evpn/evpn:instances/evpn:instance[name=current()]/evpn:vpws-evpn/evpn:rd or /evpn:evpn/evpn:base-process/evpn:auto-rd-ip) and ../../evpl:mode!='vxlan-mode'";
        description
          "Configure EVPL instances bound to an EVPN instance.";
      }
      leaf local-service-id {
        ext:operation-exclude update;
        when "../name";
        type uint32 {
          range "1..4294967294";
        }
        must "(../local-service-id and ../remote-service-id) or (not(../local-service-id) and not(../remote-service-id))";
        description
          "Configure the local SID.";
      }
      leaf remote-service-id {
        ext:operation-exclude update;
        when "../name";
        type uint32 {
          range "1..4294967294";
        }
        must "(../local-service-id and ../remote-service-id) or (not(../local-service-id) and not(../remote-service-id))";
        description
          "Configure the remote SID.";
      }
      leaf ignore-match-mtu {
        when "../name";
        type boolean;
        default "false";
        description
          "Enable/disable the ignore flag of matching MTU from peer device.";
      }
      leaf balancing-ignore-esi {
        when "../name";
        type boolean;
        default "false";
        description
          "Enable/disable the ignore flag of ESI for load balance.";
      }
      leaf control-word {
        when "../name";
        type boolean;
        must "(../control-word='true' and ../../evpl:mode!='vxlan-mode') or ../control-word!='true'";
        default "false";
        description
          "Enable/disable EVPL control word.";
      }
      leaf l2vpn-migrate {
        when "../name";
        type boolean;
        must "(../l2vpn-migrate='true' and ../../evpl:mode!='vxlan-mode' and ../../evpl:mode!='static-mode') or ../l2vpn-migrate!='true'";
        default "false";
        description
          "Enable/disable EVPL migrate L2VPN.";
      }
      leaf flow-label {
          when "../name";
          type boolean;
          must "(../flow-label='true' and ../../evpl:mode!='vxlan-mode' and ../../evpl:mode!='static-mode') or ../flow-label!='true'";
          default "false";
          description
            "Enable/disable EVPL flow label.";
      }
      leaf ccc-service-id {
        when "../name";
        type uint32 {
          range "1..4294967294";
        }
        must "(../ccc-service-id and ../ccc-out-service-id) or (not(../ccc-service-id) and not(../ccc-out-service-id))";
        description
          "Configure the local SID.";
      }
      leaf ccc-out-service-id {
        when "../name";
        type uint32 {
          range "1..4294967294";
        }
        must "(../ccc-service-id and ../ccc-out-service-id) or (not(../ccc-service-id) and not(../ccc-out-service-id))";
        description
          "Configure the remote SID.";
      }
      leaf traffic-statistics {
        when "../name";
        type boolean;
        must "(../traffic-statistics='true' and ../peer-traffic-statistics='false' and not(../../evpl:ccc/evpl:interface)) or ../traffic-statistics='false'";
        default "false";
        description
          "Enable/disable EVPL traffic statistics.";
      }
      leaf peer-traffic-statistics {
        when "../name";
        type boolean;
        must "(../peer-traffic-statistics='true' and ../../evpl:mode!='static-mode' and ../traffic-statistics='false' and not(../../evpl:ccc/evpl:interface)) or ../peer-traffic-statistics='false'";
        default "false";
        description
          "Enable/disable EVPL peer traffic statistics.";
      }
      container vrrp {
        when "../name";
        presence "Configure associated VRRP group.";
        description
          "Configure associated VRRP group.";
        leaf id {
          ext:operation-exclude update;
          type uint8 {
            range "1..255";
          }
          mandatory true;
          description
            "ID of the associated VRRP group.";
        }
        leaf interface-name {
          ext:operation-exclude update;
          type leafref {
            path "/ifm:ifm/ifm:interfaces/ifm:interface/ifm:name";
          }
          mandatory true;
          description
            "Name of the interface where the associated VRRP group resides.";
        }
        leaf version {
          ext:operation-exclude update;
          type evpl-vrrp-version;
          mandatory true;
          description
            "The VRRP version, which includes vrrp and vrrp6.";
        }
      }
      container bfd-detect {
        when "../../evpl:mode!='vxlan-mode' and ../evpn:name";
        description
            "Configure BFD detect.";
        leaf min-rx-interval {
            ext:dynamic-default;
            type uint32 {
                range "0..65535";
            }
            units ms;
            description
            "Minimum receive interval.";
        }
        leaf min-tx-interval {
            ext:dynamic-default;
            type uint32 {
                range "0..65535";
            }
            units ms;
            description
            "Minimum transmit interval.";
        }
        leaf detect-multiplier {
            type uint32 {
                range "3..50";
            }
            default "3";
            description
            "Detection multiplier.";
        }
        leaf track-interface {
            type boolean;
            must "(../track-interface = 'true' and /evpl:evpl/evpl:instances/evpl:instance[evpl:id=current()/../../../evpl:id]/evpl:interfaces/evpl:interface/evpl:name) or (../track-interface = 'false')";
            default "false";
            description
            "Enable/disable BFD track interface state.";
        }
      }
      container evpl-info {
        config false;
        description
          "Operational state of EVPL info.";
        leaf ac-interface {
            type leafref {
              path "/ifm:ifm/ifm:interfaces/ifm:interface/ifm:name";
            }
            description
              "The AC interface bound to EVPL instance.";
        }
        leaf evpl-state {
            type evpl-state;
            description
              "The state of EVPL instance.";
        }
        leaf local-ctrl-word {
            type boolean;
            description
              "The local control word.";
        }
        leaf local-mtu {
            type uint16 {
              range "0..65535";
            }
            units Byte;
            description
              "The value of local MTU, just from the interface which bound to the EVPL instance. If MTU is 0, it means the ignore flag of checking MTU is enabled.";
        }
        leaf local-reduancy-mode {
            type redundancy-mode;
            description
              "The local reduancy mode, which includes single-active and all-active modes.";
        }
        leaf local-df-state {
            type df-state;
            description
              "The local DF state.";
        }
        leaf local-df-elec-type {
          type decide-primary-type;
          description
            "Type of determining the primary/backup status of local DF.";
        }
        leaf remote-reduancy-mode {
            type redundancy-mode;
            description
              "The remote reduancy mode, which includes single-active and all-active modes.";
        }
        leaf remote-pri-df-num {
            type uint32 {
              range "0..4294967295";
            }
            description
              "Number of primary DFs.";
        }
        leaf remote-back-df-num {
            type uint32 {
              range "0..4294967295";
            }
            description
              "Number of backup DFs.";
        }
        leaf remote-none-df-num {
            type uint32 {
              range "0..4294967295";
            }
            description
              "Number of none DFs.";
        }
        leaf tunnel-type {
            type evpn-tunnel-type;
            description
              "The tunnel type of EVPN network.";
        }
        leaf evpl-type {
            type evpn-evpl-type;
            description
              "The type of EVPL.";
        }
        leaf if-last-up-time {
            type yang:date-and-time;
            description
              "The last up time of AC interface.";
        }
        leaf last-pri-time {
            type yang:date-and-time;
            description
              "The last time to be primary DF.";
        }
        leaf last-backup-time {
            type yang:date-and-time;
            description
              "The last time to be backup DF.";
        }
        leaf ccc-if {
            type leafref {
              path "/ifm:ifm/ifm:interfaces/ifm:interface/ifm:name";
            }
            description
              "The name of the CCC interface.";
        }
        leaf ccc-local-mtu {
            type uint16 {
              range "0..65535";
            }
            units Byte;
            description
              "The value of local MTU, just from the interface which bound to the EVPL instance. If MTU is 0, it means the ignore flag of checking MTU is enabled.";
        }
        leaf ccc-local-redundancy {
            type redundancy-mode;
            description
              "The local reduancy mode, which includes single-active and all-active modes.";
        }
        leaf ccc-local-df-state {
            type df-state;
            description
              "The local DF state.";
        }
        leaf ccc-local-df-elec-type {
            type decide-primary-type;
            description
              "Type of determining the primary/backup status of local DF.";
        }
        leaf ccc-remote-redundancy-mode {
            type redundancy-mode;
            description
              "The remote reduancy mode, which includes single-active and all-active modes.";
        }
        leaf ccc-remote-pri-df-num {
            type uint32 {
              range "0..4294967295";
            }
            description
              "Number of primary DFs.";
        }
        leaf ccc-remote-back-df-num {
            type uint32 {
              range "0..4294967295";
            }
            description
              "Number of backup DFs.";
        }
        leaf ccc-remote-none-df-num {
            type uint32 {
              range "0..4294967295";
            }
            description
              "Number of none DFs.";
        }
        leaf ccc-if-last-up-time {
            type yang:date-and-time;
            description
              "The last up time of AC interface.";
        }
        leaf ccc-last-pri-time {
            type yang:date-and-time;
            description
              "The last time to be primary DF.";
        }
        leaf ccc-last-backup-time {
            type yang:date-and-time;
            description
              "The last time to be backup DF.";
        }
      }
      container evpl-peer-infos {
        config false;
        description
          "List of EVPL peer info.";
        list evpl-peer-info {
          key "peer-ip nexthop-ip eline-role srv6-sid";
          description
            "Operational state of EVPL peer info.";
          leaf peer-ip {
            type inet:ip-address-no-zone;
            description
              "Peer IP address.";
          }
          leaf nexthop-ip {
            type inet:ip-address-no-zone;
            description
              "Original nexthop IP address.";
          }
          leaf eline-role {
            type eline-role;
            description
              "The E-Line role.";
          }
          leaf srv6-sid {
            type inet:ipv6-address-no-zone;
            description
              "The E-Line srv6 sid.";
          }
          leaf ccc-ac-type {
            type ccc-ac-type;
            description
              "CCC AC type.";
          }
          leaf remote-df-state {
            type df-state;
            description
              "Remote DF status.";
          }
          leaf remote-mtu {
            type uint32 {
              range "1..4294967295";
            }
            units Byte;
            description
              "The value of remote MTU, just from the interface which bound to the EVPL instance. If MTU is 0, it means the ignore flag of checking MTU is enabled.";
          }
          leaf remote-ctrl-word {
            type boolean;
            description
              "The remote control word.";
          }
          leaf remote-esi {
            type esi {
              length "1..24";
            }
            description
              "Remote ESI.";
          }
          container tunnel-infos {
            config false;
            description
              "List of EVPL peer tunnel informations.";
            list tunnel-info {
              key "id";
              description
                "Operational state of EVPL peer tunnel informations.";
              leaf id {
                type string {
                  length "1..20";
                }
                description
                  "Tunnel ID.";
              }
              leaf type {
                type evpl-tunnel-type;
                description
                  "Tunnel type.";
              }
            }
          }
        }
      }
      container label-stacks {
        config false;
        description
          "Statistics of EVPN label stacks.";
        uses evpn:label-stacks-type;
      }
      container binding-sids {
        when "../../evpl:mode='static-mode' and ../evpn:name";
        description
          "List of binding SID.";
        list binding-sid {
          key "sid";
          max-elements "3";
          description
              "Configure SID for evpl instance.";
          leaf sid {
              type inet:ipv6-address-no-zone;
              description
                "SID attribute.";
          }
          leaf peer-ip {
              type inet:ipv6-address-no-zone;
              mandatory true;
              description
              "Peer IP address.";
          }
          leaf color {
            type uint32 {
              range "0..4294967295";
            }
            description
              "Color information.";
          }
          leaf preference {
            type evpl-sid-preference-type;
            default "primary";
            description
              "The preference of SID.";
          }
        }
      }
      container upe {
        when "../../evpl:mode!='static-mode' and ../../evpl:mode!='vxlan-mode' and ../name";
        description
          "Configure EVPL as UPE.";
        leaf track-bd {
          type boolean;
          default "false";
          description
            "Enable/disable the track bridge domain.";
        }
        leaf esi {
          type esi;
          description
            "ESI, in the format of 00xx.xxxx.xxxx.xxxx.xxxx, in which x ranges from 0 to F. A static ESI cannot be all 0s.";
        }
        leaf etree-leaf-enable {
          type boolean;
          default "false";
          description
            "Enable/disable the E-Tree leaf attribute of a EVPL.";
        }
        leaf es-recovery-timer {
          type uint32 {
            range "3..1200";
          }
          units "s";
          description
            "ES recovery timer.";        
        }
        leaf track-bfd-name {
          type leafref {
            path "/bfd:bfd/bfd:sessions/bfd:session/bfd:name";
          }
          description
            "Specify the BFD that track ESI peer.";
        }
      }
      container traffic-statistics-info {
        config false;
        description
          "Operational data of traffic statistics.";
        leaf last-clear-time {
          type yang:date-and-time;
          description
            "Time when traffic statistics were cleared last time.";
        }
        leaf in-bytes-rate {
          type uint64;
          description
            "Rate of bytes received.";
        }
        leaf out-bytes-rate {
          type uint64;
          description
            "Rate of bytes sent.";
        }
        leaf in-packets-rate {
          type uint64;
          description
            "Rate of packets received.";
        }
        leaf out-packets-rate {
          type uint64;
          description
            "Rate of packets sent.";
        }
        leaf in-bytes {
          type uint64;
          description
            "Number of bytes received.";
        }
        leaf out-bytes {
          type uint64;
          description
            "Number of bytes sent.";
          }
        leaf in-packets {
          type uint64;
          description
            "Number of packets received.";
        }
        leaf out-packets {
          type uint64;
          description
            "Number of packets sent.";
        }
      }
      container peer-traffic-statistics-infos {
        config false;
        description
          "List of peer traffic statistics.";
        list peer-traffic-statistics-info {
          key "peer-ip";
          config false;
          description
            "Operational data of peer traffic statistics.";
          leaf peer-ip {
            type inet:ipv4-address-no-zone;
            description
              "IPv4 address of remote peer.";
          }
          leaf last-clear-time {
            type yang:date-and-time;
            description
              "Time when peer traffic statistics were cleared last time.";
          }
          leaf out-bytes-rate {
            type uint64;
            description
              "Rate of bytes sent.";
          }
          leaf out-packets-rate {
            type uint64;
            description
              "Rate of packets sent.";
          }
          leaf out-bytes {
            type uint64;
            description
              "Number of bytes sent.";
          }
          leaf out-packets {
            type uint64;
            description
              "Number of packets sent.";
          }
        }
      }
    }
  }
  augment "/ifm:ifm/ifm:interfaces/ifm:interface" {
    description
      "Configure EVPN with the interface.";
    container evpn {
      description
        "Configure ESI interface.";
      leaf name {
        type leafref {
          path "/evpn:evpn/evpn:instances/evpn:instance/evpn:name";
        }
        must "/evpn:evpn/evpn:instances/evpn:instance[evpn:name=current()]/evpn:type='i-evpn' or /evpn:evpn/evpn:instances/evpn:instance[evpn:name=current()]/evpn:type='normal'";
        description
          "Configure EVPL instances bound to an EVPN instance.";
      }
      leaf pbb-source-mac {
        when "../name";
        type pub-type:mac-address {
        }
        must "/evpn:evpn/evpn:instances/evpn:instance[evpn:name=current()/../evpn:name]/evpn:type='i-evpn'";
        description
          "Specifies a B-MAC address."; 
      }
      leaf esi {
        when "(../../ifm:type='Ethernet') or (../../ifm:type='GigabitEthernet') or (../../ifm:type='Eth-Trunk') or (../../ifm:type='100GE') or (../../ifm:type='200GE') or (../../ifm:type='1200GE') or (../../ifm:type='40GE') or (../../ifm:type='10GE') or (../../ifm:type='25GE') or (../../ifm:type='50GE') or (../../ifm:type='PW-VE') or (../../ifm:type='400GE') or (../../ifm:type='MultiGE') or (../../ifm:type='Virtual-Ethernet') or (../../ifm:type='FlexE') or (../../ifm:type='800GE') or (../../ifm:type='50|100GE') or (../../ifm:type='50-100GE')";
        type esi {
          length "1..24";
          pattern '( *(00([0-9a-fA-F]){2}\.(([0-9a-fA-F]){4}\.){3}(([0-9a-fA-F]){4}))? *)';
        }
        description
          "Static ESI, in the format of 00xx.xxxx.xxxx.xxxx.xxxx, in which x ranges from 0 to F. A static ESI cannot be all 0s.";
      }
      leaf esi-name {
        when "../../ifm:type='Eth-Trunk'";
        type leafref {
          path "/evpn:evpn/evpn:site/evpn:dynamic-esis/evpn:dynamic-esi/evpn:esi-name";
        }
        description
          "Dynamic ESI name is a string of 1 to 31 characters, which begins with a-z or A-Z.";
      }
      leaf es-recovery-timer {
        when "(../../ifm:type='Ethernet') or (../../ifm:type='GigabitEthernet') or (../../ifm:type='Eth-Trunk') or (../../ifm:type='100GE') or (../../ifm:type='200GE') or (../../ifm:type='1200GE') or (../../ifm:type='40GE') or (../../ifm:type='10GE') or (../../ifm:type='25GE') or (../../ifm:type='50GE') or (../../ifm:type='PW-VE') or (../../ifm:type='400GE') or (../../ifm:type='MultiGE') or (../../ifm:type='Virtual-Ethernet') or (../../ifm:type='FlexE') or (../../ifm:type='800GE') or (../../ifm:type='50|100GE') or (../../ifm:type='50-100GE')";
        type uint32 {
          range "3..1200";
        }
        units "s";
        description
          "ES recovery timer.";
      }
      leaf track-bfd-name {
        when "(../../ifm:type='Ethernet') or (../../ifm:type='GigabitEthernet') or (../../ifm:type='Eth-Trunk') or (../../ifm:type='100GE') or (../../ifm:type='200GE') or (../../ifm:type='1200GE') or (../../ifm:type='40GE') or (../../ifm:type='10GE') or (../../ifm:type='25GE') or (../../ifm:type='50GE') or (../../ifm:type='PW-VE') or (../../ifm:type='400GE') or (../../ifm:type='MultiGE') or (../../ifm:type='FlexE') or (../../ifm:type='800GE') or (../../ifm:type='50|100GE') or (../../ifm:type='50-100GE')";
        type leafref {
          path "/bfd:bfd/bfd:sessions/bfd:session/bfd:name";
        }
        description
          "Specify the BFD that track ESI peer.";
      }
      leaf e-tree-leaf {
        when "../name";
        type boolean;
        must "(../e-tree-leaf = 'true' and /evpn:evpn/evpn:instances/evpn:instance[evpn:name=current()/../evpn:name]/evpn:normal-evpn/evpn:etree-enable='true') or (../e-tree-leaf = 'false')";
        default "false";
        description
            "Enable/disable the E-Tree leaf attribute of interface.";
      }
      leaf ring-id {
        when "../esi";
        type uint32 {
          range "1..16777215";
        }
        must "not (/ifm:ifm/ifm:interfaces/ifm:interface[ifm:name != current()/../../ifm:name]/evpn:evpn[evpn:ring-id = current()])";
        description
          "Evpn ring id of interface.";
      }
      leaf state {
        type evpn:interface-state;
        config false;
        description
          "Interface state.";
      }
      leaf vc-state {
        type evpn:vc-state;
        config false;
        description
          "VC state.";
      }
      leaf ignore-dynamic-esi {
        when "(../../ifm:type='Eth-Trunk')";
        type boolean;
        default "false";
        description
          "Enable/disable ignore dynamic ESI.";
      }
    }
    container evpn-attribute {
      description
        "Configure EVPN attribute of interface.";
      container track-peers {
        when "(../../ifm:type='Eth-Trunk') or (../../ifm:type='PW-VE')";
        description
            "List of track peer.";
        list track-peer {
          key "es-track-address";
          description
            "Configure the track peer info.";
          leaf es-track-address {
            type leafref {
              path "/ni:network-instance/ni:instances/ni:instance/bgp:bgp/bgp:base-process/bgp:peers/bgp:peer/bgp:address";
            }
            must "/ni:network-instance/ni:instances/ni:instance/bgp:bgp/bgp:base-process/bgp:peers/bgp:peer[bgp:address=current()]/bgp:afs/bgp:af[bgp:type='evpn']";
            description
              "Track peer address.";
          }
        }
      }
      container track-umr-route {
        when "(../../ifm:type='Eth-Trunk') and ../../ifm:class='main-interface'";
        presence "Enable association between the UMR route with the interface status.";
        description
          "Enable/disable association between the UMR route with the interface status.";
      }
      container port-control {
        description
          "Configure EVPN port control.";
        leaf load-balancing {
          when "(../../../ifm:type='Eth-Trunk')";
          type load-balancing-mode;
          must "(not (../../../evpn/name))";
          description
           "Enable/disable port-active to interface.";
        }
      }
      container track-evpl-state {
        when "(../../ifm:type='Virtual-Ethernet' or ../../ifm:type='Global-VE') and ../../ifm:class='sub-interface'";
        presence "Enable association between the EVPL status with the interface status.";
        description
          "Enable/disable association between the EVPL status with the interface status.";
      }
      container track-df-state {
        presence "Enable association between the DF state with the interface status.";
        description
          "Enable/disable association between the DF state with the interface status.";
      }
    }
  }
  augment "/l2vpn:l2vpn/l2vpn:instances/l2vpn:instance/l2vpn:vpls/l2vpn:ldp-signaling/l2vpn:pws/l2vpn:pw" {
    description
      "Configure the EVPN attributes of a PW.";
    container evpn {
      description
        "Configure the EVPN attributes of a PW.";
      leaf etree-leaf-enable {
        when "../../../../../l2vpn:work-mode='bd-mode' and ../../l2vpn:upe='true' and ../../l2vpn:name";
        type boolean;
        must "(../etree-leaf-enable='true' and ../../../../../l2vpn:bds/l2vpn:bd/l2vpn:id and /bd:bd/bd:instances/bd:instance[bd:id=current()/../../../../../l2vpn:bds/l2vpn:bd/l2vpn:id]/evpn:evpn/evpn:name and /evpn:evpn/evpn:instances/evpn:instance[evpn:name=/bd:bd/bd:instances/bd:instance[bd:id=current()/../../../../../l2vpn:bds/l2vpn:bd/l2vpn:id]/evpn:evpn/evpn:name]/evpn:type='bd-evpn' and /evpn:evpn/evpn:instances/evpn:instance[evpn:name=/bd:bd/bd:instances/bd:instance[bd:id=current()/../../../../../l2vpn:bds/l2vpn:bd/l2vpn:id]/evpn:evpn/evpn:name]/evpn:bd-evpn/evpn:etree-enable='true') or ../etree-leaf-enable='false'";
        default "false";
        description
          "Enable/disable the E-Tree leaf attribute of a PW.";
      }
      leaf esi {
        when "../../../../../l2vpn:work-mode='bd-mode' and ../../l2vpn:upe='true' and ../../l2vpn:name";
        type leafref {
          path "/evpn:evpn/evpn:site/evpn:static-esis/evpn:static-esi/evpn:esi";
        }
        must "(/evpn:evpn/evpn:site/evpn:static-esis/evpn:static-esi[evpn:esi=current()/../evpn:esi]/evpn:redundancy-mode='single-active') or (/evpn:evpn/evpn:site/evpn:static-esis/evpn:static-esi[evpn:esi=current()/../evpn:esi]/evpn:redundancy-mode='none' and /evpn:evpn/evpn:base-process/evpn:redundancy-mode='single-active')";
        description
          "Static ESI, in the format of 00xx.xxxx.xxxx.xxxx.xxxx, in which x ranges from 0 to F. A static ESI cannot be all 0s.";
      }
      leaf state {
        type l2vpn:l2vpn-pw-state;
        config false;
        description
          "PW state.";
      }
    }
  }
  augment "/bd:bd/bd:profiles/bd:profile" {
    description
      "The EVPN configuration for bridge domain profile.";
    container evpn {
      must "../nvo3:nvo3/nvo3:vni-auto = 'true'";
      presence "EVPN instance";
      description
        "Configure EVPN for a BD profile.";
      leaf rd-auto {
        type boolean;
        default "false";
        description
          "Enable/disable RD automatic allocation.";
      }
      leaf rt-auto {
        when "../rd-auto = 'true'";
        type boolean;
        default "false";
        description
          "Enable/disable RT automatic allocation.";
      }
    }
  }
}
