/*
Copyright (C) 2025 Huawei Technologies Co., Ltd. All rights reserved.
*/
module huawei-openconfig-platform-psu-deviations-ar5710s {
  namespace "urn:huawei:yang:huawei-openconfig-platform-psu-deviations-ar5710s";
  prefix oc-platform-psu-devs-ar5710s;

  import openconfig-platform-psu {
    prefix oc-platform-psu;
  }
  import openconfig-platform {
    prefix oc-platform;
  }

  organization
    "Huawei Technologies Co., Ltd.";
  contact
    "Huawei Industrial Base
     Bantian, Longgang
     Shenzhen 518129
     People's Republic of China
     Website: http://www.huawei.com
     Email: support@huawei.com";
  description
    "This module defines deviation statements for openconfig-platform-psu module.";

  revision 2025-02-24 {
    description
      "Initial revision.";
    reference "Huawei private.";
  }

  deviation "/oc-platform:components/oc-platform:component/oc-platform:power-supply/oc-platform:config/oc-platform-psu:enabled" {
    deviate not-supported;
  }
  deviation "/oc-platform:components/oc-platform:component/oc-platform:power-supply/oc-platform:state/oc-platform-psu:enabled" {
    deviate not-supported;
  }
  deviation "/oc-platform:components/oc-platform:component/oc-platform:power-supply/oc-platform:state/oc-platform-psu:input-current" {
    deviate not-supported;
  }
}
