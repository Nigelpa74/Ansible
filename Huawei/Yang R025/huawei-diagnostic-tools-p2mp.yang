/*
Copyright (C) 2019-2025 Huawei Technologies Co., Ltd. All rights reserved.
*/
submodule huawei-diagnostic-tools-p2mp {
  yang-version 1;
  belongs-to huawei-diagnostic-tools {
    prefix diagnostic-tools;
  }

  import ietf-inet-types {
    prefix inet;
  }
  import huawei-pub-type {
    prefix pub-type;
  }
  import huawei-extension {
    prefix ext;
  }
  include huawei-diagnostic-tools-common;
  include huawei-diagnostic-tools-type;

  organization
    "Huawei Technologies Co., Ltd.";
  contact
    "Huawei Industrial Base
     Bantian, Longgang
     Shenzhen 518129
     People's Republic of China
     Website: http://www.huawei.com
     Email: support@huawei.com";
  description
    "P2mp diagnosis tool.";
  revision 2025-02-13 {
    description
      "Modify description of p2mp.";
    reference
      "Huawei private.";
  }
  revision 2022-07-05 {
    description
      "Add uint of packet-size. Add range for index in ping-results container. Add range for index, ds-index, label-index in trace-results container.";
    reference "Huawei private.";
  }
  revision 2022-01-29 {
    description
      "Add downstream container for trace results.";
    reference
      "Huawei private.";
  }
  revision 2020-01-14 {
    description
      "Add container for list.";
    reference
      "Huawei private.";
  }
  revision 2019-04-13 {
    description
      "Init revision.";
    reference
      "Huawei private.";
  }

  grouping p2mp-ping-trace-result-type {
    description
      "Test result table of P2MP test.";
    container ping-results {
      config false;
      description
        "List of ping test results.";
      list ping-result {
        key "test-name";
        description
          "Statistics of ping test result.";
        leaf test-name {
          type string {
            length "1..32";
          }
          description
            "Test name.";
        }
        leaf tunnel-name {
          type string {
            length "1..33";
          }
          description
            "TE tunnel name.";
        }
        leaf root-address {
          type inet:ipv4-address-no-zone;
          description
            "Root IP address.";
        }
        leaf opaque-value {
          type string {
            length "1..254";
          }
          description
            "The characteristic information of the LSP.";
        }
        leaf packet-send {
          type uint32;
          description
            "Total number of sent packets.";
        }
        leaf packet-receive {
          type uint32;
          description
            "Total number of received packets.";
        }
        leaf loss-ratio {
          type pub-type:percent;
          units "%";
          description
            "Packet loss ratio of a test.";
        }
        leaf status {
          type dgntl-test-status-type;
          description
            "Test status.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        container probes {
          config false;
          description
            "List of ping results of all packets in a test.";
          list probe {
            key "index";
            description
              "Statistics of ping result of a single packet in a test.";
            leaf index {
              type uint32 {
                range "1..4294967295";
              }   
              description
                "Index of packet.";
            }
            leaf sequence {
              type uint32;
              description
                "Serial number of a test packet received.";
            }
            leaf reply-address {
              type inet:ipv4-address-no-zone;
              description
                "Destination address of the related hop in a test.";
            }
            leaf data-bytes {
              type uint32;
              units "Byte";
              description
                "The response received is the number of text sections.";
            }
            leaf rtt {
              type uint32;
              units "ms";
              description
                "The round-trip time of the test message.";
            }
            leaf result-type {
              type probe-result-type;
              description
                "Result of packet sending, which is either success or timeout.";
            }
            leaf is-delete {
              ext:support-filter "true";
              type boolean;
              description
                "Enable/disable the function of deleting test results.";
            }
            leaf return-code {
              type lspv-return-code;
              description
                "Return code.";
            }
            leaf sub-code {
              type uint32;
              description
                "The return subcode contains the point in the label stack where processing was terminated. If the RSC is 0, no labels were processed. Otherwise the packet would have been label switched at depth RSC.";
            }
          }
        }
      }
    }
    container trace-results {
      config false;
      description
        "List of trace results.";
      list trace-result {
        key "test-name";
        description
          "Statistics of trace result.";
        leaf test-name {
          type string {
            length "1..32";
          }
          description
            "Test name.";
        }
        leaf tunnel-name {
          type string {
            length "1..33";
          }
          description
            "Name of the TE tunnel created by RSVP signaling. This parameter is available when LSP Type is set to TE tunnel.";
        }
        leaf root-ip-address {
          type inet:ipv4-address-no-zone;
          description
            "Root IP address.";
        }
        leaf status {
          type dgntl-test-status-type;
          description
            "Tunnel status.";
        }
        container hops {
          config false;
          description
            "List of hop results.";
          list hop {
            key "index";
            description
              "Statistics of hop result.";
            leaf index {
              type uint32 {
                range "1..4294967295";
              }   
              description
                "The index of the hop result.";
            }
            leaf ttl {
              type uint8 {
                range "1..255";
              }
              description
                "The response lifetime value received.";
            }
            leaf replier {
              type inet:ipv4-address-no-zone;
              description
                "Destination address of the related hop in a test.";
            }
            leaf rtt {
              type uint32;
              units "ms";
              description
                "RTT of test packets.";
            }
            leaf type {
              type p2mp-transmit-type;
              description
                "The type of each node.";
            }
            leaf return-code {
              type lspv-return-code;
              description
                "Return code.";
            }
            leaf result-type {
              type probe-result-type;
              description
                "Result of packet sending, which is either Success or Timeout.";
            }
            leaf is-delete {
              ext:support-filter "true";
              type boolean;
              description
                "Enable/disable the function of deleting test results.";
            }
            container downstreams {
              config false;
              description
                "List of downstream information tables.";
              list downstream {
                key "ds-index";
                description
                  "Statistics of downstream information table.";
                leaf ds-index {
                  type uint32 {
                    range "1..4294967295";
                  }  
                  description
                    "The index of the ds.";
                }
                leaf ds-address {
                  type inet:ipv4-address-no-zone;
                  description
                    "Downstream address of the related hop in a test.";
                }
                container ds-label-lists {
                  description
                    "List of downstream label information tables.";
                  list ds-label-list {
                    key "label-index";
                    description
                      "Statistics of downstream label information table.";
                    leaf label-index {
                      type uint32 {
                        range "1..4294967295";
                      } 
                      description
                        "The index of the ds label.";
                    }
                    leaf ds-label {
                      type uint32;
                      description
                        "Downstream labels.";
                    }
                  }
                }
              }
            }
          }
        }
      }
    }
  }
  rpc p2mp-start-ping {
    description
      "Start p2mp ping test.";
    ext:node-ref "/diagnostic-tools:diagnostic-tools/diagnostic-tools:p2mp/diagnostic-tools:ping-results";
    input {
      leaf test-name {
        type string {
          length "1..32";
        }
        mandatory true;
        description
          "Test name.";
      }
      choice lsp-protocol {
        mandatory true;
        description
          "Specifies the probe type of P2MP ping test.";
        case te-auto-tunnel {
          description
            "Specifies the interface type of the auto TE tunnel.";
          leaf auto-tunnel-name {
            type string {
              length "1..31";
            }
            mandatory true;
            description
              "Auto tunnel name.";
          }
        }
        case te {
          description
            "Specifies the interface name of the TE tunnel.";
          leaf tunnel-name {
            type string {
              length "1..33";
            }
            mandatory true;
            description
              "TE tunnel name.";
          }
        }
        case mldp {
          description
            "Specifies multipoint extensions for LDP.";
          leaf root-address {
            type inet:ipv4-address-no-zone;
            mandatory true;
            description
              "Root IP address.";
          }
          choice opaque-type {
            mandatory true;
            description
              "Specifies the probe type for P2MP LDP LSP.";
            case lsp-id {
              description
                "Specifies the ID on a P2MP LDP LSP.";
              leaf lsp-id {
                type uint32 {
                  range "0..4294967295";
                }
                description
                  "LSP ID.";
              }
            }
            case opaque-value {
              description
                "Specifies information used to uniquely identify a P2MP LDP LSP.";
              leaf opaque-value {
                type string {
                  length "1..254";
                }
                description
                  "The characteristic information of the LSP.";
              }
            }
          }
        }
      }
      leaf leaf-address {
        type inet:ipv4-address-no-zone;
        description
          "Leaf IP address.";
      }
      leaf source-address {
        type inet:ipv4-address-no-zone;
        description
          "Source IP address.";
      }
      leaf count {
        type uint32 {
          range "1..4294967295";
        }
        default "5";
        description
          "Number of sent test packets.";
      }
      leaf interval {
        type uint32 {
          range "2000..10000";
        }
        units "ms";
        default "2000";
        description
          "Interval for sending test packets.";
      }
      leaf packet-size {
        type uint32 {
          range "65..9600";
        }
        units "Byte";
        default "100";
        description
          "Number of bytes in a sent test packet.";
      }
      leaf exp {
        type uint32 {
          range "0..7";
        }
        default "0";
        description
          "EXP value in the label field of MPLS packets. The EXP value is used to distinguish the service types of MPLS packets.";
      }
      leaf timeout {
        type uint32 {
          range "2000..65535";
        }
        units "ms";
        default "2000";
        description
          "Time to wait for a response packet after a test packet is sent. If no response packet is received within the timeout period, the system considers that the test packet times out.";
      }
      leaf jitter {
        type uint32 {
          range "0..1000";
        }
        default "0";
        description
          "Wait for the upper bound value of the reply message to be answered.";
      }
      leaf reply-mode {
        type reply-mode-p2mp;
        default "udp";
        description
          "Mode for responding to test packets in a test.";
      }
    }
  }

  rpc p2mp-stop-ping {
    description
      "Stop p2mp ping test.";
    ext:node-ref "/diagnostic-tools:diagnostic-tools/diagnostic-tools:p2mp/diagnostic-tools:ping-results";
    input {
      leaf test-name {
        type leafref {
          path "/diagnostic-tools:diagnostic-tools/diagnostic-tools:p2mp/diagnostic-tools:ping-results/diagnostic-tools:ping-result/diagnostic-tools:test-name";
        }
        mandatory true;
        description
          "Test name.";
      }
    }
  }

  rpc p2mp-delete-ping {
    description
      "Delete p2mp ping test.";
    ext:node-ref "/diagnostic-tools:diagnostic-tools/diagnostic-tools:p2mp/diagnostic-tools:ping-results";
    input {
      leaf test-name {
        type leafref {
          path "/diagnostic-tools:diagnostic-tools/diagnostic-tools:p2mp/diagnostic-tools:ping-results/diagnostic-tools:ping-result/diagnostic-tools:test-name";
        }
        mandatory true;
        description
          "Test name.";
      }
    }
  }

  rpc p2mp-start-trace {
    description
      "Start p2mp trace test.";
    ext:node-ref "/diagnostic-tools:diagnostic-tools/diagnostic-tools:p2mp/diagnostic-tools:trace-results";
    input {
      leaf test-name {
        type string {
          length "1..32";
        }
        mandatory true;
        description
          "Test name.";
      }
      choice lsp-protocol {
        mandatory true;
        description
          "Specifies the probe type of P2MP tracert test.";
        case te-auto-tunnel {
          description
            "Specifies the interface type of the auto TE tunnel.";
          leaf auto-tunnel-name {
            type string {
              length "1..31";
            }
            mandatory true;
            description
              "Auto tunnel name.";
          }
          leaf leaf-address {
            type inet:ipv4-address-no-zone;
            description
              "Leaf IP address.";
          }
        }
        case mldp {
          description
            "Specifies multipoint extensions for LDP.";
          leaf root-address {
            type inet:ipv4-address-no-zone;
            mandatory true;
            description
              "Root IP address.";
          }
          choice opaque-type {
            mandatory true;
            description
              "Specifies the probe type for P2MP LDP LSP.";
            case lsp-id {
              description
                "Specifies the ID on a P2MP LDP LSP.";
              leaf lsp-id {
                type uint32 {
                  range "0..4294967295";
                }
                description
                  "LSP ID.";
              }
            }
            case opaque-value {
              description
                "Specifies information used to uniquely identify a P2MP LDP LSP.";
              leaf opaque-value {
                type string {
                  length "1..254";
                }
                description
                  "The characteristic information of the LSP.";
              }
            }
          }
        }
      }
      leaf ttl-flag {
        type ttl-flag-type;
        default "disable";
        description
          "The TTL flag, respond only if TTL expired.";
      }
      leaf source-address {
        type inet:ipv4-address-no-zone;
        description
          "Source IP address.";
      }
      leaf exp {
        type uint32 {
          range "0..7";
        }
        default "0";
        description
          "EXP value in the label field of MPLS packets. The EXP value is used to distinguish the service types of MPLS packets.";
      }
      leaf timeout {
        type uint32 {
          range "2000..65535";
        }
        units "ms";
        default "2000";
        description
          "Time taken to wait for the response packets after detection packets are sent. If no response packet is received within the timeout period, the system considers that the test packet times out.";
      }
      leaf jitter {
        type uint32 {
          range "0..1000";
        }
        default "0";
        description
          "The upper bound of the jitter period in milliseconds for responders to randomly delay before sending an echo reply.";
      }
      leaf ttl {
        type uint8 {
          range "1..255";
        }
        default "64";
        description
          "The life time value of the test message.";
      }
      leaf reply-mode {
        type reply-mode-p2mp;
        default "udp";
        description
          "Mode for responding to test packets in a test.";
      }
    }
  }

  rpc p2mp-stop-trace {
    description
      "Stop p2mp trace test.";
    ext:node-ref "/diagnostic-tools:diagnostic-tools/diagnostic-tools:p2mp/diagnostic-tools:trace-results";
    input {
      leaf test-name {
        type leafref {
          path "/diagnostic-tools:diagnostic-tools/diagnostic-tools:p2mp/diagnostic-tools:trace-results/diagnostic-tools:trace-result/diagnostic-tools:test-name";
        }
        mandatory true;
        description
          "Test name.";
      }
    }
  }

  rpc p2mp-delete-trace {
    description
      "Delete p2mp trace test.";
    ext:node-ref "/diagnostic-tools:diagnostic-tools/diagnostic-tools:p2mp/diagnostic-tools:trace-results";
    input {
      leaf test-name {
        type leafref {
          path "/diagnostic-tools:diagnostic-tools/diagnostic-tools:p2mp/diagnostic-tools:trace-results/diagnostic-tools:trace-result/diagnostic-tools:test-name";
        }
        mandatory true;
        description
          "Test name.";
      }
    }
  }

  augment "/diagnostic-tools:diagnostic-tools" {
    description
      "List of P2MP ping and trace tests.";
    container p2mp {
      config false;
      description
        "Statistics of P2MP ping and trace tests.";
      uses diagnostic-tools:p2mp-ping-trace-result-type;
    }
  }
}
