/*
Copyright (C) 2019 Huawei Technologies Co., Ltd. All rights reserved.
*/
module huawei-wlan-group-radio-deviations-ar5710s {
  yang-version 1;
  namespace "urn:huawei:yang:huawei-wlan-group-radio-deviations-ar5710s";
  prefix hw-grd-devs-ar5710s;

  import huawei-wlan-group-radio {
    prefix hw-grd;
  }
  import huawei-wlan-ap-group-profile {
    prefix hw-wlan-agp;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-group-radio module.";

  revision 2019-11-06 {
    description
      "Initial revision.";
    reference "Huawei private.";
  }

  deviation "/hw-wlan-agp:wlan-ap-group-profile/hw-wlan-agp:ap-group-profiles/hw-wlan-agp:ap-group-profile/hw-grd:radio-instances/hw-grd:radio-instance/hw-grd:channel-info/hw-grd:bandwidth/hw-grd:bandwidth-80plus80mhz" {
    deviate not-supported;
  }
  deviation "/hw-wlan-agp:wlan-ap-group-profile/hw-wlan-agp:ap-group-profiles/hw-wlan-agp:ap-group-profile/hw-grd:radio-instances/hw-grd:radio-instance/hw-grd:flexible-radio" {
    deviate not-supported;
  }
  deviation "/hw-wlan-agp:wlan-ap-group-profile/hw-wlan-agp:ap-group-profiles/hw-wlan-agp:ap-group-profile/hw-grd:radio-instances/hw-grd:radio-instance/hw-grd:coverage" {
    deviate not-supported;
  }
  deviation "/hw-wlan-agp:wlan-ap-group-profile/hw-wlan-agp:ap-group-profiles/hw-wlan-agp:ap-group-profile/hw-grd:radio-instances/hw-grd:radio-instance/hw-grd:reference-data-analysis" {
    deviate not-supported;
  }
  deviation "/hw-wlan-agp:wlan-ap-group-profile/hw-wlan-agp:ap-group-profiles/hw-wlan-agp:ap-group-profile/hw-grd:radio-instances/hw-grd:radio-instance/hw-grd:asfn-roam" {
    deviate not-supported;
  }
}
