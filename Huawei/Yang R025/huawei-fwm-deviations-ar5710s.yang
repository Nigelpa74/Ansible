/*
Copyright (C) 2025 Huawei Technologies Co., Ltd. All rights reserved.
*/
module huawei-fwm-deviations-ar5710s {
  namespace "urn:huawei:yang:huawei-fwm-deviations-ar5710s";
  prefix fwm-devs-ar5710s;

  import huawei-fwm {
    prefix fwm;
  }

  organization
    "Huawei Technologies Co., Ltd.";
  contact
    "Huawei Industrial Base
     Bantian, Longgang
     Shenzhen 518129
     People's Republic of China
     Website: http://www.huawei.com
     Email: support@huawei.com";
  description
    "This module defines deviation statements for huawei-fwm module.";

  revision 2025-02-24 {
    description
      "Initial revision.";
    reference "Huawei private.";
  }

  deviation "/fwm:fwm/fwm:work-mode" {
    deviate not-supported;
  }
  deviation "/fwm:fwm/fwm:coprocessor-mode" {
    deviate not-supported;
  }
  deviation "/fwm:fwm/fwm:forward-resource-mode" {
    deviate not-supported;
  }
  deviation "/fwm:fwm/fwm:fmea-items" {
    deviate not-supported;
  }
}
