/*
Copyright (C) 2025 Huawei Technologies Co., Ltd. All rights reserved.
*/
module huawei-codesign-deviations-ar5710s {
  namespace "urn:huawei:yang:huawei-codesign-deviations-ar5710s";
  prefix codesign-devs-ar5710s;

  import huawei-codesign {
    prefix codesign;
  }

  organization
    "Huawei Technologies Co., Ltd.";
  contact
    "Huawei Industrial Base
     Bantian, Longgang
     Shenzhen 518129
     People's Republic of China
     Website: http://www.huawei.com
     Email: support@huawei.com";
  description
    "This module defines deviation statements for huawei-codesign module.";

  revision 2025-02-24 {
    description
      "Initial revision.";
    reference "Huawei private.";
  }

  deviation "/codesign:codesign/codesign:software-crls/codesign:software-crl/codesign:valid" {
    deviate not-supported;
  }
}
