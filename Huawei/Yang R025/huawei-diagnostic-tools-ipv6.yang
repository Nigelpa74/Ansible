/*
Copyright (C) 2019-2025 Huawei Technologies Co., Ltd. All rights reserved.
*/
submodule huawei-diagnostic-tools-ipv6 {
  yang-version 1;
  belongs-to huawei-diagnostic-tools {
    prefix diagnostic-tools;
  }

  import huawei-pub-type {
    prefix pub-type;
  }
  import huawei-network-instance {
    prefix ni;
  }
  import huawei-ifm {
    prefix ifm;
  }
  import ietf-yang-types {
    prefix yang;
  }
  import ietf-inet-types {
    prefix inet;
  }
  import huawei-extension {
    prefix ext;
  }
  include huawei-diagnostic-tools-common;
  include huawei-diagnostic-tools-type;

  organization
    "Huawei Technologies Co., Ltd.";
  contact
    "Huawei Industrial Base
     Bantian, Longgang
     Shenzhen 518129
     People's Republic of China
     Website: http://www.huawei.com
     Email: support@huawei.com";
  description
    "IPv6 diagnosis tool.";
  revision 2025-05-17 {
    description
      "Modify must condition of sd-wan-connectid. Add slot-id in vxlan-start-ping and vxlan-start-trace, and Modify timeout range, and Add srv6-trace no-bypass. Add board-select-interface.";
    reference
      "Huawei private.";
  }
  revision 2025-02-13 {
    description
      "Modify wrong description.";
    reference
      "Huawei private.";
  }
  revision 2024-08-05 {
    description
      "Add sd-wan-connectid.";
    reference
      "Huawei private.";
  }
  revision 2023-12-08 {
    description
      "Correct Ecmp mtu type.";
    reference
      "Huawei private.";
  }
  revision 2022-07-05 {
    description
      "Add uint of packet-size. Modify timeout and udp-port range. Modify range for index in ping-results container. Add range for hop-index, probe-index, label-index, sid-index in trace-results container.";
    reference "Huawei private.";
  }
  revision 2022-04-06 {
    description
      "Add source interface and APN instance for IPv6 ping/trace.";
    reference
      "Huawei private.";
  }
  revision 2022-01-27 {
    description
      "Delete config false of container.";
    reference
      "Huawei private.";
  }
  revision 2022-01-24 {
    description
      "Add ttl-mode for IPv6 trace.";
    reference
      "Huawei private.";
  }
  revision 2022-01-22 {
    description
      "Yang parameter completion.";
    reference
      "Huawei private.";
  }
  revision 2022-01-04 {
    description
      "Add ignore MTU node.";
    reference
      "Huawei private.";
  }

  revision 2020-09-10 {
    description
      "Add fast reply inbound node.";
    reference
      "Huawei private.";
  }

  revision 2020-03-10 {
    description
      "Modify description.";
    reference
      "Huawei private.";
  }
  revision 2020-01-14 {
    description
      "Delete augment of diagnostic-tools-output.";
    reference
      "Huawei private.";
  }
  revision 2019-12-19 {
    description
      "Inherit released YANG.";
    reference
      "Huawei private.";
  }
  revision 2019-04-09 {
    description
      "Initial revision.";
    reference
      "Huawei private.";
  }
  grouping ip6-ping-trace-result-type {
    description
      "IPv6 ping trace test result.";
    container ping-results {
      description
        "List of test result.";
      list ping-result {
        key "test-name";
        description
          "Statistics of test result of a certain hop in the test path. For a ping-type test, there is only one test result.";
        leaf test-name {
          type string {
            length "1..32";
          }
          description
            "Test name.";
        }
        leaf packet-recv {
          type uint32 {
            range "0..4294967295";
          }
          description
            "Total number of received packets.";
        }
        leaf packet-send {
          type uint32 {
            range "0..4294967295";
          }
          description
            "Total number of sent packets.";
        }
        leaf loss-ratio {
          type pub-type:percent {
            range "0..100";
          }
          units "%";
          description
            "Packet loss ratio of a test.";
        }
        leaf rtt-min {
          type uint32 {
            range "0..4294967295";
          }
          units "ms";
          description
            "Minimum RTT of all test packets.";
        }
        leaf rtt-max {
          type uint32 {
            range "0..4294967295";
          }
          units "ms";
          description
            "Maximum RTT of all test packets.";
        }
        leaf average-rtt {
          type uint32 {
            range "0..4294967295";
          }
          units "ms";
          description
            "Average RTT of all test packets.";
        }
        leaf host-name {
          type pub-type:host-name;
          description
            "Host name.";
        }
        leaf status {
          type dgntl-test-status-type;
          description
            "Test status.";
        }
        leaf error-type {
          type dgntl-error-type;
          status deprecated;
          description
            "Test operation status.";
        }
        container ping-result-details {
          description
            "List of ping results of all packets in a test.";
          list ping-result-detail {
            key "index";
            description
              "Statistics of probe result.";
            leaf index {
              type uint32 {
                range "1..4294967295";
              }
              description
                "Serial number of a test packet received by a certain hop.";
            }
            leaf dest-ip-addr {
              type inet:ipv6-address-no-zone;
              description
                "Destination address of the related hop in a test.";
            }
            leaf packet-size {
              type uint32 {
                range "0..4294967295";
              }
              units "Byte";
              description
                "Number of bytes in a received response packet.";
            }
            leaf ttl {
              type uint8 {
                range "1..255";
              }
              description
                "Hop limit of received response packets.";
            }
            leaf rtt {
              type uint32 {
                range "0..4294967295";
              }
              units "ms";
              description
                "RTT of test packets.";
            }
            leaf result-type {
              type detail-result-type;
              description
                "Result of packet sending, which is either success or timeout.";
            }
            leaf is-delete {
              ext:support-filter "true";
              type boolean;
              description
                "Enable/disable the function of deleting test results.";
            }
            leaf system-time {
              type yang:date-and-time;
              description
                "System time of response packets.";
            }
            leaf incoming-if-name {
              type string {
                length "1..255";
              }
              description
                "The logical source interface of echo response packet.";
            }
            leaf incoming-phy-if-name {
              type string {
                length "1..255";
              }
              description
                "The physical source interface of echo response packet.";
            }
            leaf error-code {
              type ip6-ping-detail-error-code;
              description
                "Error code of a detection failure. This object is displayed only when detail-output is specified and the detection fails due to certain reasons.";
            }
            leaf actural-icmp-id {
              type uint32;
              description
                "The actual icmp_id. This object is displayed only when detail-output is specified and the detection fails because the icmp_id is not the expected value.";
            }
            leaf expect-icmp-id {
              type uint32;
              description
                "The expected icmp_id. This object is displayed only when detail-output is specified and the detection fails because the icmp_id is not the expected value.";
            }
            leaf actural-sequence {
              type uint32;
              description
                "The actual sequence. This object is displayed only when detail-output is specified and the detection fails because the sequence is not the expected value.";
            }
            leaf expect-sequence {
              type uint32;
              description
                "The expected sequence. This object is displayed only when detail-output is specified and the detection fails because the sequence is not the expected value.";
            }
            leaf icmp-error-code {
              type uint16;
              description
                "ICMP error code of a received packet. This object is displayed only when detail-output is specified and the detection fails due to ICMP error.";
            }
            leaf icmp-error-type {
              type uint16;
              description
                "ICMP error type of a received packet. This object is displayed only when detail-output is specified and the detection fails due to ICMP error.";
            }
            leaf path-reason {
              type uint32;
              description
                "The path reason. This object is displayed only when detail-output is specified and the detection fails due to path reason.";
            }
          }
        }
      }
    }
    container trace-results {
      description
        "List of test result.";
      list trace-result {
        key "test-name";
        description
          "Statistics of trace test result.";
        leaf test-name {
          type string {
            length "1..32";
          }
          description
            "Test name.";
        }
        leaf host-name {
          type pub-type:host-name;
          description
            "Host name.";
        }
        leaf status {
          type dgntl-test-status-type;
          description
            "Test status.";
        }
        leaf error-type {
          type dgntl-error-type;
          status deprecated;
          description
            "Test operation status.";
        }
        container trace-result-details {
          status deprecated;
          description
            "List of ping results of all packets in a test.";
          list trace-result-detail {
            key "index";
            status deprecated;
            description
              "Statistics of ping result of a single packet in a test.";
            leaf index {
              type uint32;
              status deprecated;
              description
                "Serial number of a hop in the test path. For a ping-type test such as the ping test or LSP ping test, there is only one hop in the test path, so the value is 1. For a trace-type test such as the trace test or LSP trace test, the value indicates the exact serial number of a hop in the test path.";
            }
            leaf ttl {
              type uint8 {
                range "1..255";
              }
              status deprecated;
              description
                "TTL of received response packets.";
            }
            leaf rtt {
              type uint32;
              status deprecated;
              description
                "RTT of test packets.";
            }
            leaf dest-ip-addr {
              type inet:ipv6-address-no-zone;
              status deprecated;
              description
                "Destination address of the related hop in a test.";
            }
            leaf is-delete {
              ext:support-filter "true";
              type boolean;
              status deprecated;
              description
                "Enable/disable the function of deleting test results.";
            }
          }
        }
        container hops {
          description
            "List of hop results.";
          list hop {
            key "hop-index";
            description
              "Statistics of hop result.";
            leaf hop-index {
              type uint32 {
                range "1..4294967295";
              }              
              description
                "The index of the hop.";
            }
            leaf is-delete {
              ext:support-filter "true";
              type boolean;
              description
                "Enable/disable the function of deleting test results.";
            }
            container probes {
              description
                "List of probe results.";
              list probe {
                key "probe-index";
                description
                  "Statistics of probe result.";
                leaf probe-index {
                  type uint32 {
                    range "1..4294967295";
                  }                
                  description
                    "The index of the probe packet.";
                }
                leaf rtt {
                  type uint32;
                  description
                    "RTT of test packets, expressed in milliseconds.";
                }
                leaf replier {
                  type inet:ipv6-address-no-zone;
                  description
                    "Reply address of the related hop in a test.";
                }
                leaf result-type {
                  type probe-result-type;
                  description
                    "Result of packet sending, which is either success or timeout.";
                }
                leaf srh-segment-left {
                  type uint32;
                  description
                    "Segments left.";
                }
                container mpls-labels {
                  description
                    "List of MPLS label informations.";
                  list mpls-label {
                    key "label-index";
                    description
                      "Statistics of MPLS label information.";
                    leaf label-index {
                      type uint32 {
                        range "1..4294967295";
                      }                      
                      description
                        "Label index.";
                    }
                    leaf label-value {
                      type uint32;
                      description
                        "Show MPLS label value.";
                    }
                    leaf label-exp {
                      type uint32;
                      description
                        "Show MPLS label exp.";
                    }
                    leaf label-stack-bottom {
                      type uint32;
                      description
                        "Show MPLS label stack bottom flag.";
                    }
                    leaf label-ttl {
                      type uint32;
                      description
                        "Show MPLS label TTL.";
                    }
                  }
                }
                container srh-sids {
                  description
                    "List of SID informations.";
                  list srh-sid {
                    key "sid-index";
                    description
                      "Statistics of SID information.";
                    leaf sid-index {
                      type uint32 {
                        range "1..4294967295";
                      }                      
                      description
                        "SID index.";
                    }
                    leaf sid {
                      type inet:ipv6-address-no-zone;
                      description
                        "Segment ID.";
                    }
                  }
                }
                leaf slice-id {
                  type uint32;
                  description
                    "Network slice ID.";
                }
              }
            }
          }
        }
      }
    }
  }
  grouping ip6-multipath-ping-trace-result-type {
    description
      "Multipath test result.";
    container trace-results {
      description
        "List of trace test results.";
      list trace-result {
        key "test-name";
        description
          "Statistics of trace test result.";
        leaf test-name {
          type string {
            length "1..32";
          }
          description
            "Test name.";
        }
        leaf status {
          type dgntl-test-status-type;
          description
            "Test status.";
        }
        leaf path-detect-result {
          type path-detect-result-type;
          description
            "Path detection result,indicating whether a path is detected.";
        }
        container paths {
          description
            "List of path results.";
          list path {
            key "path-index";
            description
              "Statistics of path result.";
            leaf path-index {
              type uint32 {
                range "1..4294967295";
              }
              description
                "The index of the path.";
            }
            leaf dest-port {
              type uint32;
              description
                "Destination port of the related hop in a test.";
            }
            container hops {
              description
                "List of hop results.";
              list hop {
                key "hop-index";
                description
                  "Statistics of hop result.";
                leaf hop-index {
                  type uint32 {
                    range "0..4294967295";
                  }
                  description
                    "The index of the hop.";
                }
                leaf replier {
                  type inet:ipv6-address-no-zone;
                  description
                    "Reply address of the related hop in a test.";
                }
                leaf rtt {
                  type uint32;
                  units "ms";
                  description
                    "RTT of test packets.";
                }
                leaf type {
                  type uint16;
                  description
                    "ICMP type.";
                }
                leaf code {
                  type uint16;
                  description
                    "ICMP code.";
                }
                leaf error-info {
                  type string {
                    length "1..128";
                  }
                  description
                    "ICMP error packet information.";
                }
                leaf result-type {
                  type probe-result-type;
                  description
                    "Result of packet sending, which is either success or timeout.";
                }
                leaf inbound-interface-name {
                  type string {
                    length "1..255";
                  }
                  description
                  "The name of interface that receives the test packet.";
                }
                leaf outbound-interface-name {
                  type string {
                    length "1..255";
                  }
                  description
                  "The name of interface that sends the test packet.";
                }
                leaf outbound-interface-mtu {
                  type uint16;
                  units "Byte";
                  description
                  "The outbound interface MTU.";
                }
              }
            }
          }
        }
      }
    }
  }
  grouping start-ipv6-multipath-trace-type {
    description "Start IPv6 multiPath trace parameters.";
    leaf test-name {
      type string {
        length "1..32";
      }
      mandatory true;
      description
        "Test name.";
    }
     leaf dest-ip-address {
      type inet:ipv6-address-no-zone;
      mandatory true;
      description
        "Destination address of the string type.";
    }
    leaf vrf-name {
      type leafref {
        path "/ni:network-instance/ni:instances/ni:instance/ni:name";
      }
      description
        "Name of a VPN instance.";
    }
    leaf source-address {
      type inet:ipv6-address-no-zone;
      description
        "Source address of the string type.";
    }
    leaf dest-port-begin {
      type uint16 {
        range "1..65535";
      }
      default "33434";
      description
        "The begin destination port.";
    }
    leaf dest-port-end {
      type uint16 {
        range "1..65535";
      }
      must "../dest-port-begin <= ../dest-port-end";
      description
        "The end destination port.";
    }
    leaf source-if-name {
      type leafref {
        path "/ifm:ifm/ifm:interfaces/ifm:interface/ifm:name";
      }
      description
        "The source interface for echo requests.";
    }
    leaf first-ttl {
      type uint8 {
        range "1..255";
      }
      must "../first-ttl <= ../max-ttl";
      default "1";
      description
        "TTL of the first packet in a test.";
    }
    leaf max-ttl {
      type uint8 {
        range "1..255";
      }
      must "../first-ttl <= ../max-ttl";
      default "64";
      description
        "TTL of test packets.";
    }
    leaf count {
      type uint32 {
        range "1..65535";
      }
      default "1";
      description
        "Number of sent test packets.";
    }
    choice priority {
      description
        "Priority type.";
      case dscp-value {
        description
          "DSCP value.";
        leaf dscp {
          type uint8 {
            range "0..63";
          }
          description
            "DSCP value.";
        }
      }
      case tc-value {
        description
          "Traffic class value.";
        leaf tc {
          type uint8 {
            range "0..255";
          }
          description
            "Traffic class value for echo requests to be sent.";
        }
      }
    }
  }
  rpc ipv6-start-ping {
    description
      "Start IPv6 ping.";
    ext:node-ref "/diagnostic-tools:diagnostic-tools/diagnostic-tools:ipv6/diagnostic-tools:ping-results";
    input {
      leaf test-name {
        type string {
          length "1..32";
        }
        mandatory true;
        description
          "Test name.";
      }
      leaf dest-addr {
        type pub-type:host-name;
        description
          "Destination address of the string type. You can click this node to set different types of addresses and deploy the configurations together with the configuration of the destination address type node. If the destination address type is set to IPv4, this parameter is set to IPv4. If the destination address type is set to IPv6, this parameter is set to IPv6.";
      }
      leaf source-address {
        type inet:ipv6-address-no-zone;
        description
          "Source address of the string type. You can click this node to set different types of addresses and deploy the configurations together with the configuration of the source address type node. If the source address type is set to IPv4, this parameter is set to IPv4. If the source address type is set to IPv6, this parameter is set to IPv6.";
      }
      leaf vrf-name {
        type leafref {
          path "/ni:network-instance/ni:instances/ni:instance/ni:name";
        }
        description
          "Name of a VPN instance.";
      }
      leaf peer-address {
        when "../vrf-name";
        type inet:ipv6-address-no-zone;
        description
          "Peer SID, which is the address of the last hop in the SRv6 domain, in EVPN L3VPN over SRv6 BE scenarios.";
      }
      leaf interval {
        type uint32 {
          range "1..10000";
        }
        units "ms";
        description
          "Interval for sending test packets.";
      }
      leaf packet-size {
        type uint32 {
          range "20..9600";
        }
        units "Byte";
        description
          "Number of bytes in a sent test packet.";
      }
      leaf packet-count {
        type uint32 {
          range "1..4294967295";
        }
        description
          "Number of sent test packets.";
      }
      leaf timeout {
        type uint32 {
          range "0..65535";
        }
        units "ms";
        description
          "Time to wait for a response packet after a test packet is sent. If no response packet is received within the timeout period, the system considers that the test packet times out.";
      }
      leaf ttl {
        type uint8 {
          range "1..255";
        }
        description
          "Time to live.";
      }
      leaf if-name {
        type leafref {
          path "/ifm:ifm/ifm:interfaces/ifm:interface/ifm:name";
        }
        description
          "The out interface for sending packets.";
      }
      leaf inbound-reply-fast {
        type boolean;
        must "../if-name and not(../nexthop-address) and not(../source-if-name)";
        description
          "Enable/disable fast reply from the specified Eth-Trunk member interface.";
      }
      leaf source-if-name {
        type leafref {
          path "/ifm:ifm/ifm:interfaces/ifm:interface/ifm:name";
        }
        description
          "The source interface for echo requests.";
      }
      leaf apn-ipv6-inst-name {
        type string {
          length "1..31";
        }
        must "../source-if-name and not(../nexthop-address or ../service-class or ../te-class or ../ignore-mtu='true' or ../ipv6-forwarding='true' or ../sid1)";
        description
          "APN IPv6 instance name.";
      }
      leaf segment-by-segment {
        type boolean;
        description
          "Enable/disable segment-by-segment deletion.";
      }
      leaf min-packet-size {
        type uint32 {
          range "20..9600";
        }
        units "Byte";
        description
          "The minimum size of packet to be sent.";
      }
      leaf max-packet-size {
        type uint32 {
          range "20..9600";
        }
        units "Byte";
        description
          "The maximum size of packet to be sent.";
      }
      leaf step-size {
        type uint32 {
          range "1..1000";
        }
        units "Byte";
        description
          "Increasing step size.";
      }
      leaf nexthop-address {
        type inet:ipv6-address-no-zone;
        description
          "Next hop IPv6 address.";
      }
      leaf ignore-mtu {
        type boolean;
        description
          "Enable/disable the function to ignore the MTU check.";
      }
      leaf show-system-time {
        type boolean;
        description
          "Enable/disable the function to display system time.";
      }
      leaf show-incoming-if-name {
        type boolean;
        description
          "Enable/disable the function to display the interface name for incoming packets.";
      }
      leaf ipv6-forwarding {
        type boolean;
        description
          "Enable/disable the function to forward request packets by IPv6.";
      }
      leaf show-host-name {
        type empty;
        description
          "Display the host name of the destination address.";
      }
      leaf show-detail {
        type empty;
        description
          "Detail information is displayed.";
      }
      choice priority {
        description
          "Priority type.";
        case dscp-value {
          description
            "DSCP value.";
          leaf dscp {
            type uint32 {
              range "0..63";
            }
            description
              "DSCP value.";
          }
        }
        case tos-value {
          description
            "ToS value.";
          leaf tos {
            type uint8 {
              range "0..255";
            }
            description
              "ToS.";
          }
        }
      }
      leaf pattern {
        type string {
          length "1..8";
        }
        description
          "Packet fill.";
      }
      leaf sid1 {
        type inet:ipv6-address-no-zone;
        description
          "Segment ID.";
      }
      leaf sid2 {
        type inet:ipv6-address-no-zone;
        description
          "Segment ID.";
      }
      leaf sid3 {
        type inet:ipv6-address-no-zone;
        description
          "Segment ID.";
      }
      leaf sid4 {
        type inet:ipv6-address-no-zone;
        description
          "Segment ID.";
      }
      leaf sid5 {
        type inet:ipv6-address-no-zone;
        description
          "Segment ID.";
      }
      leaf sid6 {
        type inet:ipv6-address-no-zone;
        description
          "Segment ID.";
      }
      leaf sid7 {
        type inet:ipv6-address-no-zone;
        description
          "Segment ID.";
      }
      leaf sid8 {
        type inet:ipv6-address-no-zone;
        description
          "Segment ID.";
      }
      leaf sid9 {
        type inet:ipv6-address-no-zone;
        description
          "Segment ID.";
      }
      leaf sid10 {
        type inet:ipv6-address-no-zone;
        description
          "Segment ID.";
      }
      leaf sid11 {
        type inet:ipv6-address-no-zone;
        description
          "Segment ID.";
      }      
      leaf network-slice-id {
        when "../sid1";
        type uint32 {
          range "1..4294967295";
        }
        description
          "Network slice ID.";
      }
      leaf force-match-slice {
        when "../sid1 and ../network-slice-id";
        type empty;
        description
          "Mandatory match network slice.";
      }
      leaf service-class {
        type diagnostic-tools:service-class-value;
        description
          "Service class.";
      }
      leaf te-class {
        type uint32 {
          range "1..65535";
        }
        description
          "TE class.";
      }
      leaf evc-sub-if-name {
        type leafref {
          path "/ifm:ifm/ifm:interfaces/ifm:interface/ifm:name";
        }
        description
          "Name of the EVC sub-interface.";
      }
      leaf sd-wan-connectid {
        type uint32 {
          range "1..4294967295";
        }
        must "not(../peer-address) and not(../if-name) and not(../inbound-reply-fast) and not(../source-if-name) and not(../apn-ipv6-inst-name) and not(../segment-by-segment) and not(../show-incoming-if-name) and not(../show-host-name) and not(../nexthop-address) and not(../show-system-time) and not(../show-detail) and not(../ipv6-forwarding) and not(../te-class) and not(../evc-sub-if-name) and not(../service-class) and not(../network-slice-id) and not(../force-match-slice) and not(../sid1) and not(../sid2) and not(../sid3) and not(../sid4) and not(../sid5) and not(../sid6) and not(../sid7) and not(../sid8) and not(../sid9) and not(../sid10) and not(../sid11)";
        description
          "SD-WAN connection ID.";
      }
      leaf board-select-if-name {
        type leafref {
          path "/ifm:ifm/ifm:interfaces/ifm:interface/ifm:name";
        }
        description
          "Name of the interface used for board selection.";
      }
    }
  }

  rpc ipv6-stop-ping {
    description
      "Stop IPv6 ping.";
    ext:node-ref "/diagnostic-tools:diagnostic-tools/diagnostic-tools:ipv6/diagnostic-tools:ping-results";
    input {
      leaf test-name {
        type leafref {
          path "/diagnostic-tools:diagnostic-tools/diagnostic-tools:ipv6/diagnostic-tools:ping-results/diagnostic-tools:ping-result/diagnostic-tools:test-name";
        }
        mandatory true;
        description
          "Test name.";
      }
    }
  }

  rpc ipv6-delete-ping {
    description
      "Delete IPv6 ping.";
    ext:node-ref "/diagnostic-tools:diagnostic-tools/diagnostic-tools:ipv6/diagnostic-tools:ping-results";
    input {
      leaf test-name {
        type leafref {
          path "/diagnostic-tools:diagnostic-tools/diagnostic-tools:ipv6/diagnostic-tools:ping-results/diagnostic-tools:ping-result/diagnostic-tools:test-name";
        }
        mandatory true;
        description
          "Test name.";
      }
    }
  }

  rpc ipv6-start-trace {
    description
      "Start IPv6 trace.";
    ext:node-ref "/diagnostic-tools:diagnostic-tools/diagnostic-tools:ipv6/diagnostic-tools:trace-results";
    input {
      leaf test-name {
        type string {
          length "1..32";
        }
        mandatory true;
        description
          "Test name.";
      }
      leaf dest-addr {
        type pub-type:host-name;
        description
          "Destination address of the string type. You can click this node to set different types of addresses and deploy the configurations together with the configuration of the destination address type node. If the destination address type is set to IPv4, this parameter is set to IPv4. If the destination address type is set to IPv6, this parameter is set to IPv6.";
      }
      leaf source-address {
        type inet:ipv6-address-no-zone;
        description
          "Source address of the string type. You can click this node to set different types of addresses and deploy the configurations together with the configuration of the source address type node. If the source address type is set to IPv4, this parameter is set to IPv4. If the source address type is set to IPv6, this parameter is set to IPv6.";
      }
      leaf vrf-name {
        type leafref {
          path "/ni:network-instance/ni:instances/ni:instance/ni:name";
        }
        description
          "Name of a VPN instance.";
      }
      leaf peer-address {
        when "../vrf-name";
        type inet:ipv6-address-no-zone;
        description
          "VPN IPv6 peer router address.";
      }
      leaf packet-size {
        type uint32 {
          range "20..9600";
        }
        units "Byte";
        description
          "Number of bytes in a sent test packet.";
      }
      leaf count {
        type uint32 {
          range "1..65535";
        }
        description
          "Number of sent test packets.";
      }
      leaf timeout {
        type uint32 {
          range "1..65535";
        }
        units "ms";
        description
          "Time to wait for a response packet after a test packet is sent. If no response packet is received within the timeout period, the system considers that the test packet times out.";
      }
      leaf first-ttl {
        type uint8 {
          range "1..255";
        }
        description
          "TTL of the first packet in a test.";
      }
      leaf max-ttl {
        type uint8 {
          range "1..255";
        }
        description
          "TTL of test packets.";
      }
      leaf udp-port {
        type uint32 {
          range "1..65535";
        }
        default "33434";
        description
          "Destination port number.";
      }
      leaf fixed-port-flag {
        type empty;
        description
          "Fixed destination UDP port.";
      }
      leaf show-mpls-label {
        type boolean;
        description
          "Enable/disable the function to display the MPLS label information flag.";
      }
      leaf overlay {
        type boolean;
        description
          "Enable/disable the overlay function.";
      }
      leaf nexthop-address {
        type inet:ipv6-address-no-zone;
        description
          "Next hop IPv6 address.";
      }
      leaf if-name {
        type leafref {
          path "/ifm:ifm/ifm:interfaces/ifm:interface/ifm:name";
        }
        description
          "The out interface for sending packets.";
      }
      leaf source-if-name {
        type leafref {
          path "/ifm:ifm/ifm:interfaces/ifm:interface/ifm:name";
        }
        description
          "The source interface for echo requests.";
      }
      leaf apn-ipv6-inst-name {
        type string {
          length "1..31";
        }
        must "../source-if-name and not(../nexthop-address or ../service-class or ../te-class or ../ignore-mtu='true' or ../sid1)";
        description
          "APN IPv6 instance name.";
      }
      choice priority {
        description
          "Priority type.";
        case dscp-value {
          description
            "DSCP value.";
          leaf dscp {
            type uint32 {
              range "0..63";
            }
            default "0";
            description
              "DSCP value.";
          }
        }
        case tc-value {
          description
            "Traffic class value.";
          leaf tc {
            type uint8 {
              range "0..255";
            }
            description
              "Traffic class value for echo requests to be sent.";
          }
        }
      }
      leaf pass-route {
          type boolean;
          description
            "Enable/disable pass-route deletion.";
      }
      leaf sid1 {
        type inet:ipv6-address-no-zone;
        description
          "Segment ID.";
      }
      leaf sid2 {
        type inet:ipv6-address-no-zone;
        description
          "Segment ID.";
      }
      leaf sid3 {
        type inet:ipv6-address-no-zone;
        description
          "Segment ID.";
      }
      leaf sid4 {
        type inet:ipv6-address-no-zone;
        description
          "Segment ID.";
      }
      leaf sid5 {
        type inet:ipv6-address-no-zone;
        description
          "Segment ID.";
      }
      leaf sid6 {
        type inet:ipv6-address-no-zone;
        description
          "Segment ID.";
      }
      leaf sid7 {
        type inet:ipv6-address-no-zone;
        description
          "Segment ID.";
      }
      leaf sid8 {
        type inet:ipv6-address-no-zone;
        description
          "Segment ID.";
      }
      leaf sid9 {
        type inet:ipv6-address-no-zone;
        description
          "Segment ID.";
      }
      leaf sid10 {
        type inet:ipv6-address-no-zone;
        description
          "Segment ID.";
      }
      leaf sid11 {
        type inet:ipv6-address-no-zone;
        description
          "Segment ID.";
      }
      leaf network-slice-id {
        when "../sid1";
        type uint32 {
          range "1..4294967295";
        }
        description
          "Network slice ID.";
      }
      leaf force-match-slice {
        when "../sid1 and ../network-slice-id";
        type empty;
        description
          "Mandatory match network slice.";
      }
      leaf service-class {
        type diagnostic-tools:service-class-value;
        description
          "Service class.";
      }
      leaf te-class {
        type uint32 {
          range "1..65535";
        }
        description
          "TE class.";
      }
      leaf ignore-mtu {
        type boolean;
        description
          "Enable/disable the function to ignore the MTU check.";
      }
      leaf show-host-name {
        type empty;
        description
          "Display the host name of the router on each hop.";
      }
      leaf ttl-mode {
        type trace-ttl-mode;
        description
        "TTL mode (pipe).";
      }
      leaf sd-wan-connectid {
        type uint32 {
          range "1..4294967295";
        }
        must "not(../peer-address) and not(../overlay) and not(../source-if-name) and not(../nexthop-address) and not(../pass-route) and not(../ttl-mode) and not(../if-name) and not(../te-class) and not(../apn-ipv6-inst-name) and not(../network-slice-id) and not(../force-match-slice) and not(../service-class) and not(../show-host-name) and not(../sid1) and not(../sid2) and not(../sid3) and not(../sid4) and not(../sid5) and not(../sid6) and not(../sid7) and not(../sid8) and not(../sid9) and not(../sid10) and not(../sid11)";
        description
          "SD-WAN connection ID.";
      }
      leaf board-select-if-name {
        type leafref {
          path "/ifm:ifm/ifm:interfaces/ifm:interface/ifm:name";
        }
        description
          "Name of the interface used for board selection.";
      }
    }
  }

  rpc ipv6-stop-trace {
    description
      "Stop IPv6 trace.";
    ext:node-ref "/diagnostic-tools:diagnostic-tools/diagnostic-tools:ipv6/diagnostic-tools:trace-results";
    input {
      leaf test-name {
        type leafref {
          path "/diagnostic-tools:diagnostic-tools/diagnostic-tools:ipv6/diagnostic-tools:trace-results/diagnostic-tools:trace-result/diagnostic-tools:test-name";
        }
        mandatory true;
        description
          "Test name.";
      }
    }
  }

  rpc ipv6-delete-trace {
    description
      "Delete IPv6 trace.";
    ext:node-ref "/diagnostic-tools:diagnostic-tools/diagnostic-tools:ipv6/diagnostic-tools:trace-results";
    input {
      leaf test-name {
        type leafref {
          path "/diagnostic-tools:diagnostic-tools/diagnostic-tools:ipv6/diagnostic-tools:trace-results/diagnostic-tools:trace-result/diagnostic-tools:test-name";
        }
        mandatory true;
        description
          "Test name.";
      }
    }
  }

  rpc ipv6-start-multipath-trace {
    description
      "Start IPv6 multipath trace test.";
    ext:node-ref "/diagnostic-tools:diagnostic-tools/diagnostic-tools:ipv6/diagnostic-tools:trace-results";
    input {
      leaf test-name {
        type string {
          length "1..32";
        }
        mandatory true;
        description
          "Test name.";
      }
      leaf dest-ip-address {
        type inet:ipv6-address-no-zone;
        mandatory true;
        description
          "Destination address of the string type.";
      }
      leaf vrf-name {
        type leafref {
          path "/ni:network-instance/ni:instances/ni:instance/ni:name";
        }
        description
          "Name of a VPN instance.";
      }
      leaf source-address {
        type inet:ipv6-address-no-zone;
        description
          "Source address of the string type.";
      }
      leaf dest-port-begin {
        type uint16 {
          range "1..65535";
        }
        default "33434";
        description
          "The begin destination port.";
      }
      leaf dest-port-end {
        type uint16 {
          range "1..65535";
        }
        must "../dest-port-begin <= ../dest-port-end";
        description
          "The end destination port.";
      }
      leaf source-if-name {
        type leafref {
          path "/ifm:ifm/ifm:interfaces/ifm:interface/ifm:name";
        }
        description
          "The source interface for echo requests.";
      }
      leaf first-ttl {
        type uint8 {
          range "1..255";
        }
        must "../first-ttl <= ../max-ttl";
        default "1";
        description
          "TTL of the first packet in a test.";
      }
      leaf max-ttl {
        type uint8 {
          range "1..255";
        }
        must "../first-ttl <= ../max-ttl";
        default "64";
        description
          "TTL of test packets.";
      }
      leaf timeout {
        type uint32 {
          range "1..65535";
        }
        units "ms";
        default "5000";
        description
          "Time to wait for a response packet after a test packet is sent. If no response packet is received within the timeout period, the system considers that the test packet times out.";
      }
      leaf count {
        type uint32 {
          range "1..65535";
        }
        default "1";
        description
          "Number of sent test packets.";
      }
      leaf packet-size {
        type uint32 {
          range "20..9600";
        }
        units "Byte";
        default "20";
        description
          "Number of bytes in a sent test packet.";
      }
      choice priority {
        description
          "Priority type.";
        case dscp-value {
          description
            "DSCP value.";
          leaf dscp {
            type uint8 {
              range "0..63";
            }
            description
              "DSCP value.";
          }
        }
        case tc-value {
          description
            "Traffic class value.";
          leaf tc {
            type uint8 {
              range "0..255";
            }
            description
              "Traffic class value for echo requests to be sent.";
          }
        }
      }
    }
  }
  rpc ipv6-start-multipath-trace-showpath {
    description
      "Start IPv6 multipath ECMP trace test.";
    ext:node-ref "/diagnostic-tools:diagnostic-tools/diagnostic-tools:ipv6/diagnostic-tools:trace-results";
    input {
      uses start-ipv6-multipath-trace-type;
      leaf timeout {
        type uint32 {
          range "100..600000";
        }
        units "ms";
        default "10000";
        description
          "Time to wait for a response packet after a test packet is sent. If no response packet is received within the timeout period, the system considers that the test packet times out.";
      }
      leaf packet-size {
        type uint32 {
          range "32..9600";
        }
        units "Byte";
        default "32";
        description
          "Number of bytes in a sent test packet.";
      }
    }
  }
  rpc ipv6-stop-multipath-trace {
    description
      "Stop IPv6 multipath trace test.";
    ext:node-ref "/diagnostic-tools:diagnostic-tools/diagnostic-tools:ipv6-multipath/diagnostic-tools:trace-results";
    input {
      leaf test-name {
        type leafref {
          path "/diagnostic-tools:diagnostic-tools/diagnostic-tools:ipv6-multipath/diagnostic-tools:trace-results/diagnostic-tools:trace-result/diagnostic-tools:test-name";
        }
        mandatory true;
        description
          "Test name.";
      }
    }
  }

  rpc ipv6-delete-multipath-trace {
    description
      "Delete IPv6 multipath trace test.";
    ext:node-ref "/diagnostic-tools:diagnostic-tools/diagnostic-tools:ipv6-multipath/diagnostic-tools:trace-results";
    input {
      leaf test-name {
        type leafref {
          path "/diagnostic-tools:diagnostic-tools/diagnostic-tools:ipv6-multipath/diagnostic-tools:trace-results/diagnostic-tools:trace-result/diagnostic-tools:test-name";
        }
        mandatory true;
        description
          "Test name.";
      }
    }
  }
  augment "/diagnostic-tools:diagnostic-tools" {
    description
      "List of IPv6 tests.";
    container ipv6 {
      description
        "Statistics of IPv6 tests.";
      uses ip6-ping-trace-result-type;
    }
  }
  augment "/diagnostic-tools:diagnostic-tools" {
    description
      "List of IPv6 multipath tests.";
    container ipv6-multipath {
      description
        "Statistics of IPv6 multipath tests.";
      uses ip6-multipath-ping-trace-result-type;
    }
  }
}
