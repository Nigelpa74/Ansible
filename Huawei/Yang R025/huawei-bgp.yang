/*
Copyright (C) 2019-2025 Huawei Technologies Co., Ltd. All rights reserved.
*/
module huawei-bgp {
  namespace "urn:huawei:yang:huawei-bgp";
  prefix bgp;
  import huawei-extension {
    prefix ext;
  }
  import ietf-inet-types {
    prefix inet;
  }
  import huawei-network-instance {
    prefix ni;
  }
  import huawei-pub-type {
    prefix pub-type;
  }
  import huawei-routing-policy {
    prefix rtp;
  }
  import huawei-routing {
    prefix rt;
  }
  import huawei-tunnel-management {
    prefix tnlm;
  }
  import huawei-l3vpn {
    prefix l3vpn;
  }
  import huawei-ifm {
    prefix ifm;
  }
  import huawei-socket {
    prefix socket;
  }
  import huawei-xpl {
    prefix xpl;
  }
  import huawei-bfd {
    prefix bfd;
  }
  include huawei-bgp-type;
  include huawei-bgp-common;
  include huawei-bgp-common-multiprotocol;
  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";
  revision 2025-09-10 {
    description
      "Add the route-select-delay-relax. Add a must condition for advertise-srv6-locator. Fix typos. Add leaf node of include-srv6-best-effort. Add leaf node of include-vrf-import-route and include-vrf-export-route. Add must condition of multi-nexthop-convergence.";
    reference "Huawei private.";
  }
  revision 2025-01-09 {
    description
      "Add the exclude-no-advertise node.";
    reference "Huawei private.";
  }
  revision 2024-11-26 {
    description
      "Add choice node context-policy-type to container route-server. Modify the description of the context-policy-type node.";
    reference "Huawei private.";
  }
  revision 2024-08-15 {
    description
      "Add nodes of advertise-match-route-source, add-path-label-ignore node, rpki, advertise-peer-up, lowest-priority, advertise-active-routes-number, track-session-name and received-rt-not-matched-count.";
    reference "Huawei private.";
  }
  revision 2024-03-13 {
    description
      "Add accept-non-standard.";
    reference "Huawei private.";
  }
  revision 2024-02-21 {
    description
      "Delete must condition of add-path-select-num. Modify must condition of determin-med.";
    reference "Huawei private.";
  }
  revision 2024-01-24 {
    description
      "Modify the grouping of load-balancing. Add leaf node of adaptive-routing-eibgp and leaf adaptive-routing-ibgp.";
    reference "Huawei private.";
  }
  revision 2024-01-17 {
    description
      "Add must condition for action. Modify when condition of generate-all. Add dynamic-default.";
    reference "Huawei private.";
  }
  revision 2023-12-11 {
    description
      "Add must condition for generate-all. Modify when condition of memory-resilience.";
    reference "Huawei private.";
  }
  revision 2023-11-21 {
    description
      "Modify the description of single-group-detection-threshold.";
    reference "Huawei private.";
  }
  revision 2023-11-02 {
    description
      "Add aggregate node. Add aggregate-limit ndoe. Add generate-all node.";
    reference "Huawei private.";
  }
  revision 2023-11-01 {
    description
      "Add policy-effective container. Add default-esi container.";
    reference "Huawei private.";
  }
  revision 2023-10-16 {
    description
      "Modify the grouping of slow-peer-type. Add leaf node of slow-peer. Add esi-name.";
    reference "Huawei private.";
  }
  revision 2023-09-22 {
    description
      "Modify peer-establish-mode.";
    reference "Huawei private.";
  }
  revision 2023-06-14 {
    description
      "Remove the default value of send-hold-time.";
    reference "Huawei private.";
  }
  revision 2023-06-12 {
    description
      "Add send-hold container. Add send-hold-time. Add when condition for local-graceful-restart.";
    reference "Huawei private.";
  }
  revision 2023-06-08 {
    description
      "Modify memory-overload-danger-new-route node. Modify label-route-capability-only node.";
    reference "Huawei private.";
  }
  revision 2023-04-23 {
    description
      "Add orf-type, orf-mode. Modify the must condition of orf-type and orf-mode.";
    reference "Huawei private.";
  }
  revision 2023-03-30 {
    description
      "Add vrf-route-distribute-vpnv4, vrf-route-distribute-vpnv6. Add the must condition of apply-label-mode. Modify multi-thread container.";
    reference "Huawei private.";
  }
  revision 2023-03-17 {
    description
      "Modify the when/must condition.";
    reference "Huawei private.";
  }
  revision 2023-03-16 {
    description
      "Modify extended-open-message node.";
    reference "Huawei private.";
  }
  revision 2023-02-15 {
    description
      "Add multi-thread container.";
    reference "Huawei private.";
  }
  revision 2023-02-13 {
    description
      "Add auto-frr-best-effort, include-tunnel, critical-reachable-include-tunnel.";
    reference "Huawei private.";
  }
  revision 2023-02-06 {
    description
      "Add the node of extended message capability.";
    reference "Huawei private.";
  }
  revision 2023-01-11 {
    description
      "Add memory overload container and IPv4 multicast import-rib container.";
    reference "Huawei private.";
  }
  revision 2022-12-08 {
    description
      "Modify node descriptions.";
    reference "Huawei private.";
  }
  revision 2022-11-17 {
    description
      "Add path-attribute-treat container. Add extended-open-message.";
    reference "Huawei private.";
  }
  revision 2022-10-16 {
    description
      "Delete memory-overload-danger-receive-new-route-enable, memory-overload-danger-send-new-route-enable, memory-overload-danger-suppress-peer-disable.";
    reference "Huawei private.";
  }
  revision 2022-10-13 {
    description
      "Add vpn-orf-enable nodes. Add peer-limit nodes. Modify source-vpn nodes.";
    reference "Huawei private.";
  }
  revision 2022-08-31 {
    description
      "Add memory-overload-danger-receive-new-route-enable, memory-overload-danger-send-new-route-enable, memory-overload-danger-suppress-peer-disable.";
    reference "Huawei private.";
  }
  revision 2022-07-15 {
    description
      "Add discard-ext-community-type and origin-validation-as. Add original-attributes and reoriginate-route.";
    reference "Huawei private.";
  }
  revision 2022-06-16 {
    description
      "Add graceful shutdown nodes.";
    reference "Huawei private.";
  }
  revision 2022-06-10 {
    description
      "Add bestroute-address-family-priority. Modify dynamic-peer-prefix. Add the private label address family to support load-balancing. Add specifications and peer statistic. Add container add-path-policy.";
    reference "Huawei private.";
  }
  revision 2022-05-26 {
    description
      "Add multiple instance nodes. Add bgp common multiprotocol submodule. Add maximum-load-balancing-mixed nodes. Add leaf node:IPv4 as-no-prepend, IPv6 as-no-prepend. Modify the state of peer.";
    reference "Huawei private.";
  }
  revision 2021-08-16 {
    description
      "Add bgp common multiprotocol submodule.";
    reference
      "Huawei private.";
  }
  revision 2020-02-25 {
    description
      "The YANG descriptions are modified according to new standards.";
    reference "Huawei private.";
  }
  revision 2019-03-22 {
    description
      "Initial revision.";
    reference
      "Huawei private.";
  }
  ext:task-name  "bgp";
  
  /*
   * grouping-stmt
   */
  grouping network-route-ipv4 {
    description
      "BGP network routes.";
    leaf address {
      type inet:ipv4-address-no-zone;
      description
        "Specify the IP address advertised by BGP. An IPv4 address can be configured in the IPv4 address family. Note: During the configuration of a network route, the IP address is adjusted based on the mask. It is recommended that you click Synchronize All after creating a network route.";
    }
    leaf mask-length {
      type uint8 {
        range "0..32";
      }
      description
        "Specify the mask length of an IP address.";
    }
    choice policy-type {
      description
        "Specify the route-policy or filter for route advertisement.";
      case rtp-ref {
        description
          "Specify the route policy.";
        leaf policy-name {
          type leafref {
            path "/rtp:routing-policy/rtp:policy-definitions/rtp:policy-definition/rtp:name";
          }
          description
            "Specify the route policy.";
        }
      }
      case xpl-ref {
        description
          "Route filter.";
        uses route-filter-type;
      }
    }
  }
  grouping network-route-ipv6 {
    description
      "BGP network routes.";
    leaf address {
      type inet:ipv6-address-no-zone;
      description
        "Specify the IP address advertised by BGP. An IPv6 routes can be configured in the IPv6 address family. Note: During the configuration of a network route, the IP address is adjusted based on the mask. It is recommended that you click Synchronize All after creating a network route.";
    }
    leaf mask-length {
      type uint8 {
        range "0..128";
      }
      description
        "Specify the mask length of an IP address.";
    }
    choice policy-type {
      description
        "Specify the route-policy or filter for route advertisement.";
      case rtp-ref {
        description
          "Specify the route policy.";
        leaf policy-name {
          type leafref {
            path "/rtp:routing-policy/rtp:policy-definitions/rtp:policy-definition/rtp:name";
          }
          description
            "Specify the route policy.";
        }
      }
      case xpl-ref {
        description
          "Route filter.";
        uses route-filter-type;
      }
    }
  }
  grouping advertise-route-to-evpn-type {
    description
      "Advertise-routes-type configuration.";
    list advertise-route-to-evpn {
      key "protocol";
      description
        "Configure the advertise route protocol.";
      leaf protocol {
        type enumeration {
          enum "all" {
            value 0;
            description
              "Advertise all the types of route protocol.";
          }
        }
        description
          "Route protocol.";
      }
      leaf import-multipath {
        type boolean;
        default "false";
        description
          "Enable/disable route import from multiple paths.";
      }
      leaf include-local-cross {
        type boolean;
        default "false";
        description
          "Enable/disable local cross route to advertise l2vpn evpn.";
      }
      leaf advertise-route-mode {
        type enumeration {
          enum "all" {
            value 0;
            description
              "All:";
          }
          enum "best" {
            value 1;
            description
              "Best:";
          }
          enum "valid" {
            value 2;
            description
              "Valid:";
          }
          enum "active" {
            value 3;
            description
              "Active:";
          }
        }
        default "all";
        description
          "VPN advertise route mode to evrf.";
      }
      leaf advertise-active-routes-number {
        when "../advertise-route-mode = 'active'";
        type uint16 {
          range "1..65535";
        }
        description
          "Number of active-routes to advertise.";
      }
      leaf exclude-no-advertise {
        type boolean;
        default "false";
        description
          "Enable/disable not advertise routes in the NoAdv state.";
      }
    }
  }
  grouping vpn-target-type {
    description
      "BGP IPv4/IPv6 VPN target.";
    leaf policy-vpntarget {
      type boolean;
      default "true";
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }
  grouping group-entropy-label-type {
    description
      "Entropy label parameter configuration in a peer group.";
    leaf advertise-entropy-label {
      type boolean;
      default "false";
      description
        "Enable/disable the capability of advertising entropy labels.";
    }
    leaf padding {
      when "../advertise-entropy-label='true'";
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='true'";
      type entropy-label-attribute-type;
      mandatory true;
      description
        "The attribute-type of advertising entropy labels.";
    }
    leaf entropy-label {
      type boolean;
      default "false";
      description
        "Enable/disable the function of delivering the entropy label capability to the forwarding plane.";
    }
  }
  grouping peer-entropy-label-type {
    description
      "Entropy label parameter configuration in a peer.";
    leaf advertise-entropy-label {
      type peer-comm-config-type;
      default "default";
      description
        "Enable the capability of advertising entropy labels.";
    }
    leaf padding {
      when "../advertise-entropy-label='enable'";
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='enable'";
      type entropy-label-attribute-type;
      mandatory true;
      description
        "The attribute-type of advertising entropy labels.";
    }
    leaf entropy-label {
      type peer-comm-config-type;
      default "default";
      description
        "Enable the function of delivering the entropy label capability to the forwarding plane.";
    }
    leaf effect-advertise-entropy-label {
      type boolean;
      default "false";
      config false;
      description
        "Whether the capability of advertising entropy labels is enabled on the BGP peer.";
    }
    leaf effect-padding {
      when "../effect-advertise-entropy-label='true'";
      type string {
      length "1..32";
        pattern '(([0-9A-F])*)';
      }
      config false;
      description
        "Padding format.";
    }
    leaf effect-attribute-type {
      when "../effect-advertise-entropy-label='true'";
      type entropy-label-attribute-type;
      config false;
      description
        "The attribute-type of advertising entropy labels.";
    }
    leaf effect-entropy-label {
      type boolean;
      default "false";
      config false;
      description
        "Whether the function of delivering the entropy label capability to the forwarding plane is enabled on the BGP peer.";
    }
  }
  container bgp {
    description
      "Inter-AS routing protocol that exchanges Network Layer Reachability Information (NLRI) with other BGP systems,
      Universal BGP configurations that contain the basic BGP configurations and the query information.";
    container global {
      description
        "Configure the router for BGP globally.";
      leaf yang-enable {
        type boolean;
        default "false";
        description
          "Enable/disable BGP yang mode. To manage BGP VPN instances in huawei-bgp.yang, enable YANG management for the BGP VPN instances on the device or enable the leaf node globally in the huawei-bgp.yang file.";
      }
      leaf memory-overload-exception-discard-route {
        type boolean;
        default "false";
        description
          "Enable/disable BGP to discard routes received from all peers if the memory usage of a device is abnormal.";
      }
      leaf peer-limit {
        type uint32 {
          range "1..4294967295";
        }
        description
          "Upper limit on the number of peers. The value range is controlled by the PAF.";
      }
      leaf load-balance-adaptive-orchestrator {
        type boolean;
        default "false";
        description
          "Enable/disable load-balance-adaptive-orchestrator.";
      }
    }
    container paf-controls {
      description
        "List of PAF-based limiting disabled for some features.";
      list paf-control {
        key "feature-name";
        description
          "Configure PAF-based limiting disabled for some features.";
        leaf feature-name {
          type paf-control-feature-type;
          description
            "Feature name.";
        }
      }
    }
    container path-attribute-treat {
      description
        "Configure the path attribute processing mode.";
      leaf-list accept-zero-value {
        type zero-value-attribute-id;
        description
          "Assign path attributes of zero-value to be retained.";
      }
      leaf-list accept-zero-length {
        type zero-length-attribute-id;
        description
          "Assign path attributes of zero-length to be retained.";
      }
      leaf-list accept-non-standard {
        type non-standard-attribute-id;
        description
          "Assign path attributes of non-standard value to be retained.";
      }
    }
    container specifications {
      config false;
      description
        "Operational state of BGP specification.";
      container peer-spec {
        description
          "Operational state of peer specification. The maximum value is affected by the PAF file.";
        leaf peer-max-number {
          type uint32;
          description
            "Maximum number of peers, which is determined by PAF file or the function of peer limit.";
        }
        leaf peer-total-number {
          type uint32;
          description
            "Total number of peers, including static peers, dynamic peers, and unnumbered peers.";
        }
      }
      container route-specs {
        description
          "List of route specifications.";
        list route-spec {
          key "af-type";
          description
            "Operational state of route specification. The maximum value is affected by the PAF file.";
          leaf af-type {
            type bgp:af-type;
            description
              "Address family type.";
          }
          leaf route-max-number {
            type uint32;
            description
              "Maximum number of routes, which is determined by the PAF file of the corresponding address family. For example, the IPv4 unicast address family corresponds to SPEC_RES_BGP_IPV4_ROUTE_NUM_ALL_PEER.";
          }
        }
      }
      container resource {
        description
          "Operational state of BGP resource information.";
        leaf peer-session-total-number {
          type uint32;
          description
            "BGP peer session total number.";
        }
        leaf peer-session-used-number {
          type uint32;
          description
            "BGP peer session used number.";
        }
        leaf ibgp-peer-session-used-number {
          type uint32;
          description
            "IBGP peer session used number.";
        }
        leaf ebgp-peer-session-used-number {
          type uint32;
          description
            "EBGP peer session used number.";
        }
      }
    }
    container session-car {
      must "pir-value >= cir-value and pbs-value >= cbs-value";
      description
        "Configure session CAR.";
      leaf enable {
        type boolean;
        default "true";
        description
          "Enable/disable session CAR.";
      }
      leaf cir-value {
        type uint32 {
          range "12..1200";
        }
        units "kbit/s";
        default "24";
        description
          "Specify the session CAR CIR value.";
      }
      leaf cbs-value {
        type uint32 {
          range "15000..1500000";
        }
        units "Byte";
        default "15000";
        description
          "Specify the session CAR CBS value.";
      }
      leaf pir-value {
        type uint32 {
          range "12000..60000";
        }
        units "kbit/s";
        default "48000";
        description
        "Specify the session CAR PIR value.";
      }
      leaf pbs-value {
        type uint32 {
          range "1500000..7500000";
        }
        units "Byte";
        default "6000000";
        description
        "Specify the session CAR PBS value.";
      }
    }
    container micro-car {
      must "pir-value >= cir-value and pbs-value >= cbs-value";
      description
        "Configure micro CAR.";
      leaf enable {
        type boolean;
        default "true";
        description
          "Enable/disable micro CAR.";
      }
      leaf cir-value {
        type uint32 {
          range "12..1200";
        }
        units "kbit/s";
        default "24";
        description
          "Specify the micro CAR CIR value.";
      }
      leaf cbs-value {
        type uint32 {
          range "15000..1500000";
        }
        units "Byte";
        default "15000";
        description
          "Specify the micro CAR CBS value.";
      }
      leaf pir-value {
        type uint32 {
          range "12000..60000";
        }
        units "kbit/s";
        default "48000";
        description
        "Specify the micro CAR PIR value.";
      }
      leaf pbs-value {
        type uint32 {
          range "1500000..7500000";
        }
        units "Byte";
        default "6000000";
        description
        "Specify the micro CAR PBS value.";
      }
    }
    choice memory-overload-danger-new-route-type {
      default auto;
      description
        "Specify memory overload danger configuration.";
      case auto {
        description
          "Specify memory overload to process new routes automatically.";
        container memory-overload-danger-auto-new-route {
          description
            "Configure BGP to process new routes automatically from all peers if the memory usage of a device is in the dangerous state.";
          leaf auto-mode { 
            type enable-type;
            default "enable";
            description
              "Specify memory overload to process new routes automatically.";
          }
          leaf include-vrf-import-route {
            type boolean;
            default "false";
            description
              "Enable/disable process new routes include vrf import routes.";
          }
          leaf include-vrf-export-route {
            type boolean;
            default "false";
            description
              "Enable/disable process new routes include vrf export routes.";
          }
          uses escape-timeout-type;
        }
      }
      case discard {
        description
          "Specify memory overload to discard new routes.";
        container memory-overload-danger-discard-new-route {
          presence "Create memory overload to discard new routes.";
          description
            "Configure BGP to discard new routes from all peers if the memory usage of a device is in the dangerous state.";
          leaf include-vrf-import-route {
            type boolean;
            default "false";
            description
              "Enable/disable process new routes include vrf import routes.";
          }
          leaf include-vrf-export-route {
            type boolean;
            default "false";
            description
              "Enable/disable process new routes include vrf export routes.";
          }
          uses escape-timeout-type;
        }
      }
      case accept {
        description
          "Specify memory overload to accept new routes.";
        container memory-overload-danger-accept-new-route {
          presence "Create memory overload to accept new routes.";
          description
            "Configure BGP to accept new routes from all peers if the memory usage of a device is in the dangerous state.";
        }
      }
    }
    container policy-effective {
      description
        "Configure the attributes in the routing policy to take effect.";
      container actions {
        description
          "List of action.";
        list action {
          must "((object = 'network' or object = 'import') and attribute = 'extcommunity-rt') or (object = 'peer-export' and attribute = 'med-inherit-aigp')";
          key "object attribute";
          description
            "Apply mode of the routing policy.";
          leaf object {
            type object-type;
            description
              "Type of the object to which the routing policy takes effect.";
          }
          leaf attribute {
            type attr-type;
            description
              "Route attribute type.";
          }
        } 
      }
    }
    container base-process {
      description
        "Configure the global BGP information, such as the protocol version, AS number, and system identifier.";
      leaf enable {
        type boolean;
        must "(../enable='true' and ../as) or (../enable='false')";
        default "false";
        description
          "Enable/disable BGP function.";
      }
      leaf as {
        when "../enable='true'";
        type as-number-validate;
        description
          "Local AS number, which can be in either of the two formats:
           The two-byte format is X. X is an integer ranging from 1 to 65535.
           The four-byte format is X.Y and X. When the format is X.Y, X and Y are both integers, with the value of X ranging from 1 to 65535, and the value of Y ranging from 0 to 65535; when the format is X, X is an integer, with the value ranging from 1 to 4294967295.
           An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs. The object cannot be deleted or modified.";
        ext:operation-exclude update {
          description "The node cannot be modified when BGP is enabled.";
        }
      }
      leaf keep-all-routes {
        when "../enable='true'";
        type boolean;
        default "false";
        description
          "Enable/disable saving all the updated information about BGP routes from a peer or peer group after a BGP connection is established, even though these BGP routes fail to match the routing policy on the ingress. Save all the updated information about BGP routes from a peer or peer group after a BGP connection is established, even though these BGP routes fail to match the routing policy on the ingress. By default, only the updated information about BGP routes from a specified peer is saved on condition that the routes match the routing policy on the ingress. If a router supports route refreshing, this option is not required.";
      }
      leaf check-first-as {
        when "../enable='true'";
        type boolean;
        default "true";
        description
          "Enable/disable checking the first AS in the AS_Path of the update messages from EBGP peers.";
      }
      leaf router-id-auto-select {
        when "../enable='true'";
        type boolean;
        default "false";
        description
          "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
          1. If Loopback interfaces configured with IP addresses exist, the largest IP address among the IP addresses of the Loopback interfaces is selected as the router ID. 
          2. If there is no Loopback interface configured with an IP address, the largest IP address among the IP addresses of other interfaces is selected as the router ID, regardless of whether the interface is Up.";
      }
      leaf shutdown {
        when "../enable='true'";
        type boolean;
        default "false";
        description
          "Enable/disable interrupting BGP all neighbour.";
      }
      leaf local-ifnet-mtu {
        when "../enable='true'";
        type uint16 {
          range "46..65535";
        }
        default "1500";
        description
          "BGP LOCALIFNET MTU.";
      }
      leaf private-4byte-as {
        when "../enable='true'";
        type boolean;
        default "true";
        description
          "Enable/disable BGP private 4 byte AS. With BGP private-4-byte-as, BGP private as is from 64512 to 65535 and from 4200000000 to 4294967294.";
      }
      leaf local-cross-no-med {
        when "../enable='true'";
        type boolean;
        default "false";
        description
          "Enable/disable local cross routing non-med.";
      }
      leaf as-path-limit {
        when "../enable='true'";
        type uint16 {
          range "1..2000";
        }
        description
          "Maximum number of AS numbers in the AS_Path attribute.";
      }
      leaf dynamic-session-limit {
        when "../enable='true'";
        ext:dynamic-default;
        type uint32 {
          range "1..4294967295";
        }
        description
          "Upper limit on the number of dynamic peer sessions.";
      }
      leaf peer-up-route-lowest-priority {
        when "../enable='true'";
        type boolean;
        default "false";
        description
          "Enable/disable reducing route priority to lowest.";
      }
      leaf delay-time {
        when "../peer-up-route-lowest-priority='true'";
        type uint32 {
          range "1..864000";
        }
        units "s";
        description
          "Specifies the delay time.";
      }
      leaf route-loop-detect-enable {
        type boolean;
        default "false";
        description
          "Enable/disable BGP route loop-detect control.";
      }
      leaf origin-validation-as {
        when "../enable='true'";
        type as-number-validate;
        description
          "Local origin validation AS number, which can be in either of the two formats:
           The two-byte format is X. X is an integer ranging from 1 to 65535.
           The four-byte format is X.Y and X. When the format is X.Y, X and Y are both integers, with the value of X ranging from 1 to 65535, and the value of Y ranging from 0 to 65535; when the format is X, X is an integer, with the value ranging from 1 to 4294967295.";
      }
      leaf vrf-route-distribute-vpnv4 {
        when "../enable='true'";
        type boolean;
        default "true";
        description
          "Enable/disable VPN instance route distribution to VPNv4.";
      }
      leaf vrf-route-distribute-vpnv6 {
        when "../enable='true'";
        type boolean;
        default "true";
        description
          "Enable/disable VPN instance route distribution to VPNv6.";
      }
      leaf orf-limit {
        when "../enable='true'";
	      type uint32 {
		      range "1..4294967295";
        }
        default "400000";
        description
		      "Upper limit on the number orf.";
      }
      leaf router-id-allow-same {
        when "../enable='true'";
        type boolean;
        default "false";
        description
          "Enable/disable EBGP connections between peers with the same router ID.";
      }
      leaf slow-peer-auto-recover {
        when "../enable='true'";
        type boolean;
        default "true";
        description
          "Enable/disable BGP slow neighbor auto-recovery.";
      }
      container confederation {
        when "../enable='true'";
        description
          "Configure confederation.";
        leaf id {
          type as-number-validate;
          description
            "Configure the confederation ID.";
        }
        leaf nonstanded {
          type boolean;
          default "false";
          description
            "Enable/disable nonstanded. Configure the device to be compatible with devices in a nonstandard confederation.";
        }
        leaf-list as {
          when "../id";
          type as-number-validate;
          max-elements 32;
          description
            "Configure the confederation AS number. The confederation AS number can be in either of the two formats:
            The two-byte format is X. X is an integer ranging from 1 to 65535.
            The four-byte format is X.Y and X. When the format is X.Y, X and Y are both integers, with the value of X ranging from 1 to 65535, and the value of Y ranging from 0 to 65535; when the format is X, X is an integer, with the value of X ranging from 1 to 4294967295. The confederation sub-ASs cannot be configured same as the local AS number.";
        }
      }
      container graceful-restart {
        when "../enable='true'";
        description
          "Configure the graceful-restart.";
        uses graceful-restart-type;
      }
      container graceful-shutdown {
        when "../enable='true'";
        description
          "Configure the graceful-shutdown.";
        leaf all-peer {
          type boolean;
          default "false";
          description
            "Enable/disable the graceful-shutdown function for all peers.";
        }
        leaf manual-activate {
          type boolean;
          default "false";
          description
            "Enable/disable the graceful-shutdown activation for all peers.";
        }
      }
      uses remote-prefix-sid-states-type;
      container reference-period {
        when "../enable='true'";
        must "hold-interval>suppress-interval";
        must "clear-interval>hold-interval";
        description
          "Configure the reference period.";
        uses reference-period-type;
      }
      container send-hold {
        when "../enable='true'";
        description
          "Configure BGP global send-hold timer parameters.";
        leaf time {
          type uint32 {
            range "0 | 360..172800";
          }
          units "s";
          default "86400";
          description
          "Specifies the interval for holding a session when the local end fails to send messages.";
        }
      }
      container timer {
        when "../enable='true'";
        description
          "Configure BGP global timer parameters.";
        uses global-timer-para-type;
      }
      uses graceful-restart-status-type;
      uses error-discard-info-type;
      uses vpn-brief-infos-type;
      container default-parameter {
        config false;
        description
          "Statistics of default parameter of BGP.";
        leaf version {
          type uint8;
          description
            "BGP protocol version.";
        }
        leaf connect-retry-time {
          type uint16;
          units "s";
          description
            "Value of connect retry timer.";
        }
        leaf hold-time {
          type uint32;
          units "s";
          description
            "The holdtime interval.";
        }
        leaf keepalive-time {
          type uint32;
          units "s";
          description
            "The keepalive interval.";
        }
        leaf external-route-preference {
          type uint8;
          description
            "Specifies the protocol preference for EBGP external routes.";
        }
        leaf internal-route-preference {
          type uint8;
          description
            "Specifies the protocol preference for IBGP internal routes.";
        }
        leaf local-route-preference {
          type uint8;
          description
            "Specifies the protocol preference for local BGP routes.";
        }
        leaf ebgp-route-update-interval {
          type uint16;
          units "s";
          description
            "Specifies the minimum interval for sending EBGP update packets.";
        }
        leaf ibgp-route-update-interval {
          type uint16;
          units "s";
          description
            "Specifies the minimum interval for sending IBGP update packets.";
        }
        leaf local-preference {
          type uint32;
          description
            "The default local preference for BGP.";
        }
        leaf med {
          type uint32;
          description
            "The default med for BGP.";
        }
        leaf ipv4-unicast {
          type boolean;
          description
            "The default IPv4 unicast address family for BGP.";
        }
        leaf ebgp-interface-sensitive {
          type boolean;
          description
            "The capability of resetting the EBGP session that is directly connected on the interface.";
        }
        leaf reflect-between-client {
          type boolean;
          description
            "Enable route reflection between clients.";
        }
        leaf check-first-as {
          type boolean;
          description
            "Check first AS in as_path of update messages from ebgp peer.";
        }
        leaf synchronization {
          type boolean;
          description
            "Synchronization.";
        }
        leaf support-address-family {
          type string {
            length "1..600";
          }
          description
            "Support address family.";
        }
      }
      container srgbs {
        description
          "List of segment routing global block.";
        list srgb {
          must "lower-bound < upper-bound";
          key "lower-bound";
          max-elements  "1";
          description
            "Configure segment routing global block.";
          leaf lower-bound {
            type uint32 {
              range "16..1048575";
            }
            description
              "SRGB begin value. The range of specific values is dynamic and is also affected by paf.";
          }
          leaf upper-bound {
            type uint32 {
              range "16..1048575";
            }
            mandatory true;
            description
              "SRGB end value. The range of specific values is dynamic and is also affected by paf. The ending value of SRGB must be greater than the configured value.";
          }
        }
      }
      container bestroute-af-priority-all-vpn {
        when "../enable='true'";
        description
          "Configure route selection based on the address family priority.";
        leaf ipv4-af-type {
          type ipv4-address-family-priority-type;
          description
            "VPN address family type for IPv4 Route.";
        }
        leaf ipv6-af-type {
          type ipv6-address-family-priority-type;
          description
            "VPN address family type for IPv6 Route.";
        }
      }
      container bestroute-nexthop-priority-all-vpn {
        when "../enable='true'";
        description
          "Configure route selection based on the next-hop priority as the high level condition.";
        leaf nexthop-type {
          type nexthop-priority-address-type;
          description
            "Routes with next-hop IPv4 addresses and routes with next-hop IPv6 addresses coexist. If the next-hop address type is set to IPv4, routes with next-hop IPv4 addresses have a higher priority. If the next-hop address type is set to IPv6, routes with next-hop IPv6 addresses have a higher priority.";
        }
      }
    }
    container instance-processs {
      description
        "List of the global BGP information for the list of all BGP instances, such as the protocol version, AS number, and system identifier.";
      list instance-process {
        key "name";
        max-elements 1;
        description
          "Configure the global BGP information for the BGP instances, such as the protocol version, AS number, and system identifier.";
        leaf name {
          type string {
            length "1..31";
          }
          must "../name != 'default'";
          description
            "Name of BGP Site.";
        }
        leaf as-number {
          type as-number-validate;
          mandatory true;
          description
            "Local AS number, which can be in either of the two formats:
            The two-byte format is X. X is an integer ranging from 1 to 65535.
            The four-byte format is X.Y and X. When the format is X.Y, X and Y are both integers, with the value of X ranging from 1 to 65535, and the value of Y ranging from 0 to 65535; when the format is X, X is an integer, with the value ranging from 1 to 4294967295.
            An AS consists of instance routers managed based on the same techniques. Interior Gateway Protocol (IGP) and universal routing metric packets are used inside an AS, and Exterior Gateway Protocol (EGP) is used outside to send packets to other ASs. With the development of this definition, one AS usually uses instance IGPs and metrics. Even though instance IGPs and metrics are used, the routing plan and destination reachability of an AS are consistent with those of another AS. The local AS number cannot be configured same as the confederation sub-ASs.";
          ext:operation-exclude update {
            description "The node cannot be modified when BGP is enabled.";
          }
        }
        leaf check-first-as {
          type boolean;
          default "true";
          description
            "Enable/disable checking the first AS in the AS_Path of the update messages from EBGP peers.";
        }
        leaf shutdown {
          type boolean;
          default "false";
          description
            "Enable/disable interrupting BGP all neighbour.";
        }
        leaf private-4byte-as {
          type boolean;
          default "true";
          description
            "Enable/disable BGP private 4 byte AS. With BGP private-4-byte-as, BGP private as is from 64512 to 65535 and from 4200000000 to 4294967294.";
        }
        leaf peer-up-route-lowest-priority {
          type boolean;
          default "false";
          description
            "Enable/disable reducing route priority to lowest.";
        }
        leaf delay-time {
          when "../peer-up-route-lowest-priority='true'";
          type uint32 {
            range "1..864000";
          }
          units "s";
          description
            "Specifies the delay time.";
        }
		leaf memory-limit {
          type boolean;
          default "false";
          description
            "Enable/disable using the prefix memory-limit command, you can configure the capability of BGP about memory limit when the system memory usage exceeded.";
        }
        leaf dynamic-session-limit {
          ext:dynamic-default;
          type uint32 {
            range "1..4294967295";
          }
          description
            "Upper limit on the number of dynamic peer sessions.";
        }
        leaf vrf-route-distribute-vpnv4 {
          type boolean;
          default "true";
          description
            "Enable/disable VPN instance route distribution to VPNv4.";
        }
        leaf vrf-route-distribute-vpnv6 {
          type boolean;
          default "true";
          description
            "Enable/disable VPN instance route distribution to VPNv6.";
        }
        leaf orf-limit {
	        type uint32 {
		        range "1..4294967295";
          }
          default "400000";
          description
		        "Upper limit on the number orf.";
        }
        leaf router-id-allow-same {
          type boolean;
          default "false";
          description
            "Enable/disable EBGP connections between peers with the same router ID.";
        }
        leaf slow-peer-auto-recover {
          type boolean;
          default "true";
          description
            "Enable/disable BGP slow neighbor auto-recovery.";
        }
        container graceful-restart {
          description
            "Configure the graceful-restart.";
          uses graceful-restart-type;
        }
        container reference-period {
          must "hold-interval>suppress-interval";
          must "clear-interval>hold-interval";
          description
            "Configure the reference period.";
          uses reference-period-type;
        }
        container send-hold {
          description
            "Configure BGP global send-hold timer parameters.";
          leaf time {
            type uint32 {
              range "0 | 360..172800";
            }
            units "s";
            default "86400";
            description
            "Specifies the interval for holding a session when the local end fails to send messages.";
          }
        }
        container timer {
          description
            "Configure BGP global timer parameters.";
          uses global-timer-para-type;
        }
      }
    }
    container route-learning-acceleration {
      description
        "Configure BGP route learning acceleration.";
      leaf enable {
        type boolean;
        default "false";
        description
          "Enable/disable the function of BGP route learning acceleration.";
      }
      leaf number {
        type uint8 {
          range "2..4";
        }
        description
          "Configure the number of BGP route learning thread.";
      }
    }
    container route-process-acceleration {
      description
        "Configure BGP route learning and advertising process acceleration.";
      leaf enable {
        type empty;
        must "../../route-learning-acceleration/enable = 'false'";
        description
          "Enable/disable the function of BGP route learning and advertising process acceleration.";
      }
    }
    container memory-overload {
      description
        "Configure escape parameters when memory overload danger.";
      leaf connect-escape-timeout {
        type uint8 {
          range "0..255";
        }
        units "h";
        default "72";
        description
          "Disable BGP neighbor establish when memory is overladed, and specify the escape timeout value.";
      }
    }
  }
  /*
   * augment-stmt
   */
  augment "/ni:network-instance/ni:instances/ni:instance" {
    description
      "BGP network instance configuration.";
    container bgp {
      description
        "Configure BGP network instance. All nodes of private VPN Instance in this container can be used only when the value of the global BGP enabling node (/bgp:bgp/bgp:global/bgp:yang-enable) is set to true.";
      container base-process {
        when "/bgp:bgp/bgp:base-process/bgp:enable='true'";
        presence "Create vrf session.";
        description
          "Enable/disable BGP instances.";
        ext:generated-by system {
          when "../../ni:name = '_public_'";
          description "The BGP public instance is generated automatically when BGP is enabled.";
        }
        leaf router-id-auto-select {
          when "../../../ni:name!='_public_'";
          type boolean;
          default "false";
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

            1. If Loopback interfaces configured with IP addresses exist, the largest IP address among the IP addresses of the Loopback interfaces is selected as the router ID.

            2. If there is no Loopback interface configured with an IP address, the largest IP address among the IP addresses of other interfaces is selected as the router ID, regardless of whether the interface is Up.";
        }
        leaf router-id {
          when "not(../router-id-auto-select) or ../router-id-auto-select = 'false'";
          type inet:ipv4-address-no-zone;
          description
            "ID of a router that is in IPv4 address format. Certain dynamic routing protocols require a router ID. If no router ID is specified for a router when these protocols are enabled, the router ID in the RM module is used by default. The default router ID in the RM module is 0.0.0.0 when the router is not configured with any interface. 
             The rules for selecting a router ID are as follows:
             1. If a router ID is set through this configuration, the set router ID is used. If the router ID is not set, a router ID is selected according to the following rules:
             (1) If loopback interfaces configured with IP addresses exist, the largest IP address among the IP addresses of the loopback interfaces is selected as the router ID.
             (2) If no loopback interface configured with an IP address exists, the largest IP address among the IP addresses of other interfaces is selected as the router ID, regardless of whether the interface is Up.
             The router ID is reselected only when the interface address that is selected as the router ID is deleted or changed. The router ID is not reselected in any of the following cases:
             a. The interface is Down.
             b. A loopback interface is configured when the IP address of a non-loopback interface is selected as the router ID.
             c. A larger IP address of an interface is configured.
             2. Each VPN instance selects the router ID from the addresses of the interfaces of the VPN instance according to the preceding rules.
             3. When both the AMB and SMB exist on the router, the system backs up the router ID set through the related command and the router ID that is selected from IP addresses of the interfaces. After the active/standby switchover is performed, the system checks the validity of the router ID selected from the interface addresses. If the router ID is invalid, the system reselects a router ID.";
        }
        leaf effect-router-id {
          type inet:ipv4-address-no-zone;
          default "0.0.0.0";
          config false;
          description
            "Router ID that takes effect.";
        }
        container afs {
          description
            "List of BGP address family instances.";
          list af {
            key "type";
            description
              "Configure BGP address family instance. In public network instances, all types of address families can be configured. In IPv4 VPN instances, the IPv4 unicast, IPv4 flow, and IPv4 labeled unicast address families can be configured. In IPv6 VPN instances, the IPv6 unicast and IPv6 flow address families can be configured. The IPv4 address family in the BGP _public_ VPN instance cannot be deleted.";
            ext:generated-by system {
              when "../../../../ni:name = '_public_'";
              ext:filter "type = 'ipv4uni'";
              description "The IPv4 unicast of the BGP public instance is generated automatically when BGP is enabled.";
            }
            leaf type {
              type bgp:af-type;
              description
                "Address family type of a BGP instance.";
            }
            container ipv4-unicast {
              when "../type = 'ipv4uni'";
              must "../../../../../l3vpn:afs/l3vpn:af[l3vpn:type='ipv4-unicast']";
              description
                "Configure IPv4 unicast options.";
              container common {
                description
                  "Configure IPv4 unicast common options.";
                leaf auto-frr {
                  type boolean;
                  default "false";
                  description
                    "Enable/disable BGP Auto FRR.";
                }
                leaf auto-frr-best-effort {
                  when "../auto-frr='true'";
                  type empty;
                  description
                    "SRv6 BE of the primary route is preferred as the backup path.";
                }
                leaf frr-non-host-label-route {
                  when "../auto-frr='true' and ../../../../../../../ni:name='_public_'";
                  type empty;
                  description
                    "FRR can be performed on labeled routes with non-32-bit masks.";
                }
                leaf tunnel-selector-name {
                  when "../../../../../../../ni:name='_public_'";
                  type leafref {
                    path "/rtp:routing-policy/rtp:tunnel-selectors/rtp:tunnel-selector/rtp:name";
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  when "../tunnel-selector-name";
                  type boolean;
                  default "false";
                  description
                    "Enable/disable tunnel selector for labeled, imported, and network segment routes.";
                }
                leaf maximum-load-balancing-ibgp {
                  type uint16 {
                    range "1..65535";
                  }
                  must "not (../maximum-load-balancing>1 or ../maximum-load-balancing-eibgp or ../load-balancing-eibgp-enable='true') or ../maximum-load-balancing-ibgp=1";
                  default "1";
                  description
                    "Specify the maximum number of equal-cost IBGP routes. The value range and default value are controlled by the PAF.";
                }
                leaf maximum-load-balancing-ebgp {
                  type uint16 {
                    range "1..65535";
                  }
                  must "not (../maximum-load-balancing>1 or ../maximum-load-balancing-eibgp or ../load-balancing-eibgp-enable='true') or ../maximum-load-balancing-ebgp=1";
                  default "1";
                  description
                    "Specify the maximum number of equal-cost EBGP routes. The value range and default value are controlled by the PAF.";
                }
                leaf nexthop-select-depend-type {
                  when "../../../../../../../ni:name='_public_'";
                  type select-depend-type;
                  default "depend-ip";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  type boolean;
                  default "false";
                  description
                    "Enable/disable route with AIGP attribute for route selection.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf best-route-bit-error-detection {
                  when "../../../../../../../ni:name!='_public_'";
                  type boolean;
                  default "false";
                  description
                    "Enable/disable the function to reroute traffic when a bit error event occurs.";
                }
                leaf supernet-unicast-advertise {
                  type boolean;
                  default "false";
                  description
                    "Enable/disable the function to advertise supernet unicast routes.";
                }
                leaf supernet-label-advertise {
                  type boolean;
                  default "true";
                  description
                    "Enable/disable the function to advertise supernet labeled routes.";
                }
                leaf lsp-mtu {
                  type uint16 {
                    range "46..65535";
                  }
                  default "1500";
                  description
                    "BGP LSP MTU.";
                }
                leaf label-free-delay {
                  type uint8 {
                    range "0..180";
                  }
                  units "s";
                  default "0";
                  description
                    "Label Free Delay.";
                }
                leaf bestroute-med-confederation {
                  when "../../../../../../../ni:name='_public_'";
                  type boolean;
                  default "false";
                  description
                    "Enable/disable BGP to compare MED value only within the federation.";
                }
                leaf bestroute-as-path-ignore {
                  type boolean;
                  must "../bestroute-as-path-ignore = 'false' or ../load-balanc-as-path-ignore ='false' or not(../load-balanc-as-path-ignore)";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'";
                  type boolean;
                  default "false";
                  description
                    "Enable/disable best external route selection.";
                }
                leaf attribute-set-enable {
                  when "../../../../../../../ni:name!='_public_'";
                  type boolean;
                  default "false";
                  description
                    "Enable/disable the capability of processing attribute set.";
                }
                leaf attribute-set-mode {
                  when "../attribute-set-enable='true'";
                  type bgp:attribute-set-type;
                  default "both";
                  description
                    "The processing mode of attribute set.";
                }
                leaf add-path-select-num {
                  type uint8 {
                    range "2..64";
                  }
                  description
                    "Number of Add-Path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf maximum-load-balancing {
                  type uint16 {
                    range "1..65535";
                  }
                  must "not (../maximum-load-balancing-ibgp>1 or ../maximum-load-balancing-ebgp>1 or ../maximum-load-balancing-eibgp) or ../maximum-load-balancing=1";
                  default "1";
                  description
                    "Specify the maximum number of equal-cost routes in the BGP routing table. The value can be 1 or an integer greater than 1. The value depends on the associated license. Equal-cost BGP routes can be generated for load balancing only when the BGP routes meet the first nine rules of the route-selection policy and have the same AS-Path attribute. The value range and default value are controlled by the PAF.";
                }
                leaf import-rib-nexthop-invariable {
                  when "../../../../../../../ni:name!='_public_'";
                  type boolean;
                  default "false";
                  description
                    "Enable/disable the function to advertise the route without modifying the next-hop.";
                }
                leaf route-relay-tunnel {
                  type boolean;
                    must "not(../route-relay-tunnel='true' and /rt:routing/rt:routing-manage/rt:relay-tunnel/rt:enable='true')";
                  default "false";
                  description
                    "Enable/disable unicast route recursive-lookup tunnel.";
                }
                leaf route-relay-tunnel-selector {
                  when "../route-relay-tunnel='true'";
                  type leafref {
                    path "/rtp:routing-policy/rtp:tunnel-selectors/rtp:tunnel-selector/rtp:name";
                  }
                  description
                    "Unicast route tunnel selector name.";
                }
                leaf route-relay-tunnel-v6-selector { 
                  when "../../../../../../../ni:name='_public_'"; 
                  type leafref {
                    path "/rtp:routing-policy/rtp:tunnel-selectors/rtp:tunnel-selector/rtp:name";
                  }
                  description
                    "Enable/disable unicast route recursive-lookup IPv6 tunnel by tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf bestroute-rd-large-first {
                  when "../../../../../../../ni:name!='_public_'";
                  type boolean;
                  default "false";
                  description
                    "Enable/disable a BGP device to select the route with the largest route distinguisher (RD) during route selection.";
                }
                leaf ebgp-ecmp-nexthop-changed {
                  when "../maximum-load-balancing-ebgp and ../maximum-load-balancing-ebgp>1";
                  type boolean;
                  default "false";
                  description
                    "Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when "../maximum-load-balancing-ibgp and ../maximum-load-balancing-ibgp>1";
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when "../maximum-load-balancing and ../maximum-load-balancing>1";
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'";
                  type uint16 {
                    range "1..65535";
                  }
                  must "../maximum-load-balancing-ibgp=1 and ../maximum-load-balancing-ebgp=1 and ../maximum-load-balancing=1 and ../load-balancing-eibgp-enable='false'";
                  description
                    "Specify the maximum number of equal-cost EBGP routes and IBGP routes. After the attribute is set, load balancing is performed among equal-cost BGP VPN routes, regardless of the route type, EBGP or IBGP. The value range and default value are controlled by the PAF.";
                }
                leaf eibgp-ecmp-nexthop-changed {
                  when "../maximum-load-balancing-eibgp";
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'";
                  type boolean;
                  must "not (../maximum-load-balancing-ibgp>1 or ../maximum-load-balancing-ebgp>1 or ../maximum-load-balancing-eibgp) or ../load-balancing-eibgp-enable='false'";
                  default "false";
                  description
                    "Enable/disable EIBGP route load balancing.";
                }
                leaf maximum-load-balancing-mixed {
                  when "../../../../../../../ni:name!='_public_'";
                  type uint16 {
                    range "1..65535";
                  }
                  must "not (../maximum-load-balancing>1 or ../maximum-load-balancing-eibgp) and ../maximum-load-balancing-ebgp=1 and ../maximum-load-balancing-ibgp=1 and ../load-balancing-eibgp-enable='false'";
                  description
                    "Specify the maximum number of equal-cost MIXED routes. The value range is controlled by the PAF.";
                }
                choice bestroute-nexthop-priority {
                  description
                    "Configure route selection based on the next-hop priority.";
                  case enable {
                    description
                      "Enable route selection based on the next-hop priority.";
                      leaf nexthop-priority {
                        type nexthop-priority-address-type;
                        description
                          "Routes with next-hop IPv4 addresses and routes with next-hop IPv6 addresses coexist. If the next-hop address type is set to IPv4, routes with next-hop IPv4 addresses have a higher priority. If the next-hop address type is set to IPv6, routes with next-hop IPv6 addresses have a higher priority.";
                      }
                      leaf nexthop-priority-high-level {
                        when "../nexthop-priority";
                        type empty;
                        description
                          "Route selection based on the next-hop priority as the high-level condition.";
                      }
                  }
                  case disable {
                    description
                      "Disable route selection based on the next-hop priority.";
                      leaf nexthop-priority-disable {
                        when "../../../../../../../ni:name!='_public_'";
                        type empty;
                        description
                          "Disable route selection based on the next-hop priority.";
                      }
                  }
                }
                uses group-origin-as-validation-type;
                leaf advertise-route-mode {
                  when "../../../../../../../ni:name!='_public_'";
                  type bgp-advertise-route-mode;
                  default "all";
                  description
                    "VPN advertise route mode.";
                }
                leaf reoriginate-route {
                  when "../../../../../../../ni:name!='_public_'";
                  type boolean;
                  default "false";
                  description
                    "Enable/disable route reorigination.";
                }
                leaf original-attributes {
                  when "../reoriginate-route='true'";
                  type empty;
                  description
                    "Regenerate route with original attributes.";
                }
                leaf rpd-policy-change-delay {
                  when "../../../../../../../ni:name='_public_'";
                  type uint16 {
                    range "0..180";
                  }
                  default "30";
                  description
                    "Specify the delay time of RPD policy's change.";
                }
                uses common-configure;
                leaf load-balancing-ucmp {
                  type boolean;
                  default "false";
                  description
                  "Enable/disable the function of BGP UCMP.";
                }
                leaf load-balancing-local-learn-cross {
                  when "../../../../../../../ni:name!='_public_'";
                  type boolean;
                  must ". = 'false' or (. = 'true' and ../../../../../../../l3vpn:afs/l3vpn:af[l3vpn:type='ipv4-unicast']/l3vpn:lsp-operation = 'pop-go')";
                  default "false";
                  description
                  "Enable/disable local route for peer and cross route load balancing.";
                }
                leaf attribute-set-as-path-check {
                  when "../../../../../../../ni:name!='_public_'";
                  type boolean;
                  default "false";
                  description
                    "Enable/disable the capability of checking as-path in attribute set.";
                }
                leaf route-select-rule-relax {
                  when "../../../../../../../ni:name='_public_'";
                  type boolean;
                  default "false";
                  description
                    "Enable/disable use loose rules to select routes based on priorities and determine the routes for load balancing.";
                }
                leaf multi-nexthop-convergence {
                  when "../../../../../../../ni:name='_public_'";
                  type boolean;
                  must "../multi-nexthop-convergence ='false' or ../load-balancing-ucmp ='false'";
                  default "false";
                  description
                    "Enable/disable the function to speed up the delivery of route ecmp/frr entries to the forwarding plane.";
                }
                leaf attribute-set-reserve-srv6 {
                  when "../../../../../../../ni:name!='_public_' and ((../attribute-set-mode='receive') or (../attribute-set-mode='both'))";
                  type boolean;
                  default "false";
                  description
                	"Enable/disable the capability of reserving origin srv6 attribute when parsing attribute set.";
                }
              }
              uses bgp-route-preference-options;
              container nexthop-recursive-lookup {
               description
                "Configure next hop iteration.";
                container common {
                description
                  "Configure next hop iteration common options.";
                  uses nexthop-recursive-lookup-restrain;                  
                  uses nexthop-recursive-lookup-default-route;
                  uses nexthop-recursive-lookup-include-srv6-best-effort;
                }
                container delay {
                  description
                    "Configure time of next hop change responding delay.";
                  uses nexthop-recursive-lookup-delay-grouping;
                  leaf include-tunnel {
                    when "../../../../../../../../ni:name='_public_' and ../time";
                    type empty;
                    description
                      "Delay the response to the next hop change when routes recurse to a tunnel.";
                  }
                  leaf critical-reachable-include-tunnel {
                    when "../../../../../../../../ni:name='_public_' and ../critical-event-reachable-time";
                    type empty;
                    description
                      "Delay the response to the change in which the unreachable next hop becomes reachable when routes recurse to a tunnel.";
                  }
                }
              }
              container import-routes {
                description
                  "List of imported routes.";
                list import-route {
                  key "protocol process-id";
                  description
                    "Configure route import. Routes of other protocol types can be imported by BGP. By default, BGP does not import routes of other protocol types.";
                  leaf protocol {
                    type bgp:ipv4-import-route-protocol-type;
                    description
                      "Routing protocol from which routes can be imported.";
                  }
                  leaf process-id {
                    type uint32 {
                      range "0..4294967295";
                    }
                    description
                      "Process ID of an imported routing protocol.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/rtp:routing-policy/rtp:policy-definitions/rtp:policy-definition/rtp:name";
                        }
                        description
                          "When routes are imported from other routing protocols, the route-policy filter can be used to filter the routes and change route attributes.";
                      }
                    }
                    case xpl-ref {
                      description
                        "Route filter.";
                      uses route-filter-type;
                    }
                  }
                  leaf non-relay-tunnel {
                    when "../../../../../../../../ni:name='_public_'";
                    type boolean;
                    default "false";
                    description
                      "Enable/disable imported route relay a tunnel.";
                  }
                  leaf-list exclude-direct-type {
                    when "../protocol='direct'";
                    type bgp:direct-route-type;
                    description
                      "Configure type of route to be excluded when direct routes are imported.";
                  }
                }
              }
              container aggregate-routes {
                description
                  "List of summarized routes.";
                list aggregate-route {
                  key "address mask-length";
                  description
                    "Configure a summarized route in the BGP routing table. The local outbound interface of the summarized route is Null0. When another router receives the route, the route adds an outbound interface to the route. If the Origin attributes of the specific routes for the route summarization are different, the Origin attribute of the summarized route is that with the highest priority. Origin attributes are arranged in the priority order of complete > egp > igp. A summarized route carries the community attribute of each specific route.";
                  uses unicast-aggregate-routes-type {
                    refine address {
                      must "not(contains(../address,':'))";
                    }
                    refine mask-length {
                      must "../mask-length<=32";
                    }
                  }
                }
              }
              uses ipv4-aggregate-default-route;
              container network-routes {
                description
                  "List of network routes.";
                list network-route {
                  key "address mask-length";
                  description
                    "Configure a network route in the BGP routing table.";
                  uses network-route-ipv4;
                  leaf non-relay-tunnel {
                    when "../../../../../../../../ni:name='_public_'";
                    type boolean;
                    default "false";
                    description
                      "Enable/disable imported route relay a tunnel.";
                  }
                  leaf label-index {
                    when "../../../../../../../../ni:name='_public_'";
                    type uint32 {
                      range "0..4294967294";
                    }
                    description
                    "Management label value assigned for imported routes.";
                  }
                }
              }
              container advertise-route-to-evpns {
                when "../../../../../../ni:name!='_public_'";
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "not(../../../../../../../../ni:name = current() and ../source-address-family = 'ipv4uni')";
                    description
                      "Source VPN name.";
                  }
                  leaf source-address-family {
                    type bgp:import-rib-ipv4-safi-type;
                    must "(current() = 'ipv4labeluni' and /ni:network-instance/ni:instances/ni:instance[ni:name=current()/../bgp:source-vpn]/bgp:bgp/bgp:base-process/bgp:afs/bgp:af[bgp:type='ipv4labeluni']/bgp:ipv4-labeluni) or (current() = 'ipv4uni' and /ni:network-instance/ni:instances/ni:instance[ni:name=current()/../bgp:source-vpn]/l3vpn:afs/l3vpn:af[l3vpn:type='ipv4-unicast'])";
                    description
                      "Source address family type.";
                  }
                  leaf valid-route {
                    type boolean;
                    default "false";
                    description
                      "Enable/disable imported valid route.";
                  }
                  leaf include-label-route {
                    when "../source-address-family='ipv4uni'";
                    type boolean;
                    default "false";
                    description
                      "Enable/disable imported include label route.";
                  }
                  uses choice-policy-set;
                }
              }
              uses ipv4-import-filter-protocol-type;
              uses ipv4-export-filter-policys;
              container lsp-options {
                description
                  "Configure parameters for lsp.";
                uses safi-lsp-options;
                leaf maximum-load-balancing-transit {
                  type uint16 {
                    range "1..65535";
                  }
                  default "1";
                  description
                    "Maximum number of transit LSPs for load balancing.";
                }
                leaf unicast-rt-label-advertise {
                  when "../../../../../../../ni:name='_public_'";
                  type boolean;
                  default false;
                  description
                    "Enable/disable a device to convert received IPv4 public network unicast routes to labeled routes by allocating one BGP label to each route and advertise the labeled routes to peers with the labeled route exchange capability.";
                }
                leaf unicast-rt-label-advertise-popgo {
                  when "../unicast-rt-label-advertise = 'true'";
                  type boolean;
                  default false;
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  when "../../../../../../../ni:name='_public_'";
                  type lsp-operation-type;
                  default "pop";
                  description
                    "Label operation type.";
                }
                uses ingress-choice-policy-set;
                leaf wtr-timer {
                  when "../../../../../../../ni:name='_public_'";
                  type uint8 {
                    range "1..60";
                  }
                  units "s";
                  description
                    "Specify the WTR (Wait To Restore) value of LSP in seconds.";
                }
              }
              container segment-routing-ipv6 {
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
                leaf srv6-color-only-enable {
                  type empty;
                  description
                    "Enable SRv6-TE Policy color-only iteration.";
                }
                leaf srv6-track-bfd-for-locator-enable {
                  when "../../../../../../../ni:name!='_public_'";
                  type empty;
                  description
                    "Enable SRv6-TE Policy track bfd-for-locator.";
                }
                leaf srv6-anycast-sid-enable {
                  when "../../../../../../../ni:name!='_public_'";
                  type empty;
                  description
                    "Enable Anycast SID iteration.";
                }
              }
              container hierarchy-convergence {
                when "../../../../../../ni:name='_public_'";
                description
                  "Configure unicast route hierarchy convergence.";
                uses ipv4-hierarchy-convergence;
              }
              uses vrf-af-dampening-routes;
              uses bgp:slow-peer-type;
              uses routing-table-rib-only-type {
                refine routing-table-rib-only/enable {
                  must "not (../../common/active-route-advertise = 'true' and ../enable = 'true')";
                }
              }
              uses qos-local-id-type;
              container instance-import-ribs {
                description
                  "List of imported RIBs from multi BGP instances configuration.";
                list instance-import-rib {
                  key "source-instance source-vpn source-address-family";
                  description
                    "Configure imported RIBs.";
                  leaf source-instance {
                    type leafref {
                      path "/bgp:bgp/bgp:instance-processs/bgp:instance-process/bgp:name";
                    }
                    description
                      "Configure source BGP instance.";
                  }
                  leaf source-vpn {
                    type leafref {
                      path "/ni:network-instance/ni:instances/ni:instance/ni:name";
                    }
                    must "../../../../../../../../ni:name != current() and ../../../../../../../../ni:name != '_public_'";
                    must "/ni:network-instance/ni:instances/ni:instance[ni:name = current()]/l3vpn:afs/l3vpn:af[l3vpn:type='ipv4-unicast']";
                    description
                      "Source VPN name.";
                  }
                  leaf source-address-family {
                    type bgp:vrf-import-rib-ipv4-safi-type;
                    description
                      "Source address family type.";
                  }
                  leaf valid-route {
                    type boolean;
                    default "false";
                    description
                      "Enable/disable imported valid route.";
                  }
                  leaf include-label-route {
                    when "../source-address-family='ipv4uni'";
                    type boolean;
                    default "false";
                    description
                      "Enable/disable imported include label route.";
                  }
                  uses choice-policy-set;
                }
              }
              uses region-validation-grp;
              uses bestroute-nh-relay-pri-grp;
              container bestroute-address-family-priority {
                when "../../../../../../ni:name != '_public_'";
                must "not(address-family-priority and address-family-priority-disable)";
                description
                  "Configure route selection based on the address family priority.";
                leaf address-family-priority {
                  type ipv4-address-family-priority-type;
                  description
                    "VPN address family type for IPv4 Route.";
                }
                leaf address-family-priority-disable {
                  type empty;
                  description
                    "Disable route selection based on the address-family-priority.";
                }
              }
              container load-balancing {
                description
                  "Configure load-balancing parameters.";
                leaf med-ignore {
                  type empty;
                  description
                    "After this function is enabled, routes with different MEDs can work in load balancing mode.";
                }
                leaf adaptive-routing {
                  type empty;
                  must "not(../../common/load-balancing-ucmp) or ../../common/load-balancing-ucmp = 'false'";
                  description
                    "After this function is enabled, each path of the ECMP route carries its own priority information for the Adaptive Routing to use.";
                }
                leaf adaptive-routing-eibgp {
                  when "../../../../../../../ni:name!='_public_'";
                  type empty;
                  must "not(../adaptive-routing-ibgp)";
                  description
                    "Enable/disable both the routes of eBGP and iBGP peers support load balancing adaptive-routing.";
                }
                leaf adaptive-routing-ibgp {
                  when "../../../../../../../ni:name!='_public_'";
                  type empty;
                  description
                    "Enable/disable routes of iBGP peers support load balancing adaptive-routing.";
                }
              }
              leaf-list esi-name {
                when "../../../../../../ni:name!='_public_'";
                type string {
                    length "1..31";
                }
                max-elements 512;
                description
                  "Configure the ESI name.";
              }
              container default-esi {
                when "../../../../../../ni:name != '_public_'";
                description
                  "Configure the default ESI name.";
                leaf name {
                  type string {
                      length "1..31";
                  }
                  description
                    "The default ESI name.";
                }
              }
              uses group-rpki;
              container option {
                description
                  "Configure address family common options.";
                uses option-group;
                leaf ip-prefix-route-resolution-esad-route {
                  when "../../../../../../../ni:name!='_public_'";
                  type empty;
                  description
                    "Ip-prefix route resolution with esad route.";
                }
                leaf valid-route-ipv6-nexthop {
                  when "../../../../../../../ni:name='_public_'";
                  type empty;
                  description
                    "Enable/disable public IPv4 routes are valid when the Next Hop IPv6 of the routes is reachable.";
                }
                leaf add-path-nexthop-ignore {
                  when "../../../../../../../ni:name='_public_'";
                  type empty;
                  description
                    "Enable/disable BGP to ignore the next hop of each BGP route when selecting routes for add-path. By default, only the routes with the different next hop can participate in add-path.";
                }
                leaf route-select-delay-relax {
                  when "../../../../../../../ni:name!='_public_'";
                  type empty;
                  must "../../common/route-select-delay!=0";
                  description
                    "Enable/disable delay routing rule relaxation.";
                }
              }
              container prefix-exempt {
                description
                  "Configure the exempt filtering policy applied to the routes received when bgp memory-resilence occurred.";
                uses group-exempt-ip-prefix;
              }
              uses advertise-peer-up-grouping;
              container advertise-on-startup {
                description
                  "Configure route advertisement on startup.";
                uses advertise-on-startup-delay {
                  refine advertise-delay {
                    must "not (../advertise-lowest-priority)";
                    must "not (../../bgp:advertise-peer-up/bgp:advertise-delay)";
                    must "not (/bgp:bgp/bgp:base-process/bgp:peer-up-route-lowest-priority='true')";
                  }
                }
                uses advertise-on-startup-lowest-priority {
                  refine advertise-lowest-priority {
                    must "../../../../../../../ni:name='_public_'";
                    must "not (../advertise-delay)";
                    must "not (../../bgp:advertise-peer-up/bgp:advertise-delay)";
                    must "not (/bgp:bgp/bgp:base-process/bgp:peer-up-route-lowest-priority='true')";
                  }
                }
              }
              container lowest-priority {
                description
                  "Configure route lowest-priority.";
                container aggregate-route {
                  presence "Configure aggregate-route lowest-priority.";
                  description
                  "Configure aggregate-route lowest-priority.";
                  leaf delay-time {
                  type uint32 {
                    range "1..86400";
                  }
                  units "s";
                    description
                      "Specifies the aggregate-route lowest-priority delay time.";
                  }
                }
              }
            }
            container ipv6-unicast {
              when "../type = 'ipv6uni'";
              must "../../../../../l3vpn:afs/l3vpn:af[l3vpn:type='ipv6-unicast']";
              description
                "Configure IPv6 unicast options.";
              container common {
                description
                  "Configure IPv6 unicast common options.";
                leaf router-id-auto-select {
                  when "../../../../../../../ni:name!='_public_'";
                  type boolean;
                  default "false";
                  description
                    "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

                    1. If Loopback interfaces configured with IP addresses exist, the largest IP address among the IP addresses of the Loopback interfaces is selected as the router ID.

                    2. If there is no Loopback interface configured with an IP address, the largest IP address among the IP addresses of other interfaces is selected as the router ID, regardless of whether the interface is Up.";
                }
                leaf router-id {
                  when "../../../../../../../ni:name!='_public_' and ../router-id-auto-select = 'false'";
                  type inet:ipv4-address-no-zone;
                  description
                    "ID of a router that is in IPv4 address format. Certain dynamic routing protocols require a router ID. If no router ID is specified for a router when these protocols are enabled, the router ID in the RM module is used by default. The default router ID in the RM module is 0.0.0.0 when the router is not configured with any interface. 
                     The rules for selecting a router ID are as follows:
                     1. If a router ID is set through this configuration, the set router ID is used. If the router ID is not set, a router ID is selected according to the following rules:
                     (1) If loopback interfaces configured with IP addresses exist, the largest IP address among the IP addresses of the loopback interfaces is selected as the router ID.
                     (2) If no loopback interface configured with an IP address exists, the largest IP address among the IP addresses of other interfaces is selected as the router ID, regardless of whether the interface is Up.
                     The router ID is reselected only when the interface address that is selected as the router ID is deleted or changed. The router ID is not reselected in any of the following cases:
                     a. The interface is Down.
                     b. A loopback interface is configured when the IP address of a non-loopback interface is selected as the router ID.
                     c. A larger IP address of an interface is configured.
                     2. Each VPN instance selects the router ID from the addresses of the interfaces of the VPN instance according to the preceding rules.
                     3. When both the AMB and SMB exist on the router, the system backs up the router ID set through the related command and the router ID that is selected from IP addresses of the interfaces. After the active/standby switchover is performed, the system checks the validity of the router ID selected from the interface addresses. If the router ID is invalid, the system reselects a router ID.";
                }
                leaf auto-frr {
                  type boolean;
                  default "false";
                  description
                    "Enable/disable BGP auto FRR.";
                }
                leaf auto-frr-best-effort {
                  when "../auto-frr='true'";
                  type empty;
                  description
                    "SRv6 BE of the primary route is preferred as the backup path.";
                }
                leaf maximum-load-balancing-ibgp {
                  type uint16 {
                    range "1..65535";
                  }
                  default "1";
                  description
                    "Specify the maximum number of equal-cost IBGP routes. The value range and default value are controlled by the PAF.";
                }
                leaf maximum-load-balancing-ebgp {
                  type uint16 {
                    range "1..65535";
                  }
                  default "1";
                  description
                    "Specify the maximum number of equal-cost EBGP routes. The value range and default value are controlled by the PAF.";
                }
                leaf explicit-null {
                  when "../../../../../../../ni:name='_public_'";
                  type boolean;
                  must "not(../lsp-operation='pop-go' and ../explicit-null='true')";
                  default "false";
                  description
                    "Enable/disable the function to explicit null. After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
                }
                leaf lsp-operation {
                  when "../../../../../../../ni:name='_public_'";
                  type lsp-operation-type;
                  must "not(../lsp-operation='pop-go' and ../explicit-null='true')";
                  default "pop";
                  description
                    "Label operation mode.";
                }
                leaf nexthop-select-depend-type {
                  when "../../../../../../../ni:name='_public_'";
                  type select-depend-type;
                  default "depend-tunnel";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  type boolean;
                  default "false";
                  description
                    "Enable/disable route with AIGP attribute for route selection.";
                }
                leaf supernet-unicast-advertise {
                  type boolean;
                  default "false";
                  description
                    "Enable/disable advertise supernet unicast routes.";
                }
                leaf bestroute-med-confederation {
                  when "../../../../../../../ni:name='_public_'";
                  type boolean;
                  default "false";
                  description
                    "Enable/disable BGP to compare Med value only within the federation.";
                }
                leaf bestroute-as-path-ignore {
                  type boolean;
                  must "../bestroute-as-path-ignore = 'false' or ../load-balanc-as-path-ignore ='false' or not(../load-balanc-as-path-ignore)";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'";
                  type boolean;
                  default "false";
                  description
                    "Enable/disable best external route selection.";
                }
                leaf attribute-set-enable {
                  when "../../../../../../../ni:name!='_public_'";
                  type boolean;
                  default "false";
                  description
                    "Enable/disable the capability of processing attribute set.";
                }
                leaf attribute-set-mode {
                  when "../attribute-set-enable='true'";
                  type bgp:attribute-set-type;
                  default "both";
                  description
                    "The processing mode of attribute set.";
                }
                leaf add-path-select-num {
                  when "../../../../../../../ni:name='_public_'";
                  type uint8 {
                    range "2..64";
                  }
                  description
                    "Number of add-path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf maximum-load-balancing {
                  type uint16 {
                    range "1..65535";
                  }
                  default "1";
                  description
                    "Specify the maximum number of equal-cost routes in the BGP routing table. The value depends on the associated license. Equal-cost BGP routes can be generated for load balancing only when the BGP routes meet the first nine rules of the route-selection policy and have the same AS-Path attribute. The value range and default value are controlled by the PAF.";
                }
                leaf best-route-bit-error-detection {
                  when "../../../../../../../ni:name!='_public_'";
                  type boolean;
                  default "false";
                  description
                    "Enable/disable the function to reroute traffic when a bit error event occurs.";
                }
                leaf import-rib-nexthop-invariable {
                  when "../../../../../../../ni:name!='_public_'";
                  type boolean;
                  default "false";
                  description
                    "Enable/disable advertise the route without modifying the next-hop.";
                }
                leaf route-relay-tunnel-v4 {
                  type boolean;
                  default "false";
                  description
                    "Enable/disable unicast-route recursive-lookup tunnel.";
                }
                leaf route-relay-tunnel-v4-selector {
                  when "../route-relay-tunnel-v4='true'";
                  type leafref {
                    path "/rtp:routing-policy/rtp:tunnel-selectors/rtp:tunnel-selector/rtp:name";
                  }
                  description
                    "Unicast route tunnel selector name.";
                }
                leaf route-relay-tunnel-v6-selector { 
                  when "../../../../../../../ni:name='_public_'"; 
                  type leafref {
                    path "/rtp:routing-policy/rtp:tunnel-selectors/rtp:tunnel-selector/rtp:name";
                  }
                  description
                    "Enable/disable unicast route recursive-lookup IPv6 tunnel by tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf bestroute-rd-large-first {
                  when "../../../../../../../ni:name!='_public_'";
                  type boolean;
                  default "false";
                  description
                    "Enable/disable a BGP device to select the route with the largest route distinguisher (RD) during route selection.";
                }
                choice bestroute-nexthop-priority {
                  description
                    "Configure route selection based on the next-hop priority.";
                  case enable {
                    description
                      "Enable route selection based on the next-hop priority.";
                      leaf nexthop-priority {
                        type nexthop-priority-address-type;
                        description
                          "Routes with next-hop IPv4 addresses and routes with next-hop IPv6 addresses coexist. If the next-hop address type is set to IPv4, routes with next-hop IPv4 addresses have a higher priority. If the next-hop address type is set to IPv6, routes with next-hop IPv6 addresses have a higher priority.";
                      }
                      leaf nexthop-priority-high-level {
                        when "../nexthop-priority";
                        type empty;
                        description
                          "Route selection based on the next-hop priority as the high-level condition.";
                      }
                  }
                  case disable {
                    description
                      "Disable route selection based on the next-hop priority.";
                      leaf nexthop-priority-disable {
                        when "../../../../../../../ni:name!='_public_'";
                        type empty;
                        description
                          "Disable route selection based on the next-hop priority.";
                      }
                  }
                }
                leaf ebgp-ecmp-nexthop-changed {
                  when "../maximum-load-balancing-ebgp and ../maximum-load-balancing-ebgp>1";
                  type boolean;
                  default "false";
                  description
                    "Enable/disable next hop of equal-cost EBGP routes is changed. Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when "../maximum-load-balancing-ibgp and ../maximum-load-balancing-ibgp>1";
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when "../maximum-load-balancing and ../maximum-load-balancing>1";
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'";
                  type uint16 {
                    range "1..65535";
                  }
                  must "../maximum-load-balancing-ibgp=1 and ../maximum-load-balancing-ebgp=1 and ../maximum-load-balancing=1 and ../load-balancing-eibgp-enable='false'";
                  description
                    "Specify the maximum number of equal-cost EBGP routes and IBGP routes. After the attribute is set, load balancing is performed among equal-cost BGP VPN routes, regardless of the route type, EBGP or IBGP. The value range and default value are controlled by the PAF.";
                }
                leaf eibgp-ecmp-nexthop-changed {
                  when "../maximum-load-balancing-eibgp";
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'";
                  type boolean;
                  must "not (../maximum-load-balancing-ibgp>1 or ../maximum-load-balancing-ebgp>1 or ../maximum-load-balancing-eibgp) or ../load-balancing-eibgp-enable='false'";
                  default "false";
                  description
                    "Enable/disable EIBGP route load balancing.";
                }
                leaf maximum-load-balancing-mixed {
                  when "../../../../../../../ni:name!='_public_'";
                  type uint16 {
                    range "1..65535";
                  }
                  must "not (../maximum-load-balancing>1 or ../maximum-load-balancing-eibgp) and ../maximum-load-balancing-ebgp=1 and ../maximum-load-balancing-ibgp=1 and ../load-balancing-eibgp-enable='false'";
                  description
                    "Specify the maximum number of equal-cost MIXED routes. The value range is controlled by the PAF.";
                }
                uses group-origin-as-validation-type;
                leaf advertise-route-mode {
                  when "../../../../../../../ni:name!='_public_'";
                  type bgp-advertise-route-mode;
                  default "all";
                  description
                    "VPN advertise route mode.";
                }
                leaf reoriginate-route {
                  when "../../../../../../../ni:name!='_public_'";
                  type boolean;
                  default "false";
                  description
                    "Enable/disable route reorigination.";
                }
                leaf original-attributes {
                  when "../reoriginate-route='true'";
                  type empty;
                  description
                    "Regenerate route with original attributes.";
                }
                uses common-configure;
                leaf load-balancing-ucmp {
                  type boolean;
                  default "false";
                  description
                  "Enable/disable the function of BGP UCMP.";
                }
                leaf load-balancing-local-learn-cross {
                  when "../../../../../../../ni:name!='_public_'";
                  type boolean;
                  must ". = 'false' or (. = 'true' and ../../../../../../../l3vpn:afs/l3vpn:af[l3vpn:type='ipv6-unicast']/l3vpn:lsp-operation = 'pop-go')";
                  default "false";
                  description
                  "Enable/disable local route for peer and cross route load balancing.";
                }
                leaf attribute-set-as-path-check {
                  when "../../../../../../../ni:name!='_public_'";
                  type boolean;
                  default "false";
                  description
                    "Enable/disable the capability of checking as-path in attribute set.";
                }
                leaf route-select-rule-relax {
                  when "../../../../../../../ni:name='_public_'";
                  type boolean;
                  default "false";
                  description
                    "Enable/disable use loose rules to select routes based on priorities and determine the routes for load balancing.";
                }
                leaf multi-nexthop-convergence {
                  when "../../../../../../../ni:name='_public_'";
                  type boolean;
                  must "../multi-nexthop-convergence ='false' or ../load-balancing-ucmp ='false'";
                  default "false";
                  description
                    "Enable/disable the function to speed up the delivery of route ecmp/frr entries to the forwarding plane.";
                }
                leaf attribute-set-reserve-srv6 {
                  when "../../../../../../../ni:name!='_public_' and ((../attribute-set-mode='receive') or (../attribute-set-mode='both'))";
                  type boolean;
                  default "false";
                  description
                	"Enable/disable the capability of reserving origin srv6 attribute when parsing attribute set.";
                }
              }
              uses bgp-route-preference-options;
              container nexthop-recursive-lookup {
               description
                "Configure next hop iteration.";
                container common {
                  description
                    "Configure next hop iteration common options.";
                  uses nexthop-recursive-lookup-restrain;
                  uses nexthop-recursive-lookup-default-route;
                  uses nexthop-recursive-lookup-include-srv6-best-effort;
                }
                container delay {
                  description
                    "Configure time of next hop change responding delay.";
                  uses nexthop-recursive-lookup-delay-grouping;
                }
              }
              uses ipv6-import-route;
              uses ipv6-aggregate-routes;
              uses ipv6-aggregate-default-route;
              container network-routes {
                description
                  "List of network routes.";
                list network-route {
                  key "address mask-length";
                  description
                    "Configure a network route in the BGP routing table.";
                  uses network-route-ipv6;
                }
              }
              container advertise-route-to-evpns {
                when "../../../../../../ni:name!='_public_'";
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "../../../../../../../../ni:name != current()";
                    description
                      "Source VPN name for imported RIBs.";
                  }
                  leaf source-address-family {
                    type bgp:import-rib-ipv6-safi-type;
                    must "/ni:network-instance/ni:instances/ni:instance[ni:name=current()/../bgp:source-vpn]/l3vpn:afs/l3vpn:af[l3vpn:type='ipv6-unicast']";
                    description
                      "Source address family type for imported RIBs.";
                  }
                  leaf valid-route {
                    type boolean;
                    default "false";
                    description
                      "Enable/disable imported valid route.";
                  }
                  leaf include-label-route {
                    type boolean;
                    default "false";
                    description
                      "Enable/disable imported include label route.";
                  }
                  uses choice-policy-set;
                }
              }
              container segment-routing-ipv6 {
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
                leaf srv6-color-only-enable {
                  type empty;
                  description
                    "Enable SRv6-TE Policy color-only iteration.";
                }
                leaf srv6-track-bfd-for-locator-enable {
                  when "../../../../../../../ni:name!='_public_'";
                  type empty;
                  description
                    "Enable SRv6-TE Policy track bfd-for-locator.";
                }
                leaf srv6-anycast-sid-enable {
                  when "../../../../../../../ni:name!='_public_'";
                  type empty;
                  description
                    "Enable Anycast SID iteration.";
                }
              }
              container hierarchy-convergence {
                when "../../../../../../ni:name='_public_'";
                description
                  "Configure unicast route hierarchy convergence.";
                uses ipv6-hierarchy-convergence;
              }
              uses vrf-af-dampening-routes;
              uses ipv6-import-filter-protocol-type;
              uses ipv6-export-filter-protocol-type;
              uses bgp:slow-peer-type;
              uses routing-table-rib-only-type {
                refine routing-table-rib-only/enable {
                  must "not (../../common/active-route-advertise = 'true' and ../enable = 'true')";
                }
              }
              uses ipv6-qos-local-id-type;
              uses region-validation-grp;
              uses bestroute-nh-relay-pri-grp;
              container bestroute-address-family-priority {
                when "../../../../../../ni:name != '_public_'";
                must "not(address-family-priority and address-family-priority-disable)";
                description
                  "Configure route selection based on the address family priority.";
                leaf address-family-priority {
                  type ipv6-address-family-priority-type;
                  description
                    "VPN address family type for IPv6 Route.";
                }
                leaf address-family-priority-disable {
                  type empty;
                  description
                    "Disable route selection based on the address-family-priority.";
                }
              }
              uses load-balancing6;
              leaf-list esi-name {
                when "../../../../../../ni:name!='_public_'";
                type string {
                    length "1..31";
                }
                max-elements 512;
                description
                  "Configure the ESI name.";
              }
              container default-esi {
                when "../../../../../../ni:name != '_public_'";
                description
                  "Configure the default ESI name.";
                leaf name {
                  type string {
                      length "1..31";
                  }
                  description
                    "The default ESI name.";
                }
              }
              uses group-rpki;
              container option {
                description
                  "Configure address family common options.";
                uses option-group;
                leaf ip-prefix-route-resolution-esad-route {
                  when "../../../../../../../ni:name!='_public_'";
                  type empty;
                  description
                    "Ip-prefix route resolution with esad route.";
                }
                leaf add-path-label-ignore {
                  when "../../../../../../../ni:name='_public_'";
                  type empty;
                  description
                    "Enable/disable BGP to ignore the label of each BGP route when selecting routes for add-path.";
                }
                leaf route-relay-srpolicy-color-only {
                  when "../../../../../../../ni:name='_public_'";
                  type empty;
                  must "not(../../segment-routing-ipv6/srv6-best-effort-enable or ../../segment-routing-ipv6/srv6-traffic-engineer-enable)";
                  description
                    "Enable/disable unicast-route color-only recursive-lookup sr-te-policy.";
                }
                leaf route-select-delay-relax {
                  when "../../../../../../../ni:name!='_public_'";
                  type empty;
                  must "../../common/route-select-delay!=0";
                  description
                    "Enable/disable delay routing rule relaxation.";
                }
              }
              container prefix-exempt {
                description
                  "Configure the exempt filtering policy applied to the routes received when bgp memory-resilence occurred.";
                uses group-exempt-ipv6-prefix;
              }
              uses advertise-peer-up-grouping;
              container advertise-on-startup {
                description
                  "Configure route advertisement on startup.";
                uses advertise-on-startup-delay {
                  refine advertise-delay {
                    must "not (../advertise-lowest-priority)";
                    must "not (../../bgp:advertise-peer-up/bgp:advertise-delay)";
                    must "not (/bgp:bgp/bgp:base-process/bgp:peer-up-route-lowest-priority='true')";
                  }
                }
                uses advertise-on-startup-lowest-priority {
                  refine advertise-lowest-priority {
                    must "../../../../../../../ni:name='_public_'";
                    must "not (../advertise-delay)";
                    must "not (../../bgp:advertise-peer-up/bgp:advertise-delay)";
                    must "not (/bgp:bgp/bgp:base-process/bgp:peer-up-route-lowest-priority='true')";
                  }
                }
              }
              container lowest-priority {
                description
                  "Configure route lowest-priority.";
                container aggregate-route {
                  presence "Configure aggregate-route lowest-priority.";
                  description
                  "Configure aggregate-route lowest-priority.";
                  leaf delay-time {
                  type uint32 {
                    range "1..86400";
                  }
                  units "s";
                    description
                      "Specifies the aggregate-route lowest-priority delay time.";
                  }
                }
              }
            }
            container ipv4-vpn {
              when "../type = 'ipv4vpn' and ../../../../../ni:name='_public_'";
              description
                "Configure IPv4 VPNv4 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/rtp:routing-policy/rtp:tunnel-selectors/rtp:tunnel-selector/rtp:name";
                }
                description
                  "Configure a tunnel selector and apply it to the BGP IPv4 unicast, BGP VPNv4 address families and BGP VPNv6 address families so that IPv4,VPNv4 and VPNv6 labeled routes can be iterated to tunnels based on the tunnel selector.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type-ext;
                default "depend-ip";
                description
                  "In none mode, route selection does not depend on whether the next hop is reachable. In tunnel mode, the labeled BGP IPv4 route can participate in route selection only after its next hop is iterated to an LSP. In IP 
                  mode, the labeled BGP IPv4 route can participate in route selection only after its next hop is iterated to an IP address. By default, the labeled BGP IPv4 route can participate in route selection 
                  if its next hop can be iterated to an IP address, regardless of whether the LSP of the next hop exists. This allows the RR that is not enabled with MPLS to forward labeled routes. In non-RR 
                  networking or RR networking where the BGP next hop is changed, BGP needs to check whether there is an LSP destined for the next hop. If such an LSP is not found, BGP needs to establish an LSP in 
                  advance. If the default setting is adopted, a labeled BGP IPv4 unicast route may be selected prior to LSP establishment. As a result, services are incorrectly switched before LSP establishment and 
                  service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'";
                type boolean;
                default "false";
                description
                  "Enable/disable best external route selection.";
              }
              leaf label-free-delay {
                type uint8 {
                  range "0..180";
                }
                units "s";
                default "0";
                description
                  "Label free delay.";
              }
              leaf add-path-select-num {
                when "../../../../../../ni:name='_public_'";
                type uint8 {
                  range "2..64";
                }
                description
                  "Number of Add-Path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              leaf activate-route-tag {
                type boolean;
                default "false";
                description
                  "Enable/disable tag-based filtering.";
              }
              leaf vpn-orf-enable {
                type boolean;
                default "true";
                description
                  "Enable/disable VPN-ORF capability.";
              }
              uses route-reflector-ext-community-filter-type;
              uses load-balancing-configuration;
              uses vrf-af-dampening-routes;
              container nexthop-recursive-lookup {
               description
                "Configure next hop iteration.";
                container common {
                  description
                    "Configure next hop iteration common options.";
                  uses nexthop-recursive-lookup-restrain;
                  uses nexthop-recursive-lookup-default-route;
                  uses nexthop-recursive-lookup-include-srv6-best-effort;
                  }
                  uses nexthop-recursive-lookup-delay;          
                  uses bit-error-detection-type;
              }
              uses ipv4-import-filter-protocol-type;
              uses ipv4vpn-export-filter-protocol-type;
              uses bgp:slow-peer-type;
              uses bestroute-nexthop-priority-grp;
              uses bestroute-nh-relay-pri-grp-mask;
              container option {
                description
                  "Configure address family common options.";
                uses option-group;
                leaf srv6-multi-prefix-sid-enable {
                  type empty;
                  description
                    "Enable parsing multi prefix SIDs of VPN route.";
                }
              }
              container prefix-exempt {
                description
                  "Configure the exempt filtering policy applied to the routes received when bgp memory-resilence occurred.";
                uses group-exempt-ip-prefix;
              }
              container advertise-on-startup {
                description
                  "Configure route advertisement on startup.";
                uses advertise-on-startup-delay {
                  refine advertise-delay {
                    must "not (/bgp:bgp/bgp:base-process/bgp:peer-up-route-lowest-priority='true')";
                  }
                }
              }
            }
            container ipv6-vpn {
              when "../type = 'ipv6vpn' and ../../../../../ni:name='_public_'";
              description
                "Configure IPv6 VPNv6 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/rtp:routing-policy/rtp:tunnel-selectors/rtp:tunnel-selector/rtp:name";
                }
                description
                  "Configure a tunnel selector and apply it to the BGP IPv4 unicast, BGP VPNv4 address families and BGP VPNv6 address families so that IPv4,VPNv4 and VPNv6 labeled routes can be iterated to tunnels based on the tunnel selector. By default, no tunnel selector is configured.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type-ext;
                default "depend-ip";
                description
                  "In none mode, route selection does not depend on whether the next hop is reachable. In tunnel mode, the labeled BGP IPv4 route can participate in route selection only after its next hop is iterated to an LSP. In IP 
                  mode, the labeled BGP IPv4 route can participate in route selection only after its next hop is iterated to an IP address. By default, the labeled BGP IPv4 route can participate in route selection 
                  if its next hop can be iterated to an IP address, regardless of whether the LSP of the next hop exists. This allows the RR that is not enabled with MPLS to forward labeled routes. In non-RR 
                  networking or RR networking where the BGP next hop is changed, BGP needs to check whether there is an LSP destined for the next hop. If such an LSP is not found, BGP needs to establish an LSP in 
                  advance. If the default setting is adopted, a labeled BGP IPv4 unicast route may be selected prior to LSP establishment. As a result, services are incorrectly switched before LSP establishment and 
                  service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'";
                type boolean;
                default "false";
                description
                  "Enable/disable best external route selection.";
              }
              leaf add-path-select-num {
                when "../../../../../../ni:name='_public_'";
                type uint8 {
                  range "2..64";
                }
                description
                  "Number of add-path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              leaf label-free-delay {
                type uint8 {
                  range "0..180";
                }
                units "s";
                default "0";
                description
                  "Label free delay.";
              }
              leaf vpn-orf-enable {
                type boolean;
                default "true";
                description
                  "Enable/disable VPN-ORF capability.";
              }
              uses route-reflector-ext-community-filter-type;
              uses load-balancing-configuration;
              container nexthop-recursive-lookup {
               description
                "Configure next hop iteration.";
                  container common {
                  description
                    "Configure next hop iteration common options.";
                    uses nexthop-recursive-lookup-restrain;
                    uses nexthop-recursive-lookup-default-route;
                    uses nexthop-recursive-lookup-include-srv6-best-effort;
                  }
                  uses nexthop-recursive-lookup-delay;
                  uses bit-error-detection-type;
              }
              uses ipv6-import-filter-protocol-type;
              uses ipv6vpn-export-filter-protocol-type;
              uses bgp:slow-peer-type;
              uses vrf-af-dampening-routes;
              uses bestroute-nexthop-priority-grp;
              uses bestroute-nh-relay-pri-grp-mask;
              container option {
                description
                  "Configure address family common options.";
                uses option-group;
                leaf srv6-multi-prefix-sid-enable {
                  type empty;
                  description
                    "Enable parsing multi prefix SIDs of VPN route.";
                }
              }
              container prefix-exempt {
                description
                  "Configure the exempt filtering policy applied to the routes received when bgp memory-resilence occurred.";
                uses group-exempt-ipv6-prefix;
              }
              container advertise-on-startup {
                description
                  "Configure route advertisement on startup.";
                uses advertise-on-startup-delay {
                  refine advertise-delay {
                    must "not (/bgp:bgp/bgp:base-process/bgp:peer-up-route-lowest-priority='true')";
                  }
                }
              }
            }
            container ipv4-labeluni {
              when "../type = 'ipv4labeluni'";
              must "../../../../../l3vpn:afs/l3vpn:af[l3vpn:type='ipv4-unicast']";
              description
                "Configure IPv4 label unicast options.";
              container common {
                description
                  "Configure IPv4 label unicast common options.";
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf frr-non-host-label-route {
                  when "../auto-frr='true' and ../../../../../../../ni:name='_public_'";
                  type empty;
                  description
                    "FRR can be performed on labeled routes with non-32-bit masks.";
                }
                leaf tunnel-selector-name {
                  when "../../../../../../../ni:name='_public_'";
                  type leafref {
                    path "/rtp:routing-policy/rtp:tunnel-selectors/rtp:tunnel-selector/rtp:name";
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  when "../tunnel-selector-name";
                  type boolean;
                  default "false";
                  description
                    "Enable/disable tunnel selector for labeled, imported, and network segment routes.";
                }
                leaf nexthop-select-depend-type {
                  when "../../../../../../../ni:name='_public_'";
                  type select-depend-type;
                  default "depend-tunnel";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf best-route-bit-error-detection {
                  when "../../../../../../../ni:name!='_public_'";
                  type boolean;
                  default "false";
                  description
                    "Enable/disable the function to reroute traffic when a bit error event occurs.";
                }
                leaf supernet-label-advertise {
                  type boolean;
                  default "true";
                  description
                    "Enable/disable the function to advertise supernet labeled routes.";
                }
                leaf lsp-mtu {
                  type uint16 {
                    range "46..65535";
                  }
                  default "1500";
                  description
                    "BGP LSP MTU.";
                }
                leaf label-free-delay {
                  type uint8 {
                    range "0..180";
                  }
                  units "s";
                  default "0";
                  description
                    "Label free delay.";
                }
                leaf bestroute-med-confederation {
                  when "../../../../../../../ni:name='_public_'";
                  type boolean;
                  default "false";
                  description
                    "Enable/disable BGP to compare Med value only within the federation.";
                }
                leaf bestroute-as-path-ignore {
                  type boolean;
                  must "../bestroute-as-path-ignore = 'false' or ../load-balanc-as-path-ignore ='false' or not(../load-balanc-as-path-ignore)";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'";
                  type boolean;
                  default "false";
                  description
                    "Enable/disable best external route selection.";
                }
                leaf add-path-select-num {
                  when "../../../../../../../ni:name='_public_'";
                  type uint8 {
                    range "2..64";
                  }
                  description
                    "Number of add-path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                leaf import-rib-nexthop-invariable {
                  when "../../../../../../../ni:name!='_public_'";
                  type boolean;
                  default "false";
                  description
                    "Enable/disable the command to enable advertise the route without modifying the next-hop.";
                }
                uses reflect-type;
                uses reflector-cluster-type;
                leaf reflect-between-client {
                  type boolean;
                  default "true";
                  description
                    "Enable/disable route reflection between clients. If clients of a route reflector (RR) are fully meshed, you can disable route reflection among clients to reduce the cost.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf ext-community-change {
                  type boolean;
                  default "false";
                  description
                    "Enable/disable the function to change the extended community attribute.";
                }
                leaf ebgp-interface-sensitive {
                  type boolean;
                  default "true";
                  status obsolete;
                  description
                    "Enable/disable the function of EBGP interface fast sensing. If this function is enabled, the sessions of directly connected EBGP peers are immediately cleared from the associated interface when the interface becomes down.";
                }
              }
              container nexthop-recursive-lookup {
               description
                "Configure next hop iteration.";
                container common {
                  description
                    "Configure next hop iteration common options.";
                    uses nexthop-recursive-lookup-restrain;
                    uses nexthop-recursive-lookup-include-srv6-best-effort;
                }
                uses nexthop-recursive-lookup-delay;
              }
              container import-routes {
                description
                  "List of imported routes.";
                list import-route {
                  key "protocol process-id";
                  description
                    "Apply route import policy. Routes of other protocol types can be imported by BGP. By default, BGP does not import routes of other protocol types.";
                  uses import-routes-type;
                  leaf non-relay-tunnel {
                    when "../../../../../../../../ni:name='_public_'";
                    type boolean;
                    default "false";
                    description
                      "Enable/disable imported route relay a tunnel.";
                  }
                  leaf-list exclude-direct-type {
                    when "../protocol='direct'";
                    type bgp:direct-route-type;
                    description
                      "Configure type of route to be excluded when direct routes are imported.";
                  }
                }
              }
              container network-routes {
                description
                  "List of network routes.";
                list network-route {
                  key "address mask-length";
                  description
                    "Configure a network route in the BGP routing table.";
                  uses network-route-ipv4;
                  leaf non-relay-tunnel {
                    when "../../../../../../../../ni:name='_public_'";
                    type boolean;
                    default "false";
                    description
                      "Enable/disable imported route relay a tunnel.";
                  }
                  leaf label-index {
                    when "../../../../../../../../ni:name='_public_'";
                    type uint32 {
                      range "0..4294967294";
                    }
                    description
                    "Management label value assigned for imported routes.";
                  }
                }
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "not(../../../../../../../../ni:name = current() and ../source-address-family = 'ipv4labeluni')";
                    description
                      "Source VPN name.";
                  }
                  leaf source-address-family {
                    type bgp:import-rib-ipv4-safi-type;
                    must "(current() = 'ipv4labeluni' and /ni:network-instance/ni:instances/ni:instance[ni:name=current()/../bgp:source-vpn]/bgp:bgp/bgp:base-process/bgp:afs/bgp:af[bgp:type='ipv4labeluni']/bgp:ipv4-labeluni) or (current() = 'ipv4uni' and /ni:network-instance/ni:instances/ni:instance[ni:name=current()/../bgp:source-vpn]/l3vpn:afs/l3vpn:af[l3vpn:type='ipv4-unicast'])";
                    description
                      "Source address family type.";
                  }
                  leaf valid-route {
                    type boolean;
                    default "false";
                    description
                      "Enable/disable imported valid route.";
                  }
                  leaf include-label-route {
                    when "../source-address-family='ipv4uni'";
                    type boolean;
                    default "false";
                    description
                      "Enable/disable imported include label route.";
                  }
                  uses choice-policy-set;
                }
              }
              container lsp-options {
                description
                  "Configure BGP ingress-lsp.";
                uses safi-lsp-options;
                leaf maximum-load-balancing-transit {
                  type uint16 {
                    range "1..65535";
                  }
                  default "1";
                  description
                    "Maximum number of transit LSPs for load balancing.";
                }
                leaf unicast-rt-label-advertise-popgo {
                  when "../../../../../../../ni:name='_public_'";
                  type boolean;
                  default false;
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  when "../../../../../../../ni:name='_public_' and ../apply-label-mode='per-route'";
                  type lsp-operation-type;
                  default "pop";
                  description
                    "Label operation type.";
                }
                uses ingress-choice-policy-set;
                leaf apply-label-mode {
                  when "../../../../../../../ni:name='_public_'";
                  type labeluni-apply-label-type;
                  must "(/bgp:bgp/bgp:base-process/bgp:srgbs/bgp:srgb/bgp:lower-bound and ../apply-label-mode = 'per-route') or not(/bgp:bgp/bgp:base-process/bgp:srgbs/bgp:srgb/bgp:lower-bound)";
                  must "not (.= 'per-path' and (../../import-ribs/import-rib/include-label-route = 'true' or ../../import-ribs/import-rib/source-address-family = 'ipv4labeluni'))";
                  default "per-route";
                  description
                    "Method of distributing labels to labeled unicast routes."; 
                }
                leaf wtr-timer {
                  when "../../../../../../../ni:name='_public_'";
                  type uint8 {
                    range "1..60";
                  }
                  units "s";
                  description
                    "Specify the WTR (Wait To Restore) value of LSP in seconds.";
                }
              }
              uses vrf-af-dampening-routes;
              uses bgp:slow-peer-type;
              container option {
                description
                  "Configure address family common options.";
                leaf add-path-nexthop-ignore {
                  when "../../../../../../../ni:name='_public_'";
                  type empty;
                  description
                    "Enable/disable BGP to ignore the next hop of each BGP route when selecting routes for add-path. By default, only the routes with the different next hop can participate in add-path.";
                }
                leaf load-balancing-nexthop-ignore {
                  when "../../../../../../../ni:name='_public_'";
                  type empty;
                  description
                    "Enable/disable BGP to ignore the next hop of each BGP route when selecting routes for load balancing. By default, only the routes with the different next hop can participate in load balancing.";
                }
                leaf advertise-community-graceful-shutdown {
                  type bgp:advertise-community-gshut-type;
                  description
                  "Specify the type of peer that advertises community graceful shutdown.";
                }
              }
            }
            container ipv4-multicast {
              when "../type='ipv4multi'";
              must "../../../../../l3vpn:afs/l3vpn:af[l3vpn:type='ipv4-unicast']";
              description
                "Configure IPv4 multicast options.";
              container common {
                description
                  "Configure BGP IPv4-multicast address family options.";
                leaf auto-frr {	
	              when "../../../../../../../ni:name!='_public_'";			
	              type boolean;			
	              default "false";			
	              description			
	                "Enable/disable BGP Auto FRR. If IP FRR, VPN FRR, and Auto FRR are all enabled, IP FRR and VPN FRR take precedence over Auto FRR. If a route fails to match the routing policy of IP FRR or VPN FRR, Auto FRR takes effect.";			
	            }
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf bestroute-med-confederation {
                  when "../../../../../../../ni:name='_public_'";
                  type boolean;
                  default "false";
                  description
                    "Enable/disable BGP to compare Med value only within the federation.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                uses reflect-type;
                uses reflector-cluster-type;
                leaf reflect-between-client {
                  type boolean;
                  default "true";
                  description
                    "Enable/disable route reflection between clients. If clients of a route reflector (RR) are fully meshed, you can disable route reflection among clients to reduce the cost.";
                }
                leaf determin-med {
                  type boolean;
                  default "false";
                  description
                    "Enable/disable deterministic MED so that the route selection result is relevant to the sequence in which routes are received.";
                }
                uses bestroute-med-plus-igp-type;
                uses bestroute-router-id-prior-clusterlist-type;
                leaf bestroute-as-path-ignore {
                  type boolean;
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
              }
                leaf bestroute-med-none-as-maximum {
                  type boolean;
                  default "false";
                  description
                    "Enable/disable BGP considers its MED as the largest MED value (4294967295). If a route does not carry MED, BGP considers its MED as the default value (0) during route selection.";
                }
                leaf maximum-load-balancing {
                  type uint16 {
                    range "1..65535";
                  }
                  must "not (../maximum-load-balancing-ibgp>1 or ../maximum-load-balancing-ebgp>1) or ../maximum-load-balancing=1";
                  default "1";
                  description
                    "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute. The value range and default value are controlled by the PAF.";
                }
                leaf maximum-load-balancing-ibgp {
                  type uint16 {
                    range "1..65535";
                  }
                  must "not (../maximum-load-balancing>1) or ../maximum-load-balancing-ibgp=1";
                  default "1";
                  description
                    "Specify the maximum number of equal-cost IBGP routes. The value range and default value are controlled by the PAF.";
                }
                leaf maximum-load-balancing-ebgp {
                  type uint16 {
                    range "1..65535";
                  }
                  must "not (../maximum-load-balancing>1) or ../maximum-load-balancing-ebgp=1";
                  default "1";
                  description
                    "Specify the maximum number of equal-cost EBGP routes. The value range and default value are controlled by the PAF.";
                }
                leaf ext-community-change {
                  type boolean;
                  default "false";
                  description
                    "Enable/disable the function to change the extended community attribute.";
                }
              }
              container nexthop-recursive-lookup {
                description
                  "Configure next hop iteration.";
                container common {
                  description
                  "Configure next hop iteration common options.";
                  choice policy-type {
                    description
                      "Set route-policy or route-filter.";
                    case rtp-ref {
                    description
                      "Route policy.";
                      leaf route-policy {
                        type leafref {
                          path "/rtp:routing-policy/rtp:policy-definitions/rtp:policy-definition/rtp:name";
                        }
                        description
                          "Specify the name of a routing policy.";
                      }
                    }
                    case xpl-ref {
                      description
                        "Route filter.";
                      uses route-filter-type;
                    }
                  }
                  uses nexthop-recursive-lookup-include-srv6-best-effort;
                }
                uses nexthop-recursive-lookup-delay;
              }
              uses bgp-route-preference-options;
              uses vrf-af-dampening-routes;
              container network-routes {
                description
                  "List of network routes.";
                list network-route {
                  key "address mask-length";
                  description
                    "Configure a network route in the BGP routing table.";
                  uses network-route-ipv4;
                }
              }
              container import-routes {
                description
                  "List of imported routes.";
                list import-route {
                  key "protocol process-id";
                  description
                    "Configure route import. Routes of other protocol types can be imported by BGP. By default, BGP does not import routes of other protocol types.";
                  leaf protocol {
                    type bgp:ipv4multi-import-route-protocol-type;
                    description
                      "Routing protocol from which routes can be imported.";
                  }
                  leaf process-id {
                    type uint32 {
                      range "0..4294967295";
                    }
                    must "((../protocol='ospf' or ../protocol='isis' or ../protocol='rip') and ../process-id!=0) or (../protocol!='ospf' and ../protocol!='isis' and ../protocol!='rip' and ../process-id=0)";
                    description
                      "Process ID of an imported routing protocol. The process ID is 0, if the imported routing protocol is direct routes, static routes, UNRs, or OP-routes. The process ID must be specified range from 1 to 4294967295, if the imported routing protocol is RIP, OSPF, ISIS.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/rtp:routing-policy/rtp:policy-definitions/rtp:policy-definition/rtp:name";
                        }
                        description
                          "When routes are imported from other routing protocols, the route-policy filter can be used to filter the routes and change route attributes.";
                      }
                    }
                    case xpl-ref {
                      description
                        "Route filter.";
                      uses route-filter-type;
                    }
                  }
                  leaf-list exclude-direct-type {
                    when "../protocol='direct'";
                    type bgp:direct-route-type;
                    description
                      "Configure type of route to be excluded when direct routes are imported.";
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  uses unicast-aggregate-routes-type {
                    refine address {
                      must "not(contains(../address,':'))";
                    }
                    refine mask-length {
                      must "../mask-length<=32";
                    }
                  }
                }
              }
              uses ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:ipv4-export-filter-protocol-type;
                    description
                      "Specify the name of a routing protocol. The routing protocol takes effect only on the routes to be advertised.";
                  }
                  leaf process-id {
                    type uint32 {
                    range "0..4294967295";
                    }
                    must "((../protocol='ospf' or ../protocol='rip' or ../protocol='isis') and ../process-id!=0) or ((../protocol!='ospf' and ../protocol!='rip' and ../protocol!='isis') and ../process-id=0)";
                    description
                      "Specify the process ID required to be matched. The value is an integer ranging from 0 to 4294967295. If direct or static routes need to be filtered, no process ID is required.";
                  }
                  uses ipv4-filter-protocol-policy-choice-type;
                }
              }
              uses bgp:slow-peer-type;
              container qos {
                when "../../../../../../ni:name='_public_'";
                description
                  "Configure QoS.";
                uses qos-local-id-policy-choice-type; 
              }
              container import-ribs {
                when "../../../../../../ni:name!='_public_'";
                description
                  "List of imported RIBs configuration.";
                list import-rib {
                  key "source-vpn source-address-family";
                  description
                    "Configure imported RIBs.";
                  leaf source-vpn {
                    type leafref {
                      path "/ni:network-instance/ni:instances/ni:instance/ni:name";
                    }
                    must "../../../../../../../../ni:name = current()";
                    description
                      "Source VPN name.";
                  }
                  leaf source-address-family {
                    type bgp:import-rib-ipv4-multicast-safi-type;
                    must "/ni:network-instance/ni:instances/ni:instance[ni:name=current()/../bgp:source-vpn]/l3vpn:afs/l3vpn:af[l3vpn:type='ipv4-unicast']";
                    description
                      "Source address family type.";
                  }
                  leaf valid-route {
                    type boolean;
                    default "false";
                    description
                      "Enable/disable imported valid route.";
                  }
                  leaf include-label-route {
                    type boolean;
                    default "false";
                    description
                      "Enable/disable imported include label route.";
                  }
                  uses choice-policy-set;
                }
              }
            }
          }
        }
        container vpn-as-number {
          when "../../../ni:name!='_public_'";
          description
            "Configure BGP vpn as-number.";
            leaf local-ipv4 {
              type as-number-validate;
              description
                "IPv4 as-number.";
            }
            leaf local-ipv6 {
              type as-number-validate;
              description
                "IPv6 as-number.";
            }
            leaf ipv4-as-no-prepend {
              when "../local-ipv4";
              type empty;
              description
                "IPv4 as-number no prepend.";
            }
            leaf ipv6-as-no-prepend {
              when "../local-ipv6";
              type empty;
              description
                "IPv6 as-number no prepend.";
            }
        }
        container dynamic-peer-prefixes {
          description
            "List of IP prefixes from which a dynamic BGP peer group listens for BGP connection requests.";
          list dynamic-peer-prefix {
            key "address mask-length peer-group";
            description
              "Configure an IP prefix from which a dynamic BGP peer group listens for BGP connection requests.";
            leaf address {
              type inet:ip-address-no-zone;
              description
                "Network segment address for a dynamic peer connection.";
            }
            leaf mask-length {
              type uint8 {
                range "0..128";
              }
              description
                "Mask length of a network segment.";
            }
            leaf peer-group {
              type leafref {
                path "../../../peer-groups/peer-group/name";
              }
              must "../../../peer-groups/peer-group[name = current()]/peer-establish-mode = 'dynamic'";
              must "../../../peer-groups/peer-group[name = current()]/type = 'ibgp' or (../../../peer-groups/peer-group[name = current()]/listen-as or ../../../peer-groups/peer-group[name = current()]/listen-as-segments/listen-as-segment or ../../../peer-groups/peer-group[name = current()]/as-number-type='confederation')";
              description
                "The peer-group within which the dynamic neighbor will be configured.";
            }
          }
        }
        container unnumbered-peer-interfaces {
          description
            "List of address unnumbered interface.";
          list unnumbered-peer-interface {
            key "if-name";
            description
              "Configure the interface bound to the peer group.";
            leaf if-name {
              type leafref {
                path "/ifm:ifm/ifm:interfaces/ifm:interface/ifm:name";
              }
              description
                "Address unnumbered interface.";
            }
            leaf peer-group {
              type leafref {
                path "../../../peer-groups/peer-group/name";
              }
              must "../../../peer-groups/peer-group[name = current()]/peer-establish-mode='unnumbered'";
              mandatory true;
              description
                "The peer-group within which the unnumbered neighbor will be configured.";
              ext:operation-exclude update {
                description "The node cannot be modified, when node is already configured.";
              }
            }
          }
        }
        container peer-groups {
          description
            "List of BGP peer groups. The BGP peer groups can help you simplify the configurations. If you want to perform the same configuration for several peers, you can create a peer group and then configure the peer group. After you add these peers to the peer group, all these peers will have the same configurations as the peer group.";
          list peer-group {
            key "name";
            description
              "Configure information about a BGP peer group.";
            leaf name {
              type string {
                length "1..47";
                pattern '([^\? ]+)';
              }
              description
                "Specify the name of a peer group. The value is a string of characters, spaces not supported.";
            }
            leaf type {
              type group-type;
              mandatory true;
              description
                "Specify the type of a peer group. The value can be IBGP or EBGP.The object cannot be modified.";
              ext:operation-exclude update {
                description "The node cannot be modified, when node is already configured.";
              }
            }
            uses peer-local-if-type;
            uses authentication-attr-type;
            leaf tcp-ao-name {
              type leafref {
                path "/socket:socket/socket:tcp-aos/socket:tcp-ao/socket:name";
              }
              must "not(../password-type!='null' or ../key-chain-name)";
              must "/socket:socket/socket:tcp-aos/socket:tcp-ao[socket:name=current()]/socket:accept-mismatch='false'";
              description
                "Specify TCP-AO authentication for establishing the TCP connection between BGP peers.";
            }
            leaf description {
              type string {
                length "1..255";
                pattern '([^?]*)';
              }
              description
                "Specify the description of a peer group. The value is a string, which can be letters or digits, spaces supported. By default, no description is configured.";
            }
            leaf group-as {
              when "not(../type='ibgp') and ../peer-establish-mode = 'static'";
              type as-number-validate;
              description
                "Specify the AS number of a peer group. The AS number is in either a 2-byte or 4-byte format. 
                The two-byte format is X. X is an integer ranging from 1 to 65535.
                The four-byte format is X.Y and X. When the format is X.Y, X and Y are both integers, with the value of X ranging from 1 to 65535, and the value of Y ranging from 0 to 65535; when the format is X, X is an integer, with the value of X ranging from 1 to 4294967295.";
            }
            leaf tcp-mss {
              type uint16 {
                range "176..4096";
              }
              description
                "Maximum TCP MSS value used for TCP connection establishment for a peer group.";
            }
            leaf ebgp-max-hop {
              when "../type='ebgp'";
              type uint32 {
                range "1..255";
              }
              must "not(../valid-ttl-hops) or (../valid-ttl-hops>=1 and not(../valid-ttl-hops>255) and ../ebgp-max-hop=1)";
              default "1";
              description
                "Maximum number of hops in an indirect EBGP connection. By default, EBGP connections can be established only between directly connected peers. The function must be configured on both ends.";
            }
            leaf extended-open-message {
              when "../../../../../ni:name='_public_'";
              type peer-attr-enable-type;
              default "disable";
              description
              "Enable the capability of advertising BGP Open messages with extended optional parameters length.";
            }
            leaf valid-ttl-hops {
              type uint16 {
                range "1..255";
              }
              must "not(../ebgp-max-hop and ../ebgp-max-hop>1)";
              description
                "Enable GTSM on a peer or peer group. The valid-TTL-Value parameter is used to specify the number of TTL hops to be detected. If the value is configured as hops, the valid TTL range of the detected packet is [255-hops+1, 255].";
            }
            uses peer-tracking-type;
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf connect-mode {
              when "../peer-establish-mode!='dynamic' and ../peer-establish-mode!='dynamic-ipv6'";
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              when "../peer-establish-mode = 'static'";
              type boolean;
              default "false";
              description
                "Enable/disable path mtu auto discovery.";
            }
            leaf local-ifnet-disable {
              type boolean;
              description
                "Enable/disable MPLS local IFNET tunnel creation on a BGP peer. By default, MPLS local IFNET tunnels can be created on an EBGP peer,but such tunnels cannot be created on an IBGP peer.";
              ext:dynamic-default {
                ext:default-value "false" {
                  when "../type='ebgp'";
                  description "The default value is false when group type is ebgp.";
                }
                ext:default-value "true" {
                  when "../type='ibgp'";
                  description "The default value is true when group type is ibgp.";
                }
              }
            }
            leaf check-first-as {
              when "../type='ebgp'";
              type peer-cap-config-state;
              default "default";
              description
                "Check the first AS in the AS_Path of the update messages from EBGP peers.";
            }
            leaf memory-priority {
              type memory-priority;
              default "medium";
              description
                "Set a priority that determines the disconnection order of each BGP peer relationship in a peer group if memory overload occurs.";
            }
            leaf oscillation-dampening {
              when "../peer-establish-mode!='dynamic' and ../peer-establish-mode!='dynamic-ipv6'";
              type boolean;
              default "true";
              description
                "Enable/disable BGP to suppress the establishment of a specified peer group's peer relationships that flap continuously. By default, the capability is enabled.";
            }
            leaf peer-establish-mode {
              type peer-establish-mode;
              default "static";
              description
                "Specify mode in which a BGP peer is established.";
              ext:operation-exclude update|delete {
                description "The node cannot be modified, deleted when node is already configured.";
              }
            }
            leaf as-number-type {
              when "(../peer-establish-mode = 'dynamic' or ../peer-establish-mode = 'dynamic-ipv6') and ../../../../../ni:name='_public_'";
              type as-number-type;
              must ". = 'dynamic-neighbor' or (. = 'confederation' and /bgp:bgp/bgp:base-process/bgp:confederation/bgp:id and ../type = 'ebgp')";
              default "dynamic-neighbor";
              description
                "Specify the type of the AS number that is used to establish a BGP peer relationship dynamically. The value can be dynamic-neighbor or confederation.";
              ext:operation-exclude update|delete {
                description "The node cannot be modified, deleted when node is already configured.";
              }
            }
            leaf-list listen-as {
              when "(../peer-establish-mode = 'dynamic' or ../peer-establish-mode = 'dynamic-ipv6') and ../type = 'ebgp'";
              type as-number-validate;
              must "not(. = /bgp:bgp/bgp:base-process/bgp:as) and not(/ni:network-instance/ni:instances/ni:instance[ni:name='_public_']/bgp:bgp/bgp:base-process/bgp:peer-groups/bgp:peer-group[name = current()/../name]/bgp:as-number-type='confederation')";
              max-elements 6;
              description
                "Specify the peer AS from which a dynamic EBGP peer group listens for BGP connection requests.";
            }
            container listen-as-segments {
              when "(../peer-establish-mode = 'dynamic' or ../peer-establish-mode = 'dynamic-ipv6') and ../type = 'ebgp'";
              description
                "List of AS number ranges for listening.";
              list listen-as-segment {
                must "not(../../listen-as) and not(/ni:network-instance/ni:instances/ni:instance[ni:name='_public_']/bgp:bgp/bgp:base-process/bgp:peer-groups/bgp:peer-group[name = current()/../../name]/bgp:as-number-type='confederation')";
                key "begin-as end-as";
                max-elements 16;
                description
                  "Specify an AS number range from which a dynamic EBGP peer group listens for connection requests. The value of begin-as must be smaller than that of end-as. The value of As-Segment cannot contain the value of LocalAS or the value of fake-as. An AS number range cannot contain a confederation AS number, and any two AS number ranges cannot contain each other.";
                leaf begin-as {
                  type as-number-validate;
                  description
                    "Specify the start AS number in an AS range.";
                }
                leaf end-as {
                  type as-number-validate;
                  description
                    "Specify the end AS number in an AS range.";
                }
              }
            }
            container fake-as-parameter {
              description
                "Configure BGP fake-as parameters.";
              leaf fake-as {
                when "../../bgp:type='ebgp'";
                type bgp:as-number-validate;
                description
                  "Fake AS number that is specified for a local peer. By default, a peer uses the actual AS number of the local end.
                  An AS number can be in either two-byte format or four-byte format:
                  The two-byte format is X. X is an integer ranging from 1 to 65535.
                  The four-byte format is X.Y and X. When the format is X.Y, X and Y are both integers, with the value of X ranging from 1 to 65535, and the value of Y ranging from 0 to 65535; when the format is X, X is an integer, with the value of X ranging from 1 to 4294967295.";
              }
              leaf dual-as {
                when "../fake-as";
                type boolean;
                default "false";
                description
                  "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
              }
              leaf prepend-global-as {
                when "../fake-as";
                type boolean;
                default "false";
                description
                  "Enable/disable the function to add the global AS number to the Update packets to be advertised.";
              }
              leaf prepend-fake-as {
                when "../fake-as";
                type boolean;
                default "false";
                description
                  "Enable/disable the function to add the Fake AS number to received Update packets.";
              }
            }
            uses group-timer-para-type;
            uses group-bfd-parameter-type;
            container graceful-restart {
              when "../peer-establish-mode!='dynamic' and ../peer-establish-mode!='dynamic-ipv6'";
              description
                "Configure graceful restart.";
              uses group-graceful-restart-type;
              leaf peer-reset {
                type boolean;
                default "false";
                description
                  "Enable/disable resetting BGP peer graceful.";
              }
            }
            container local-graceful-restart {
              when "../peer-establish-mode = 'static'";
              description
                "Configure local graceful restart.";
              uses group-local-graceful-restart-type;
            }
            container graceful-shutdown {
              description
                "Configure graceful shutdown.";
              leaf enable {
                type empty;
                description
                  "Enable/disable graceful shutdown capability.";
              }
              choice attribute {
                when "enable";
                description
                  "Specify the graceful shutdown attribute.";
                case set-as-prepend {
                  description
                    "Set AS prepend.";
                  leaf as-prepend {
                    type uint8 {
                      range "1..6";
                    }
                    description
                      "Number of ASs to be added.";
                  }
                }
                case set-local-preference {
                  description
                    "Set local preference.";
                  leaf local-preference {
                    type uint32;
                    description
                      "The local preference of BGP routes.";
                  }
                }
              }
              leaf manual-activate {
                type empty;
                description
                  "Enable/disable graceful shutdown activation.";
              }
            }
            container ssl-policy {
              when "../../../../../ni:name='_public_' and ../peer-establish-mode='static'";
              description
                "Configure SSL policy for BGP group.";
              uses group-ssl-policy-grouping {
                refine role {
                  must "(../role='client' and ../../connect-mode != 'listen-only') or (../role='server' and ../../connect-mode != 'connect-only')";
                }
              }
            }
            container memory-resilience {
              description
                "Configure memory resiliency.";
               uses low-memory-exempt-grouping;
            }
            container members {
              config false;
              description
                "List of members in a peer group.";
              list member {
                key "peer-address";
                config false;
                description
                  "Statistics of member in a peer group.";
                leaf peer-address {
                  type inet:ip-address-no-zone;
                  config false;
                  description
                    "Specify the address of the peer joining the peer group.";
                }
              }
            }
            container role {
              when "../type = 'ebgp' and ../peer-establish-mode = 'static'";
              description
                "Configure BGP role for group.";
              leaf value {
                type bgp-role-type;
                description
                  "The BGP Role characterizes the relationship between the eBGP speakers forming a session.";
              }
            }
            container uninterrupted-dynamic-capability {
              when "../peer-establish-mode = 'static' and ../../../../../ni:name = '_public_'";
              description
                "Configure uninterrupted dynamic capability.";
              leaf multi-protocol {
                type empty;
                description
                  "Enable BGP to advertise multi-protocol dynamic capability to peers.";
              }
            }
            container afs {
              description
                "List of all peer groups that are enabled in a specified address family.";
              list af {
                key "type";
                description
                  "Configure peer group enabled in a specified address family.";
                leaf type {
                  type bgp:group-af-type;
                  must "../../../../../afs/af[type = current()]";
                  description
                    "Address family type of a BGP instance.";
                }
                container ipv4-unicast {
                  when "../type = 'ipv4uni'";
                  must "../../../../../../../l3vpn:afs/l3vpn:af[l3vpn:type='ipv4-unicast']";
                  description
                    "Configure IPv4 unicast options.";
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-type;
                    must "((../orf-mode='null' and ../orf-type='null') or (../orf-mode!='null' and ../orf-type!='null')) and ((../../../../../../../../ni:name!='_public_' and ../orf-type!='nonstandard-compatible') or ../../../../../../../../ni:name='_public_')";
                    default "null";
                    description
                      "ORF Type.";
                  }
                  leaf orf-mode {
                    type bgp:bgp-orf-mode-type;
                    must "(../orf-mode='null' and ../orf-type='null') or (../orf-mode!='null' and ../orf-type!='null')";
                    default "null";
                    description
                      "Configure an outbound route filtering (ORF) mode.";
                  }
                  leaf label-route-capability {
                    type boolean;
                    default "false";
                    description
                      "Enable/disable a device to exchange labeled routes.";
                  }
                  leaf check-tunnel-reachable {
                    when "../label-route-capability='true'";
                    type boolean;
                    default "false";
                    description
                      "Enable/disable tunnel reachability check.";
                  }
                  leaf check-withdraw-type {
                    when "../label-route-capability='true'";
                    type boolean;
                    default "true";
                    status obsolete;
                    description
                      "Enable/disable withdraw type check.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf static-route-nexthop-invariable {
                    when "../../../../../../../../ni:name='_public_' and ../nexthop-configure='invariable'";
                    type boolean;
                    default "false";
                    description
                      "Enable/disable BGP speaker does not change the next hop of an imported static route when advertising them to its peers.";
                  }
                  leaf unicast-route-nexthop-invariable {
                    when "../../../../../../../../ni:name='_public_' and ../nexthop-configure='invariable'";
                    type boolean;
                    default "false";
                    description
                      "Enable/disable BGP speaker does not change the next hop of an imported unicast route when advertising them to its peers.";
                  }
                  uses peer-policy-filter-type;
                  leaf origin-as-validation {
                    when "../advertise-ext-community='true' and ../../../../peer-establish-mode='static'";
                    type boolean;
                    default "false";
                    description
                      "Enable/disable the BGP peer origin validation.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    type add-path-cap-type;
                    default "null";
                    description
                      "Enable Add-Path route advertisement to a peer.";
                  }
                  uses ip-prefix-filter-type;
                  uses as-path-filter-type;
                  uses peer-group-acl-name-or-num-type;
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  uses rt-update-interval-type;
                  uses preferred-value-type;
                  leaf add-path-number {
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    when "../../../../bgp:type='ebgp'";
                    type peer-attr-enable-type;
                    default "disable";
                    description
                      "Enable/disable BGP to prevents the routes received from an EBGP peer from being broadcast to other peers with the same AS number.";
                  }
                  leaf exp-mode {
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_' and ../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf prefix-sid {
                    when "../../../../../../../../ni:name='_public_'";
                    type boolean;
                    default "false";
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        when "../prefix-sid='true'";
                        type empty;
                        description
                          "Advertise SRv6 locators.";
                      }
                    }
                  }
                  uses group-independent-peer-group-type;
                  uses load-balancing-type;
                  leaf advertise-community {
                    type boolean;
                    default "false";
                    description
                      "Enable/disable advertise the community attribute to a peer or a peer group.";
                  }
                  leaf advertise-ext-community {
                    type boolean;
                    default "false";
                    description
                      "Enable/disable advertise the extended community attribute to a peer or peer group.";
                  }
                  uses discard-ext-community-grouping;
                  uses advertise-large-community-group-type;
                  container option {
                    description
                      "Configure IPv4 unicast group common options.";
                    leaf export-origin-as-validation {
                      type peer-attr-enable-type;
                      default "disable";
                      description
                        "Enable/disable the function ebgp group advertising dependent roa validation, route is advtised roa reslut is valid.";
                    }
                    leaf include-not-found {
                      when "../export-origin-as-validation='enable'";
                      type boolean;
                      default "false";
                      description
                        "Enable/disable the include-not-found attribute of the ROA validation.";
                    }
                    leaf external {
                      when "../include-not-found='true'";
                      type boolean;
                      default "false";
                      description
                        "Enable/disable ROA export validation to advertise only external not found routes.";
                    }
                  }
                  uses ipv4-default-route-match-conditions-type;
                  uses route-limit-accept-type;
                  uses public-as-only-type;
                  uses group-public-as-only-import-type;
                  uses advertise-dependent-filter-group-type;
                  container entropy-label-parameter {
                    when "../../../../../../../../ni:name='_public_' and ../label-route-capability='true'";
                    description
                      "Configure information about entropy label parameter in a peer group.";
                    uses group-entropy-label-type;
                  }
                  container route-server {
                    description
                      "Configure the route server function on a device and specifies an EBGP peer as its client.";
                    leaf route-server-client {
                      when "../../../../../bgp:type='ebgp' and ../../../../../peer-establish-mode='static'";
                      type empty;
                      must "(not(/bgp:bgp/bgp:base-process/bgp:confederation/bgp:id) and (/bgp:bgp/bgp:base-process/bgp:confederation/bgp:nonstanded = 'false'))";
                      must "../../label-route-capability = 'false'";
                      must "not(../../prefix-sid) or ../../prefix-sid = 'false'";
                      description
                        "Enable/disable the route server function on a device and specifies an EBGP peer as its client.";
                    }
                    choice context-policy-type {
                      description
                        "Set the route-server-client context-policy or context-filter.";
                      case rtp-ref {
                        description
                          "Specify the filtering policy applied to the routes to be advertised to a peer client. By default, no such policy is specified.";
                        leaf policy-name {
                          when "../route-server-client";
                          type leafref {
                            path "/rtp:routing-policy/rtp:policy-definitions/rtp:policy-definition/rtp:name";
                          }
                          must "not(../../add-path-number) and (not(../../add-path-mode) or ../../add-path-mode='null')";
                          description
                            "Specify a route policy name.";
                        }
                      }
                      case xpl-ref {
                        description
                          "Configure a route-filter to filter the routes to be advertised to a peer client. By default, no route-filter is specified.";
                        leaf filter-name {
                          when "../route-server-client";
                          type leafref {
                            path "/xpl:xpl/xpl:route-filters/xpl:route-filter/xpl:name";
                          }
                          must "not(../../add-path-number) and (not(../../add-path-mode) or ../../add-path-mode='null')";
                          description
                            "Specify a route-filter name.";
                        }
                        leaf filter-parameter {
                          when "../filter-name";
                          type xpl:filter-parameter-type;
                          description
                            "Specify a route-filter parameter.";
                        }
                      }
                    }
                  }
                  container hierarchy-convergence {
                    when "../../../../../../../../ni:name='_public_'";
                    description
                      "Configure the current peer group's hierarchy convergence capability.";
                    uses group-hierarchy-convergence;
                  }
                  container link-bandwidth {
                    description
                      "Configure link bandwidth attribute.";
                    leaf advertise {
                      when "../../../../../bgp:type='ebgp'";
                      type peer-attr-enable-type;
                      default "disable";
                      description
                        "Enable/disable advertise the link bandwidth attribute to an EBGP peer.";
                    }
                    leaf transitive {
                      type peer-attr-enable-type;
                      default "disable";
                      description
                        "Enable/disable transitive the link bandwidth attribute.";
                    }
                    leaf generate {
                      when "../../../../../bgp:type='ebgp'";
                      type peer-attr-enable-type;
                      default "disable";
                      description
                        "Enable/disable generate the link bandwidth attribute to an EBGP peer.";
                    }
                    leaf aggregate {
                      type peer-attr-enable-type;
                      default "disable";
                      description
                        "Enable or disable the aggregated bandwidth extended community attribute.";
                    }
                    leaf aggregate-limit {
                      when "../bgp:aggregate='enable'";
                      type uint32 {
                        range "1..4294967295";
                      }
                      description
                        "Set the upper limit of the aggregated bandwidth community attribute values.";
                    }
                    leaf generate-all {
                      when "../bgp:generate='enable' and ../../../../../../../../../ni:name='_public_'";
                      type empty;
                      description "Enable or disable Link Bandwidth attribute generation for directly connected EBGP peer interfaces and single-hop EBGP peer interfaces.";
                    }
                  }
                  container add-path-policy {
                    when "../add-path-number";
                    description
                      "Configure peer group add-path route-policy or route-filter.";
                    uses add-path-policy-grouping;
                  }
                  container soo-reverse {
                    when "../../../../../../../../ni:name='_public_'";
                    description
                      "Configure soo reverse for public peer group.";
                    uses group-soo-reverse;
                  }
                  container traffic-statistics {
                    when "../../../../../../../../ni:name='_public_' and ../../../../bgp:type='ebgp' and ../../../../peer-establish-mode='static'";
                    description
                      "Configure downloading rib out to get traffic statistics.";
                    leaf rib-out {
                      type empty;
                      description
                        "Downloading rib out to get traffic statistics.";
                    }
                  }
                  container rpki {
                    description
                      "Configure IPv4 unicast group rpki.";
                    container aspa {
                      when "../../../../../bgp:type='ebgp'";
                      description
                        "Configure IPv4 unicast group aspa.";
                      leaf asra-extend-validation-export {
                        type empty;
                        description
                          "Configure the function ebgp group advertising dependent ASRA validation, route is advertised when ASRA result is valid.";
                      }
                      leaf asra-backward-validation-export {
                        when "../asra-extend-validation-export";
                        type boolean;
                        default "false";
                        description
                          "Enable/disable the function ebgp group advertising dependent ASRA backward validation.";
                      }
                      leaf include-not-found {
                        when "../asra-extend-validation-export";
                        type boolean;
                        default "false";
                        description
                          "Enable/disable the include-not-found attribute of the ASRA validation.";
                      }
                      leaf external {
                        when "../include-not-found='true'";
                        type boolean;
                        default "false";
                        description
                          "Enable/disable ASRA export validation to advertise only external not found routes.";
                      }
                    }
                  }
                }
                container ipv6-unicast {
                  when "../type = 'ipv6uni'";
                  must "../../../../../../../l3vpn:afs/l3vpn:af[l3vpn:type='ipv6-unicast']";
                  description
                    "Configure IPv6 unicast options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v6-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf label-route-capability {
                    type boolean;
                    default "false";
                    description
                      "Enable/disable a device to exchange labeled routes.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf static-route-nexthop-invariable {
                    when "../../../../../../../../ni:name='_public_' and ../nexthop-configure='invariable' and ../../../../peer-establish-mode!='dynamic'";
                    type boolean;
                    default "false";
                    description
                      "Enable/disable BGP speaker does not change the next hop of an imported static route when advertising them to its peers.";
                  }
                  leaf unicast-route-nexthop-invariable {
                    when "../../../../../../../../ni:name='_public_' and ../nexthop-configure='invariable'";
                    type boolean;
                    default "false";
                    description
                      "Enable/disable BGP speaker does not change the next hop of an imported unicast route when advertising them to its peers.";
                  }
                  uses peer-policy-filter-type;
                  leaf advertise-ext-community {
                    type boolean;
                    default "false";
                    description
                      "Enable/disable advertise the extended community attribute to a peer or peer group.";
                  }
                  leaf origin-as-validation {
                    when "../advertise-ext-community='true' and ../../../../peer-establish-mode='static'";
                    type boolean;
                    default "false";
                    description
                      "Enable/disable the BGP peer origin validation.";
                  }
                  uses discard-ext-community-grouping;
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'";
                    type add-path-cap-type;
                    default "null";
                    description
                      "Enable Add-Path route advertisement to a peer.";
                  }
                  uses ipv6-prefix-filter-type;
                  uses as-path-filter-type;
                  uses peer-group-acl6-name-or-num-type;
                  uses rt-update-interval-type;
                  uses preferred-value-type;
                  leaf add-path-number {
                    when "../../../../../../../../ni:name='_public_'";
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    when "../../../../bgp:type='ebgp'";
                    type peer-attr-enable-type;
                    default "disable";
                    description
                      "Enable/disable BGP to prevents the routes received from an EBGP peer from being broadcast to other peers with the same AS number.";
                  }
                  leaf advertise-best-external {
                    when "../../../../../../../../ni:name='_public_' and ../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'";
                    type boolean;
                    default "false";
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        when "../prefix-sid='true'";
                        type empty;
                        description
                          "Advertise SRv6 locators.";
                      }
                    }
                  }
                  uses advertise-large-community-group-type;
                  uses group-independent-peer-group-type;
                  container option {
                    description
                      "Configure IPv6 unicast group common options.";
                    leaf export-origin-as-validation {
                      type peer-attr-enable-type;
                      default "disable";
                      description
                        "Enable/disable the function ebgp group advertising dependent roa validation, route is advtised roa reslut is valid.";
                    }
                    leaf include-not-found {
                      when "../export-origin-as-validation='enable'";
                      type boolean;
                      default "false";
                      description
                        "Enable/disable the include-not-found attribute of the ROA validation.";
                    }
                    leaf external {
                      when "../include-not-found='true'";
                      type boolean;
                      default "false";
                      description
                        "Enable/disable ROA export validation to advertise only external not found routes.";
                    }
                    leaf label-route-capability-only {
                      when "../../../../../../../../../ni:name='_public_'";
                      type peer-attr-enable-type;
                      must ". = 'disable' or (. = 'enable' and ../../label-route-capability = 'false')";
                      default "disable";
                      description
                        "Enable/disable a device to only exchange labeled routes, and the open messages for labeled routes do not carry the IPv6 unicast route negotiation capability.";
                    }
                    leaf advertise-match-route-source {
                      when "../../../../../../../../../ni:name='_public_'";
                      type boolean;
                      default "false";
                      description
                        "Enable/disable the matching of the source address type of the route to be sent out by the peer group.";
                    }
                  }
                  uses ipv6-default-route-match-conditions-type;
                  uses route-limit-accept-type;
                  uses public-as-only-type;
                  uses group-public-as-only-import-type;
                  uses advertise-dependent-filter6-group-type;
                  container route-server {
                    description
                      "Configure the route server function on a device and specifies an EBGP peer as its client.";
                    leaf route-server-client {
                      when "../../../../../bgp:type='ebgp' and ../../../../../peer-establish-mode='static'";
                      type empty;
                      must "(not(/bgp:bgp/bgp:base-process/bgp:confederation/bgp:id) and (/bgp:bgp/bgp:base-process/bgp:confederation/bgp:nonstanded = 'false'))";
                      must "../../label-route-capability = 'false'";
                      must "not(../../prefix-sid) or ../../prefix-sid = 'false'";
                      description
                        "Enable/disable the route server function on a device and specifies an EBGP peer as its client.";
                    }
                    choice context-policy-type {
                      description
                        "Set the route-server-client context-policy or context-filter.";
                      case rtp-ref {
                        description
                          "Specify the filtering policy applied to the routes to be advertised to a peer client. By default, no such policy is specified.";
                        leaf policy-name {
                          when "../route-server-client";
                          type leafref {
                            path "/rtp:routing-policy/rtp:policy-definitions/rtp:policy-definition/rtp:name";
                          }
                          must "not(../../add-path-number) and (not(../../add-path-mode) or ../../add-path-mode='null')";
                          description
                            "Specify a route policy name.";
                        }
                      }
                      case xpl-ref {
                        description
                          "Configure a route-filter to filter the routes to be advertised to a peer client. By default, no route-filter is specified.";
                        leaf filter-name {
                          when "../route-server-client";
                          type leafref {
                            path "/xpl:xpl/xpl:route-filters/xpl:route-filter/xpl:name";
                          }
                          must "not(../../add-path-number) and (not(../../add-path-mode) or ../../add-path-mode='null')";
                          description
                            "Specify a route-filter name.";
                        }
                        leaf filter-parameter {
                          when "../filter-name";
                          type xpl:filter-parameter-type;
                          description
                            "Specify a route-filter parameter.";
                        }
                      }
                    }
                  }
                  container hierarchy-convergence {
                    when "../../../../../../../../ni:name='_public_'";
                    description
                      "Configure the current peer group's hierarchy convergence capability.";
                    uses group-hierarchy-convergence;
                  }
                  container link-bandwidth {
                    description
                      "Configure link bandwidth attribute.";
                    leaf advertise {
                      when "../../../../../bgp:type='ebgp'";
                      type peer-attr-enable-type;
                      default "disable";
                      description
                        "Enable/disable advertise the link bandwidth attribute to an EBGP peer.";
                    }
                    leaf transitive {
                      type peer-attr-enable-type;
                      default "disable";
                      description
                        "Enable/disable transitive the link bandwidth attribute.";
                    }
                    leaf generate {
                      when "../../../../../bgp:type='ebgp'";
                      type peer-attr-enable-type;
                      default "disable";
                      description
                        "Enable/disable generate the link bandwidth attribute to an EBGP peer.";
                    }
                    leaf aggregate {
                      type peer-attr-enable-type;
                      default "disable";
                      description
                        "Enable or disable the aggregated bandwidth extended community attribute.";
                    }
                    leaf aggregate-limit {
                      when "../bgp:aggregate='enable'";
                      type uint32 {
                        range "1..4294967295";
                      }
                      description
                        "Set the upper limit of the aggregated bandwidth community attribute values.";
                    }
                    leaf generate-all {
                      when "../bgp:generate='enable' and ../../../../../../../../../ni:name='_public_'";
                      type empty;
                      description "Enable or disable Link Bandwidth attribute generation for directly connected EBGP peer interfaces and single-hop EBGP peer interfaces.";
                    }
                  }
                  container add-path-policy {
                    when "../add-path-number";
                    description
                      "Configure peer group add-path route-policy or route-filter.";
                    uses add-path-policy-grouping;
                  }
                  container soo-reverse {
                    when "../../../../../../../../ni:name='_public_'";
                    description
                      "Configure soo reverse for public peer group.";
                    uses group-soo-reverse;
                  }
                  container rpki {
                    description
                      "Configure IPv6 unicast group rpki.";
                    container aspa {
                      when "../../../../../bgp:type='ebgp'";
                      description
                        "Configure IPv6 unicast group aspa.";
                      leaf asra-extend-validation-export {
                        type empty;
                        description
                          "Configure the function ebgp group advertising dependent ASRA validation, route is advertised when ASRA result is valid.";
                      }
                      leaf asra-backward-validation-export {
                        when "../asra-extend-validation-export";
                        type boolean;
                        default "false";
                        description
                          "Enable/disable the function ebgp group advertising dependent ASRA backward validation.";
                      }
                      leaf include-not-found {
                        when "../asra-extend-validation-export";
                        type boolean;
                        default "false";
                        description
                          "Enable/disable the include-not-found attribute of the ASRA validation.";
                      }
                      leaf external {
                        when "../include-not-found='true'";
                        type boolean;
                        default "false";
                        description
                          "Enable/disable ASRA export validation to advertise only external not found routes.";
                      }
                    }
                  }
                }
                container ipv4-vpn {
                  when "../type = 'ipv4vpn'";
                  description
                    "Configure IPv4 vpnv4 options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v4-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when "../export-policy or ../export-filter";
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    type add-path-cap-type;
                    default "null";
                    description
                      "Enable Add-Path route advertisement to a peer.";
                  }
                  uses ip-prefix-filter-type;
                  uses peer-ipv4-reoriginate-type;
                  uses as-path-filter-type;
                  uses peer-group-acl-name-or-num-type;
                  uses rt-update-interval-type;
                  uses preferred-value-type;
                  leaf add-path-number {
                    type uint8 {
                      range "2..64";
                    }
                    description
                      "Number of Add-Path routes that can be advertised to a peer.";
                  }
                  leaf upe {
                    type boolean;
                    default "false";
                    description
                      "Enable/disable the peer as an underlayer PE (UPE).";
                  }
                  leaf advertise-best-external {
                    when "../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-group-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    when "../../../../bgp:type='ebgp'";
                    type peer-attr-enable-type;
                    default "disable";
                    description
                      "Enable/disable BGP to prevents the routes received from an EBGP peer from being broadcast to other peers with the same AS number.";
                  }
                  uses group-independent-peer-group-type;
                  leaf origin-as-validation {
                    when "../../../../peer-establish-mode='static'";
                    type boolean;
                    default "false";
                    description
                      "Enable/disable the BGP peer origin validation.";
                  }
                  leaf high-priority {
                    type boolean;
                    default "false";
                    description
                       "Enable/disable vpn-router high priority.";
                  }
                  leaf prefix-sid {
                    type boolean;
                    default "false";
                    description
                      "Enable/disable a SID mode relay for group.";
                  }
                  leaf remote-nexthop {
                    when "../../../../bgp:type='ibgp'";
                    type boolean;
                    default "false";
                    description
                  	"Enable/disable the device to advertise the remote-nexthop attribute to an IBGP peer group.";
                  }
                  choice prefix-sid-packet {
                    description
                      "Prefix-sid packet method.";
                    case sid-type5 {
                      description
                        "Packet by type5.";
                      leaf sid-type5 {
                        when "../prefix-sid='true'";
                        type empty;
                        description
                          "Packet by type5.";
                      }
                      leaf advertise-srv6-locator {
                        when "../sid-type5";
                        type empty;
                        description
                          "Advertise SRv6 locators.";
                      }
                      leaf advertise-anycast-sid {
                        when "../sid-type5";
                        type empty;
                        description
                          "Advertise anycast SID.";
                      }
                    }
                  }
                  container default-route-originates {
                    description
                      "Configure advertised default VPNv4 routes.";
                    uses default-route-originate-type;
                  }
                  uses route-limit-type;
                  uses public-as-only-type;
                  uses group-public-as-only-import-type;
                }
                container ipv6-vpn {
                  when "../type = 'ipv6vpn'";
                  description
                    "Configure IPv6 vpn options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v6-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when "../export-policy or ../export-filter";
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    type add-path-cap-type;
                    default "null";
                    description
                      "Enable Add-Path route advertisement to a peer.";
                  }
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  leaf reoriginate-vpnv6-route-enable {
                    type boolean;
                    default "false";
                    description
                      "Enable/disable VPNv6 route regeneration and advertisement.";
                  }
                  uses as-path-filter-type;
                  uses peer-group-acl6-name-or-num-type;
                  uses rt-update-interval-type;
                  uses preferred-value-type;
                  leaf add-path-number {
                    type uint8 {
                      range "2..64";
                    }
                    description
                      "Number of Add-Path routes that can be advertised to a peer.";
                  }
                  leaf upe {
                    type boolean;
                    default "false";
                    description
                      "Enable/disable the peer as an underlayer PE (UPE).";
                  }
                  leaf advertise-best-external {
                    when "../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-group-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    when "../../../../bgp:type='ebgp'";
                    type peer-attr-enable-type;
                    default "disable";
                    description
                      "Enable/disable BGP to prevents the routes received from an EBGP peer from being broadcast to other peers with the same AS number.";
                  }
                  uses group-independent-peer-group-type;
                  leaf origin-as-validation {
                    when "../../../../peer-establish-mode='static'";
                    type boolean;
                    default "false";
                    description
                      "Enable/disable the BGP peer origin validation.";
                  }
                  leaf high-priority {
                    type boolean;
                    default "false";
                    description
                       "Enable/disable vpn-router high priority.";
                  }
                  leaf prefix-sid {
                    type boolean;
                    default "false";
                    description
                      "Enable/disable a SID mode relay for group.";
                  }
                  choice prefix-sid-packet {
                    description
                      "Prefix-sid packet method.";
                    case sid-type5 {
                      description
                        "Packet by type5.";
                      leaf advertise-srv6-locator {
                        when "../prefix-sid='true'";
                        type empty;
                        description
                          "Advertise SRv6 locators.";
                      }
                      leaf advertise-anycast-sid {
                        when "../prefix-sid='true'";
                        type empty;
                        description
                          "Advertise anycast SID.";
                      }
                    }
                  }
                  container default-route-originates {
                    description
                      "Configure advertised default VPNv6 routes.";
                    uses default-route-originate-type;
                  }
                  uses route-limit-type;
                  uses public-as-only-type;
                  uses group-public-as-only-import-type;
                }
                container ipv4-labeluni {
                  when "../type = 'ipv4labeluni'";
                  must "../../../../../../../l3vpn:afs/l3vpn:af[l3vpn:type='ipv4-unicast']";
                  description
                    "Configure IPv4 label unicast options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                      when "../../../../../../../../ni:name='_public_'";
                      type bgp:bgp-orf-type;
                      must "(../orf-mode='null' and ../orf-type='null') or (../orf-mode!='null' and ../orf-type!='null')";
                      default "null";
                      description
                        "ORF Type.";
                    }
                    leaf orf-mode {
                      when "../../../../../../../../ni:name='_public_'";
                      type bgp:bgp-orf-mode-type;
                      default "null";
                      description
                        "Configure an outbound route filtering (ORF) mode.";
                    }
                  leaf check-tunnel-reachable {
                    type boolean;
                    default "false";
                    description
                      "Enable/disable tunnel reachability check.";
                  }
                  uses peer-policy-filter-type;
                  leaf advertise-ext-community {
                    type boolean;
                    default "false";
                    description
                      "Enable/disable advertise the extended community attribute to a peer or peer group.";
                  }
                  uses discard-ext-community-grouping;
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    when "../../../../../../../../ni:name='_public_'";
                    type add-path-cap-type;
                    default "null";
                    description
                      "Enable Add-Path route advertisement to a peer.";
                  }
                  uses ip-prefix-filter-type;
                  uses as-path-filter-type;
                  uses peer-group-acl-name-or-num-type;
                  uses rt-update-interval-type;
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf exp-mode {
                    when "../../../../../../../../ni:name!='_public_'";
                    type exp-mode-type;
                    default "null";
                    description
                      "Specify the ASs in which a BGP label can inherit the QoS priority carried in the outer label of public tunnel in the Core AS and the ASs in which the priorities of BGP LSPs must be restored before the LSPs are advertised to a non-core AS.";
                  }
                  leaf add-path-number {
                    when "../../../../../../../../ni:name='_public_'";
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_' and ../../../../bgp:type='ibgp'";
                    type boolean;
                    must "../reflect-client='false' or ../advertise-best-external='false'";
                    must "../add-path-mode='null' or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  leaf prefix-sid {
                    when "../../../../../../../../ni:name='_public_'";
                    type boolean;
                    default "false";
                    description
                      "Enable/disable a device to exchange IPv4 prefix SIDs with a specified IPv6 peer group.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-group-type;
                  uses group-independent-peer-group-type;
                  uses route-limit-accept-type;
                  uses public-as-only-type;
                  uses group-public-as-only-import-type;
                  container entropy-label-parameter {
                    when "../../../../../../../../ni:name='_public_'";
                    description
                      "Configure information about entropy label parameter in a peer group.";
                    uses group-entropy-label-type;
                  }
                  container add-path-policy {
                    when "../add-path-number";
                    description
                      "Configure peer group add-path route-policy or route-filter.";
                    uses add-path-policy-grouping;
                  }
                }
                container ipv4-multicast {
                  when "../type='ipv4multi'";
                  must "../../../../../../../l3vpn:afs/l3vpn:af[l3vpn:type='ipv4-unicast']";
                  description
                    "Configure IPv4 multicast options.";
                  uses default-route-advertise-type;
                  uses ip-prefix-filter-type;
                  uses as-path-filter-type;
                  uses peer-group-acl-name-or-num-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'";
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-policy-filter-type;
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-group-type;
                  uses rt-update-interval-type;
                  uses bgp:preferred-value-type;
                  uses group-independent-peer-group-type;
                  uses route-limit-type;
                  uses public-as-only-type;
                  uses group-public-as-only-import-type;
                }
              }
            }
          }
        }
        container peers {
          description
            "List of BGP peers.";
          list peer {
            key "address";
            description
              "Configure a single BGP peer.";
            leaf address {
              type inet:ip-address-no-zone;
              description
                "Connection address of a peer, which can be an IPv4 or IPv6 address.";
            }
            leaf remote-as {
              type as-number-validate;
              mandatory true;
              description
                "AS number of a peer, which must be selected or group name when creating, and which can be in either two-byte format or four-byte format:
                 The two-byte format is X. X is an integer ranging from 1 to 65535.
                 The four-byte format is X.Y and X. When the format is X.Y, X and Y are both integers, with the value of X ranging from 1 to 65535, and the value of Y ranging from 0 to 65535; when the format is X, X is an integer, with the value of X ranging from 1 to 4294967295.
                 The object cannot be modified.";
              ext:operation-exclude update {
                description "The node cannot be modified, when node is already configured.";
              }
            }
            leaf group-name {
              type leafref {
                path "../../../peer-groups/peer-group/name";
              }
              must "../../../peer-groups/peer-group[name = current()]/peer-establish-mode = 'static'";
              description
                "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
              ext:operation-exclude update {
                description "The node cannot be modified, when the peer already belongs to a peer-group.";
              }
            }
            uses peer-local-if-type;
            uses authentication-attr-type;
            leaf tcp-ao-disable {
              type empty;
              description
                "Disable the TCP-AO authentication for establishing the TCP connection between BGP peers.";
            }
            leaf tcp-ao-name {
              when "not(../tcp-ao-disable)";
              type leafref {
                path "/socket:socket/socket:tcp-aos/socket:tcp-ao/socket:name";
              }
              must "not(../password-type!='null' or ../key-chain-name)";
              must "/socket:socket/socket:tcp-aos/socket:tcp-ao[socket:name=current()]/socket:accept-mismatch='false'";
              description
                "Specify TCP-AO authentication for establishing the TCP connection between BGP peers.";
            }
            leaf description {
              type string {
                length "1..255";
                pattern '([^?]*)';
              }
              description
                "Description of a peer, which can be letters or digits. The description is a string, spaces supported. By default, no description is configured for a peer.";
            }
            leaf ebgp-max-hop {
              type uint32 {
                range "1..255";
              }
              must "not(../valid-ttl-hops) or (../valid-ttl-hops>=1 and ../valid-ttl-hops<=255 and ../ebgp-max-hop=1)";
              description
                "Maximum number of hops in an indirect EBGP connection. By default, EBGP connections can be established only between directly connected peers. The function must be configured on both ends. By default, value is determined by the neighbor type, the default value of EBGP is 1 and the default value of IBGP is 0.";
              ext:dynamic-default;
            }
            uses peer-tracking-type;
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf valid-ttl-hops {
              type uint16 {
                range "1..255";
              }
              must "not(../ebgp-max-hop and ../ebgp-max-hop>1)";
              description
                "Enable GTSM on a peer or peer group. The valid-TTL-Value parameter is used to specify the number of TTL hops to be detected. If the value is configured as hops, the valid TTL range of the detected packet is [255-hops+1, 255].";
            }
            leaf connect-mode {
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              type boolean;
              default "false";
              description
                "Enable/disable path mtu auto discovery.";
            }
            leaf local-ifnet-disable {
              type boolean;
              description
                "Enable/disable MPLS local IFNET tunnel creation on a BGP IPv4 peer. By default, MPLS local IFNET tunnels can be created on an EBGP peer,but such tunnels cannot be created on an IBGP peer.";
              ext:dynamic-default;
            }
            leaf check-first-as {
              type peer-cap-config-state;
              default "default";
              description
                "Check the first AS in the AS_Path of the update messages from EBGP peers.";
            }
            leaf egress-engineer {
              when "../../../../../ni:name='_public_'";
              type epe-state;
              default "default";
              description
                "BGP Egress Peer Engineering (BGP-EPE) is enable or disable. The default value is default (The function is disable, If the neighbour joins the group, the function is Inheritance group).";
            }
            leaf tcp-mss {
              type uint16 {
                range "176..4096";
              }
              description
                "Maximum TCP MSS value used for TCP connection establishment for a peer.";
            }
            leaf memory-priority {
              type peer-memory-priority;
              default "default";
              description
                "Set a priority that determines the disconnection order of a BGP peer relationship if memory overload occurs.";
            }
            leaf memory-priority-capability {
              type memory-priority;
              config false;
              description
                "Priority that is used to determine the disconnection order of a BGP peer relationship if memory overload occurs.";
            }
            leaf extended-open-message {
              when "../../../../../ni:name='_public_'";
              type peer-attr-enable-type;
              description
              "Enable the capability of advertising BGP Open messages with extended optional parameters length.";
            }
            leaf extended-message {
              type peer-ext-msg-enable-type;
              must "contains(../address, ':')";
              description
              "Enable the capability of advertising BGP update extended messages.";
            }
            leaf oscillation-dampening {
              type peer-attr-enable-type;
              description
                "Enable/disable BGP to suppress the establishment of a specified peer relationship that flaps continuously. By default, the capability is enabled.";
            }
            uses rely-state-interface-grouping;
            container effect-state {
              config false;
              description
                "Operational state of a BGP peer. It uses the peer-specific configuration or inherits the configuration of its peer group.";
              leaf oscillation-dampening {
                type boolean;
                description
                  "Whether the capability of suppressing the establishment of a specified peer relationship that flaps continuously is enabled on the BGP peer.";
              }
            }
            container fake-as-parameter {
              description
                "Configure BGP fake-as parameters.";
              uses fake-as-type;
            }
            uses peer-timer-para-type;
            uses peer-bfd-parameter-type {
              refine bfd-parameter/track-session-name {
                must "(/bfd:bfd/bfd:sessions/bfd:session[bfd:name=current()]/bfd:destination-address-static-unicast-ipv4=../../address and /bfd:bfd/bfd:sessions/bfd:session[bfd:name=current()]/bfd:vrf-name-static-unicast-ipv4=../../../../../../ni:name and /bfd:bfd/bfd:sessions/bfd:session[bfd:name=current()]/bfd:is-group-static-unicast-ipv4='true') or (/bfd:bfd/bfd:sessions/bfd:session[bfd:name=current()]/bfd:destination-address-static-ipv6=../../address and /bfd:bfd/bfd:sessions/bfd:session[bfd:name=current()]/bfd:vrf-name-static-ipv6=../../../../../../ni:name and /bfd:bfd/bfd:sessions/bfd:session[bfd:name=current()]/bfd:is-group-static-ipv6='true')";
              }
            }
            uses peer-bfd-parameter-state-grouping;
            container egress-engineer-parameter {
              when "../egress-engineer='enable'";
              description
                "Configure BGP peer egress engineering information.";
              leaf static-label {
                type uint32 {
                  range "16..1048575";
                }
                description
                  "The static label for BGP EPE. The value range and default value are controlled by the PAF.";
              }
              leaf label-pop {
                when "../static-label";
                type boolean;
                must "not(../relate-bfd='true' and ../label-pop='true')";
                default "false";
                description
                  "Enable/disable the BGP-EPE label popping function.";
              }
              leaf relate-bfd {
                type boolean;
                must "not(../relate-bfd='true' and ../label-pop='true')";
              default "false";
                description
                  "Enable/disable association between the BGP-EPE label and BFD status.";
              }
              leaf peer-set-name {
                type leafref {
                path "../../../../bgp:egress-engineer-peer-sets/bgp:egress-engineer-peer-set/bgp:peer-set-name";
                }
                description
                  "Add peer to peer set.";
              }
            }
            container graceful-restart {
              description
                "Configure graceful restart.";
              uses peer-graceful-restart-type;
              leaf peer-reset {
                type peer-comm-config-type;
                default "default";
                description
                  "Enable/disable resetting BGP peer graceful.";
              }
              leaf effect-peer-reset {
                type boolean;
                config false;
                description
                  "Whether to enable/disable resetting BGP peer graceful.";
              }
            }
            container local-graceful-restart {
              description
                "Configure local graceful restart.";
              uses peer-local-graceful-restart-type;
            }
            container graceful-shutdown {
              description
                "Configure graceful shutdown.";
              leaf enable {
                type peer-attr-enable-type;
                description
                  "Enable/disable graceful shutdown capability.";
              }
              choice attribute {
                when "enable='enable'";
                description
                  "Specify the graceful shutdown attribute.";
                case set-as-prepend {
                  description
                    "Set AS prepend.";
                  leaf as-prepend {
                    type uint8 {
                      range "1..6";
                    }
                    description
                      "Number of ASs to be added.";
                  }
                }
                case set-local-preference {
                  description
                    "Set local preference.";
                  leaf local-preference {
                    type uint32;
                    description
                      "The local preference of BGP routes.";
                  }
                }
              }
              leaf manual-activate {
                type peer-attr-enable-type;
                description
                  "Enable/disable graceful shutdown activation for a peer.";
              }
            }
            container ssl-policy {
              when "../../../../../ni:name='_public_'";
              description
                "Configure SSL policy for BGP peer.";
              uses peer-ssl-policy-grouping {
                refine role {
                  must "(.='client' and ../../connect-mode != 'listen-only') or (.='server' and ../../connect-mode != 'connect-only') or (.= 'disable')";
                }
                refine server-certificate {
                  must "(../role = 'server') or (../role = 'disable') or (../role = 'client' and ../server-certificate != 'enable') or (not(../role) and not(../../bgp:group-name)) or (not(../role) and ../../bgp:group-name and  (../../../../bgp:peer-groups/bgp:peer-group[bgp:name=current()/../../bgp:group-name]/bgp:ssl-policy/bgp:role = 'server' or not(../../../../bgp:peer-groups/bgp:peer-group[bgp:name=current()/../../bgp:group-name]/bgp:ssl-policy/bgp:role))) or (not(../role) and ../../bgp:group-name and  ../../../../bgp:peer-groups/bgp:peer-group[bgp:name=current()/../../bgp:group-name]/bgp:ssl-policy/bgp:role = 'client' and ../server-certificate != 'enable')";
                }
              }
            }
            uses peer-memory-resilience-grouping;
            container role {
              description
                "Configure BGP role for peer.";
              leaf enable {
                type peer-attr-enable-type;
                description
                  "Enable/disable BGP role for peer.";
              }
              leaf value {
                when "../enable = 'enable'";
                type bgp-role-type;
                mandatory true;
                description
                  "The BGP Role characterizes the relationship between the eBGP speakers forming a session.";
              }
            }
            container uninterrupted-dynamic-capability {
              when "../../../../../ni:name='_public_'";
              description
                "Configure uninterrupted dynamic capability.";
              leaf multi-protocol {
                type peer-attr-enable-type;
                description
                  "Enable/disable BGP to advertise multi-protocol dynamic capability to peers.";
              }
            }
            container afs {
              description
                "List of peers in a specified address family.";
              list af {
                key "type";
                description
                  "Configure peer in a specified address family.";
                leaf type {
                  type bgp:af-type;
                  must "../../../../../afs/af[type = current()]";
                  description
                    "Specify the address family type to set the peer enable.";
                }
                container ipv4-unicast {
                  when "../type='ipv4uni'";
                  must "../../../../../../../l3vpn:afs/l3vpn:af[l3vpn:type='ipv4-unicast']";
                  description
                    "Configure IPv4 unicast options.";
                  leaf group-name {
                    type leafref {
                      path "../../../../../../peer-groups/peer-group/name";
                    }
                    must "../../../../../../peer-groups/peer-group[name = current()]/afs/af[type = 'ipv4uni']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-type;
                    must "((../orf-mode='null' and ../orf-type='null') or (../orf-mode!='null' and ../orf-type!='null')) and ((../../../../../../../../ni:name!='_public_' and ../orf-type!='nonstandard-compatible') or ../../../../../../../../ni:name='_public_')";
                    default "null";
                    description
                      "ORF Type.";
                  }
                  leaf orf-mode {
                    type bgp:bgp-orf-mode-type;
                    must "(../orf-mode='null' and ../orf-type='null') or (../orf-mode!='null' and ../orf-type!='null')";
                    default "null";
                    description
                      "Configure an outbound route filtering (ORF) mode.";
                  }
                  leaf label-route-capability {
                    type boolean;
                    default "false";
                    description
                      "Enable/disable a device to exchange labeled routes.";
                  }
                  leaf check-tunnel-reachable {
                    when "../label-route-capability='true'";
                    type boolean;
                    default "false";
                    description
                      "Enable/disable tunnel reachability check.";
                  }
                  leaf check-withdraw-type {
                    when "../label-route-capability='true'";
                    type boolean;
                    default "true";
                    status obsolete;
                    description
                      "Enable/disable withdraw type check.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf static-route-nexthop-invariable {
                    when "../../../../../../../../ni:name='_public_' and ../nexthop-configure='invariable' and contains(../../../../address,'.')";
                    type boolean;
                    default "false";
                    description
                      "Enable/disable BGP speaker does not change the next hop of an imported static route when advertising them to its peers.";
                  }
                  leaf unicast-route-nexthop-invariable {
                    when "../../../../../../../../ni:name='_public_' and ../nexthop-configure='invariable' and contains(../../../../address,'.')";
                    type boolean;
                    default "false";
                    description
                      "Enable/disable BGP speaker does not change the next hop of an imported unicast route when advertising them to its peers.";
                  }
                  uses peer-policy-filter-type;
                  leaf origin-as-validation {
                    when "../advertise-ext-community='true'";
                    type boolean;
                    default "false";
                    description
                      "Enable/disable the BGP peer origin validation.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    type add-path-cap-type;
                    default "null";
                    description
                      "Enable add-path route advertisement to a peer.";
                  }
                  uses ip-prefix-filter-type;
                  uses as-path-filter-type;
                  uses peer-group-acl-name-or-num-type;
                  uses rt-update-interval-type;
                  uses preferred-value-type;
                  leaf add-path-number {
                    type uint8 {
                      range "2..64";
                    }
                    description
                      "Number of add-path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    type peer-attr-enable-type;
                    description
                      "Enable/disable BGP to prevents the routes received from an EBGP peer from being broadcast to other peers with the same AS number.";
                  }
                  leaf exp-mode {
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf prefix-sid {
                    when "../../../../../../../../ni:name='_public_'";
                    type bgp:peer-comm-config-type;
                    default "default";
                    description
                  	"Enable/disable a device to exchange IPv4 prefix SIDs with a specified IPv6 peer.";
                  }
                  leaf prefix-sid-state {
                    when "../../../../../../../../ni:name='_public_'";
                    type boolean;
                    default "false";
                    config false;
                    description
                  	"Whether the prefix-sid to a peer is enabled.";
                  }
                  choice prefix-sid-packet {
                    description
                      "Prefix-sid packet method.";
                    case sid-type5 {
                      description
                        "Packet by type5.";
                      leaf advertise-srv6-locator {
                        when "../prefix-sid='enable'";
                        type empty;
                        must "contains(../../../../bgp:address, ':')";
                        description
                          "Advertise SRv6 locators.";
                      }
                    }
                  }
                  container effect-state {
                    config false;
                    description
                      "Operational state of peer.";
                    leaf advertise-srv6-locator {
                      type boolean;
                      description
                        "Whether to advertise SRv6 locators on the BGP peer.";
                    }
                  }
                  uses load-balancing-type;
                  leaf advertise-community {
                    type boolean;
                    default "false";
                    description
                      "Enable/disable advertise the community attribute to a peer or a peer group.";
                  }
                  leaf advertise-ext-community {
                    type boolean;
                    default "false";
                    description
                      "Enable/disable advertise the extended community attribute to a peer or peer group.";
                  }
                  uses discard-ext-community-grouping;
                  uses advertise-large-community-type;
                  uses peer-independent-peer-group-type;
                  leaf rpd-policy-export {
                    when "../../../../../../../../ni:name='_public_'";
                    type bgp:peer-enable-config-type;
                    default "default";
                    description
                  	"Enable/disable RPD export policy.";
                  }
                  container option {
                    description
                      "Configure IPv4 unicast peer common options.";
                    leaf export-origin-as-validation {
                      type peer-attr-enable-type;
                      description
                        "Enable/disable the function ebgp peer advertising dependent roa validation, route is advtised roa reslut is valid.";
                    }
                    leaf include-not-found {
                      when "../export-origin-as-validation='enable'";
                      type boolean;
                      default "false";
                      description
                        "Enable/disable the include-not-found attribute of the ROA validation.";
                    }
                    leaf external {
                      when "../include-not-found='true'";
                      type boolean;
                      default "false";
                      description
                        "Enable/disable ROA export validation to advertise only external not found routes.";
                    }
                  }
                  uses ipv4-default-route-match-conditions-type;
                  uses route-limit-accept-type;
                  uses public-as-only-type;
                  uses peer-public-as-only-import-type;
                  container entropy-label-parameter {
                    when "../../../../../../../../ni:name='_public_' and ../label-route-capability='true'";
                    description
                      "Configure information about entropy label parameter configuration in a peer.";
                    uses peer-entropy-label-type;
                  }
                  uses path-attr-map-type;
                  uses advertise-dependent-filter-type;
                  container route-server {
                    description
                      "Configure the route server function on a device and specifies an EBGP peer as its client.";
                    leaf route-server-client {
                      type peer-attr-enable-type;
                      must "(. = 'disable') or (not(/bgp:bgp/bgp:base-process/bgp:confederation/bgp:id) and (/bgp:bgp/bgp:base-process/bgp:confederation/bgp:nonstanded = 'false'))";
                      must "(. = 'disable') or (../../label-route-capability = 'false')";
                      description
                        "Enable/disable the route server function on a device and specifies an EBGP peer as its client.";
                    }
                    choice context-policy-type {
                      description
                        "Set the route-server-client context-policy or context-filter.";
                      case rtp-ref {
                        description
                          "Specify the filtering policy applied to the routes to be advertised to a peer client. By default, no such policy is specified.";
                        leaf policy-name {
                          when "../route-server-client='enable'";
                          type leafref {
                            path "/rtp:routing-policy/rtp:policy-definitions/rtp:policy-definition/rtp:name";
                          }
                          must "not(../../add-path-number) and (not(../../add-path-mode) or ../../add-path-mode='null')";
                          description
                            "Specify a route policy name.";
                        }
                      }
                      case xpl-ref {
                        description
                          "Configure a route-filter to filter the routes to be advertised to a peer client. By default, no route-filter is specified.";
                        leaf filter-name {
                          when "../route-server-client='enable'";
                          type leafref {
                            path "/xpl:xpl/xpl:route-filters/xpl:route-filter/xpl:name";
                          }
                          must "not(../../add-path-number) and (not(../../add-path-mode) or ../../add-path-mode='null')";
                          description
                            "Specify a route-filter name.";
                        }
                        leaf filter-parameter {
                          when "../filter-name";
                          type xpl:filter-parameter-type;
                          description
                            "Specify a route-filter parameter.";
                        }
                      }
                    }
                  }
                  container hierarchy-convergence {
                    when "../../../../../../../../ni:name='_public_'";
                    description
                      "Configure the current peer's hierarchy convergence capability.";
                    uses peer-hierarchy-convergence;
                  }
                  container link-bandwidth {
                    description
                      "Configure peer link bandwidth attribute.";
                    uses peer-link-bandwidth-type;
                    leaf generate-all {
                      when "../bgp:generate='enable' and ../../../../../../../../../ni:name='_public_'";
                      type empty;
                      must "contains(../../../../../address,'.')";
                      description "Enable or disable Link Bandwidth attribute generation for directly connected EBGP peer interfaces and single-hop EBGP peer interfaces.";
                    }
                  }
                  container add-path-policy {
                    when "../add-path-number";
                    description
                      "Configure peer add-path route-policy or route-filter. This configuration is applicable between IBGP peers only.";
                    uses add-path-policy-grouping;
                  }
                  container soo-reverse {
                    when "../../../../../../../../ni:name='_public_'";
                    description
                      "Configure soo reverse for public peer.";
                    leaf enable {
                      type peer-attr-enable-type;
                      must "contains(../../../../../address,'.')";
                      description
                        "Enable/disable soo reverse for peer.";
                    }
                    leaf value {
                      when "../enable ='enable'";
                      type string {
                        length "3..21";
                      }
                      mandatory true;
                      description
                        "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.";
                    }
                  }
                  container traffic-statistics {
                    when "../../../../../../../../ni:name='_public_'";
                    description
                      "Configure downloading rib out to get traffic statistics for public EBGP peer.";
                    leaf rib-out {
                      type peer-attr-enable-type;
                      must "contains(../../../../../address,'.')";
                      description
                        "Enable/disable downloading rib out to get traffic statistics for public EBGP peer.";
                    }
                  }
                  container rpki {
                    description
                      "Configure IPv4 unicast peer rpki.";
                    container aspa {
                      description
                        "Configure IPv4 unicast peer aspa.";
                      leaf asra-extend-validation-export {
                        type peer-attr-enable-type;
                        description
                          "Enable/disable the function ebgp peer advertising dependent ASRA validation, route is advertised when ASRA result is valid.";
                      }
                      leaf asra-backward-validation-export {
                        when "../asra-extend-validation-export='enable'";
                        type boolean;
                        default "false";
                        description
                          "Enable/disable the function ebgp peer advertising dependent ASRA backward validation.";
                      }
                      leaf include-not-found {
                        when "../asra-extend-validation-export='enable'";
                        type boolean;
                        default "false";
                        description
                          "Enable/disable the include-not-found attribute of the ASRA validation.";
                      }
                      leaf external {
                        when "../include-not-found='true'";
                        type boolean;
                        default "false";
                        description
                          "Enable/disable ASRA export validation to advertise only external not found routes.";
                      }
                    }
                  }
                }
                container ipv6-unicast {
                  when "../type = 'ipv6uni'";
                  must "../../../../../../../l3vpn:afs/l3vpn:af[l3vpn:type='ipv6-unicast']";
                  description
                    "Configure IPv6 unicast options.";
                  leaf group-name {
                    type leafref {
                      path "../../../../../../peer-groups/peer-group/name";
                    }
                    must "../../../../../../peer-groups/peer-group[name = current()]/afs/af[type = 'ipv6uni']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v6-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf label-route-capability {
                    type boolean;
                    default "false";
                    description
                      "Enable/disable a device to exchange labeled routes.";
                  }
                  leaf nexthop-configure {
                    type nexthop-configuration-type;
                    must "(not(contains(../../../../address,':')) and ../nexthop-configure='local') or contains(../../../../address,':')";
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf static-route-nexthop-invariable {
                    when "../../../../../../../../ni:name='_public_' and ../nexthop-configure='invariable'";
                    type boolean;
                    default "false";
                    description
                      "Enable/disable BGP speaker does not change the next hop of an imported static route when advertising them to its peers.";
                  }
                  leaf unicast-route-nexthop-invariable {
                    when "../../../../../../../../ni:name='_public_' and ../nexthop-configure='invariable'";
                    type boolean;
                    default "false";
                    description
                      "Enable/disable BGP speaker does not change the next hop of an imported unicast route when advertising them to its peers.";
                  }
                  uses peer-policy-filter-type;
                  leaf advertise-ext-community {
                    type boolean;
                    default "false";
                    description
                      "Enable/disable advertise the extended community attribute to a peer or peer group.";
                  }
                  leaf origin-as-validation {
                    when "../advertise-ext-community='true'";
                    type boolean;
                    default "false";
                    description
                      "Enable/disable the BGP peer origin validation.";
                  }
                  uses discard-ext-community-grouping;
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'";
                    type add-path-cap-type;
                    default "null";
                    description
                      "Enable Add-Path route advertisement to a peer.";
                  }
                  uses ipv6-prefix-filter-type;
                  uses as-path-filter-type;
                  uses peer-group-acl6-name-or-num-type;
                  uses rt-update-interval-type;
                  uses preferred-value-type;
                  leaf add-path-number {
                    when "../../../../../../../../ni:name='_public_'";
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    type peer-attr-enable-type;
                    description
                      "Enable/disable BGP to prevents the routes received from an EBGP peer from being broadcast to other peers with the same AS number.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf tunnel-policy {
                    when "../../../../../../../../ni:name='_public_'";
                    type leafref {
                      path "/tnlm:tunnel-management/tnlm:tunnel-policys/tnlm:tunnel-policy/tnlm:name";
                    }
                    description
                      "Apply a tunnel policy for a 6PE peer. By default, no tunnel policy is configured.";
                  }
                  leaf prefix-sid {
                    when "../../../../../../../../ni:name='_public_'";
                    type bgp:peer-comm-config-type;
                    must "(contains(../../../../address,'.') and ../prefix-sid='default') or contains(../../../../address,':')";
                    default "default";
                    description
                  	"Enable/disable a device to exchange prefix SIDs with a specified IPv6 peer.";
                  }
                  leaf prefix-sid-state {
                    when "../../../../../../../../ni:name='_public_'";
                    type boolean;
                    default "false";
                    config false;
                    description
                  	"Whether the prefix-sid to a peer is enabled.";
                  }
                  choice prefix-sid-packet {
                    description
                      "Prefix-sid packet method.";
                    case sid-type5 {
                      description
                        "Packet by type5.";
                      leaf advertise-srv6-locator {
                        when "../prefix-sid='enable'";
                        type empty;
                        description
                          "Advertise SRv6 locators.";
                      }
                    }
                  }
                  container effect-state {
                    config false;
                    description
                      "Operational state of peer.";
                    leaf advertise-srv6-locator {
                      type boolean;
                      description
                        "Whether to advertise SRv6 locators on the BGP peer.";
                    }
                  }
                  uses advertise-large-community-type;
                  uses peer-independent-peer-group-type;
                  container option {
                    description
                      "Configure IPv6 unicast peer common options.";
                    leaf export-origin-as-validation {
                      type peer-attr-enable-type;
                      description
                        "Enable/disable the function ebgp peer advertising dependent roa validation, route is advtised roa reslut is valid.";
                    }
                    leaf include-not-found {
                      when "../export-origin-as-validation='enable'";
                      type boolean;
                      default "false";
                      description
                        "Enable/disable the include-not-found attribute of the ROA validation.";
                    }
                    leaf external {
                      when "../include-not-found='true'";
                      type boolean;
                      default "false";
                      description
                        "Enable/disable ROA export validation to advertise only external not found routes.";
                    }
                    leaf label-route-capability-only {
                      type peer-attr-enable-type;
                      must "(. = 'disable') or (../../label-route-capability = 'false')";
                      description
                        "Enable/disable a device to only exchange labeled routes, and the Open messages for labeled routes do not carry the IPv6 unicast route negotiation capability.";
                    }
                    leaf advertise-match-route-source {
                      when "../../../../../../../../../ni:name='_public_'";
                      type peer-attr-enable-type;
                      description
                        "Enable/disable the matching of the source address type of the route to be sent out by the peer group.";
                    }
                  }
                  uses ipv6-default-route-match-conditions-type;
                  uses route-limit-accept-type;
                  uses public-as-only-type;
                  uses peer-public-as-only-import-type;
                  uses path-attr-map-type;
                  uses advertise-dependent-filter6-type;
                  container route-server {
                    description
                      "Configure the route server function on a device and specifies an EBGP peer as its client.";
                    leaf route-server-client {
                      type peer-attr-enable-type;
                      must "(. = 'disable') or (not(/bgp:bgp/bgp:base-process/bgp:confederation/bgp:id) and (/bgp:bgp/bgp:base-process/bgp:confederation/bgp:nonstanded = 'false'))";
                      must "(. = 'disable') or (../../label-route-capability = 'false')";
                      must "not(../../prefix-sid) or ../../prefix-sid = 'default'";
                      description
                        "Enable/disable the route server function on a device and specifies an EBGP peer as its client.";
                    }
                    choice context-policy-type {
                      description
                        "Set the route-server-client context-policy or context-filter.";
                      case rtp-ref {
                        description
                          "Specify the filtering policy applied to the routes to be advertised to a peer client. By default, no such policy is specified.";
                        leaf policy-name {
                          when "../route-server-client='enable'";
                          type leafref {
                            path "/rtp:routing-policy/rtp:policy-definitions/rtp:policy-definition/rtp:name";
                          }
                          must "not(../../add-path-number) and (not(../../add-path-mode) or ../../add-path-mode='null')";
                          description
                            "Specify a route policy name.";
                        }
                      }
                      case xpl-ref {
                        description
                          "Configure a route-filter to filter the routes to be advertised to a peer client. By default, no route-filter is specified.";
                        leaf filter-name {
                          when "../route-server-client='enable'";
                          type leafref {
                            path "/xpl:xpl/xpl:route-filters/xpl:route-filter/xpl:name";
                          }
                          must "not(../../add-path-number) and (not(../../add-path-mode) or ../../add-path-mode='null')";
                          description
                            "Specify a route-filter name.";
                        }
                        leaf filter-parameter {
                          when "../filter-name";
                          type xpl:filter-parameter-type;
                          description
                            "Specify a route-filter parameter.";
                        }
                      }
                    }
                  }
                  container hierarchy-convergence {
                    when "../../../../../../../../ni:name='_public_'";
                    description
                      "Configure the current peer's hierarchy convergence capability.";
                    uses peer-hierarchy-convergence;
                  }
                  container link-bandwidth {
                    description
                      "Configure peer link bandwidth attribute.";
                    uses peer-link-bandwidth-type;
                    leaf generate-all {
                      when "../bgp:generate='enable' and ../../../../../../../../../ni:name='_public_'";
                      type empty;
                      must "contains(../../../../../address,':')";
                      description "Enable or disable Link Bandwidth attribute generation for directly connected EBGP peer interfaces and single-hop EBGP peer interfaces.";
                    }
                  }
                  container add-path-policy {
                    when "../add-path-number";
                    description
                      "Configure peer add-path route-policy or route-filter. This configuration is applicable between IBGP peers only.";
                    uses add-path-policy-grouping;
                  }
                  container soo-reverse {
                    when "../../../../../../../../ni:name='_public_'";
                    description
                      "Configure soo reverse for public peer.";
                    leaf enable {
                      type peer-attr-enable-type;
                      must "contains(../../../../../address,':')";
                      description
                        "Enable/disable soo reverse for peer.";
                    }
                    leaf value {
                      when "../enable ='enable'";
                      type string {
                        length "3..21";
                      }
                      mandatory true;
                      description
                        "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.";
                    }
                  }
                  container rpki {
                    description
                      "Configure IPv6 unicast peer rpki.";
                    container aspa {
                      description
                        "Configure IPv6 unicast peer aspa.";
                      leaf asra-extend-validation-export {
                        type peer-attr-enable-type;
                        description
                          "Enable/disable the function ebgp peer advertising dependent ASRA validation, route is advertised when ASRA result is valid.";
                      }
                      leaf asra-backward-validation-export {
                        when "../asra-extend-validation-export='enable'";
                        type boolean;
                        default "false";
                        description
                          "Enable/disable the function ebgp peer advertising dependent ASRA backward validation.";
                      }
                      leaf include-not-found {
                        when "../asra-extend-validation-export='enable'";
                        type boolean;
                        default "false";
                        description
                          "Enable/disable the include-not-found attribute of the ASRA validation.";
                      }
                      leaf external {
                        when "../include-not-found='true'";
                        type boolean;
                        default "false";
                        description
                          "Enable/disable ASRA export validation to advertise only external not found routes.";
                      }
                    }
                  }
                }
                container ipv4-vpn {
                  when "../type = 'ipv4vpn'";
                  description
                    "Configure IPv4 VPNv4 options.";
                  leaf group-name {
                    type leafref {
                      path "../../../../../../peer-groups/peer-group/name";
                    }
                    must "../../../../../../peer-groups/peer-group[name = current()]/afs/af[type = 'ipv4vpn']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v4-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when "../export-policy or ../export-filter";
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  uses peer-add-path-type;
                  uses ip-prefix-filter-type;
                  uses peer-ipv4-reoriginate-type;
                  uses as-path-filter-type;
                  uses peer-group-acl-name-or-num-type;
                  uses rt-update-interval-type;
                  uses preferred-value-type;
                  leaf upe {
                    type boolean;
                    default "false";
                    description
                      "Enable/disable the peer as an underlayer PE (UPE).";
                  }
                  leaf high-priority {
                    type peer-comm-config-type;
                    default "default";
                    description
                       "Enable/disable vpn-router high priority.";
                  }
                  leaf prefix-sid {
                    type bgp:peer-comm-config-type;
                    must "(contains(../../../../address,'.') and ../prefix-sid='default') or contains(../../../../address,':')";
                    default "default";
                    description
                      "Specify a SID mode relay for peer.";
                  }
                  choice prefix-sid-packet {
                    description
                      "Prefix-sid packet method.";
                    case sid-type5 {
                      description
                        "Packet by type5.";
                      leaf sid-type5 {
                        when "../prefix-sid='enable'";
                        type empty;
                        description
                          "Packet by type5.";
                      }
                      leaf advertise-srv6-locator {
                        when "../sid-type5";
                        type empty;
                        description
                          "Advertise SRv6 locators.";
                      }
                      leaf advertise-anycast-sid {
                        when "../sid-type5";
                        type empty;
                        description
                          "Advertise anycast SID.";
                      }
                    }
                  }
                  leaf advertise-best-external {
                    type boolean;
                    must "../reflect-client='false' or ../advertise-best-external='false'";
                    must "../add-path-mode='null' or ../advertise-best-external='false'";
                    must "not(../add-path-number and ../advertise-best-external='true')";
                    default "false";
                    description
                      "Enable/disable the device to advertise Best External routes to peers.";
                  }
                  uses advertise-large-community-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    type peer-attr-enable-type;
                    description
                      "Enable/disable BGP to prevents the routes received from an EBGP peer from being broadcast to other peers with the same AS number.";
                  }
                  uses peer-independent-peer-group-type;
                  uses peer-origin-as-validation-type;
                  leaf private-nexthop {
                    type boolean;
                    default "false";
                    description
                  	"Enable/disable BGP to import routes received from VPNv4 peers into local VPN instances based on import rules without checking the route validity and then recurse the routes to next hop IP addresses instead of tunnels.";
                  }
                  leaf remote-nexthop {
                    type boolean;
                    default "false";
                    description
                  	"Enable/disable the device to advertise the remote-nexthop attribute to an IBGP peer.";
                  }
                  leaf-list accept-zero-value {
                    type zero-value-peer-attribute;
                    description
                      "Assign path attributes of zero-value to be retained.";
                  }
                  container default-route-originates {
                    description
                      "Configure advertised default VPNv4 routes.";
                    uses default-route-originate-type;
                  }
                  uses route-limit-type;
                  uses public-as-only-type;
                  uses peer-public-as-only-import-type;
                  uses path-attr-map-type;
                }
                container ipv6-vpn {
                  when "../type = 'ipv6vpn'";
                  description
                    "Configure IPv6 vpn options.";
                  leaf group-name {
                    type leafref {
                      path "../../../../../../peer-groups/peer-group/name";
                    }
                    must "../../../../../../peer-groups/peer-group[name = current()]/afs/af[type = 'ipv6vpn']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    type bgp:bgp-orf-v6-type;
                    must "(../orf-mode='null' and ../orf-type='null') or (../orf-mode!='null' and ../orf-type!='null')";
                    default "null";
                    description
                      "ORF Type.";
                  }
                  leaf orf-mode {
                    type bgp:bgp-orf-mode-type;
                    default "null";
                    description
                      "Configure an outbound route filtering (ORF) mode.";
                  }
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when "../export-policy or ../export-filter";
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  uses peer-add-path-type;
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  leaf reoriginate-vpnv6-route-enable {
                    type boolean;
                    default "false";
                    description
                      "Enable/disable VPNv6 route regeneration and advertisement.";
                  }
                  uses as-path-filter-type;
                  uses peer-group-acl6-name-or-num-type;
                  uses rt-update-interval-type;
                  uses preferred-value-type;
                  leaf advertise-best-external {
                    type boolean;
                    must "../reflect-client='false' or ../advertise-best-external='false'";
                    must "../add-path-mode='null' or ../advertise-best-external='false'";
                    must "not(../add-path-number and ../advertise-best-external='true')";
                    default "false";
                    description
                      "Enable/disable the device to advertise Best External routes to peers.";
                  }
                  uses advertise-large-community-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf peer-as-check {
                    type peer-attr-enable-type;
                    description
                      "Enable/disable BGP to prevents the routes received from an EBGP peer from being broadcast to other peers with the same AS number.";
                  }
                  uses peer-independent-peer-group-type;
                  uses peer-origin-as-validation-type;
                  leaf upe {
                    type boolean;
                    default "false";
                    description
                      "Enable/disable the peer as an underlayer PE (UPE).";
                  }
                  leaf high-priority {
                    type peer-comm-config-type;
                    default "default";
                    description
                       "Enable/disable vpn-router high priority.";
                  }
                  leaf prefix-sid {
                    type bgp:peer-comm-config-type;
                    must "(contains(../../../../address,'.') and ../prefix-sid='default') or contains(../../../../address,':')";
                    default "default";
                    description
                      "Specify a SID mode relay for peer.";
                  }
                  leaf prefix-sid-state {
                    type boolean;
                    default "false";
                    config false;
                    description
                  	"Whether the prefix-sid to a peer is enabled.";
                  }
                  leaf private-nexthop {
                    type boolean;
                    default "false";
                    description
                  	"Enable/disable BGP to import routes received from VPNv6 peers into local VPN instances based on import rules without checking the route validity and then recurse the routes to next hop IP addresses instead of tunnels.";
                  }
                  leaf-list accept-zero-value {
                    type zero-value-peer-attribute;
                    description
                      "Assign path attributes of zero-value to be retained.";
                  }
                  choice prefix-sid-packet {
                    description
                      "Prefix-sid packet method.";
                    case sid-type5 {
                      description
                        "Packet by type5.";
                      leaf advertise-srv6-locator {
                        when "../prefix-sid='enable'";
                        type empty;
                        description
                          "Advertise SRv6 locators.";
                      }
                      leaf advertise-anycast-sid {
                        when "../prefix-sid='enable'";
                        type empty;
                        description
                          "Advertise anycast SID.";
                      }
                    }
                  }
                  container default-route-originates {
                    description
                      "Configure advertised default VPNv6 routes.";
                    uses default-route-originate-type;
                  }
                  uses route-limit-type;
                  uses public-as-only-type;
                  uses peer-public-as-only-import-type;
                  uses path-attr-map-type;
                }
                container ipv4-labeluni {
                  when "../type = 'ipv4labeluni'";
                  must "../../../../../../../l3vpn:afs/l3vpn:af[l3vpn:type='ipv4-unicast']";
                  description
                    "Configure IPv4 label unicast options.";
                  leaf group-name {
                    type leafref {
                      path "../../../../../../peer-groups/peer-group/name";
                    }
                    must "../../../../../../peer-groups/peer-group[name = current()]/afs/af[type = 'ipv4labeluni']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    when "../../../../../../../../ni:name='_public_'";
                    type bgp:bgp-orf-type;
                    must "(../orf-mode='null' and ../orf-type='null') or (../orf-mode!='null' and ../orf-type!='null')";
                    default "null";
                    description
                      "ORF Type.";
                  }
                  leaf orf-mode {
                    when "../../../../../../../../ni:name='_public_'";
                    type bgp:bgp-orf-mode-type;
                    default "null";
                    description
                      "Configure an outbound route filtering (ORF) mode.";
                  }
                  leaf check-tunnel-reachable {
                    type boolean;
                    default "false";
                    description
                      "Enable/disable tunnel reachability check.";
                  }
                  uses peer-policy-filter-type;
                  leaf advertise-ext-community {
                    type boolean;
                    default "false";
                    description
                      "Enable/disable advertise the extended community attribute to a peer or peer group.";
                  }
                  uses discard-ext-community-grouping;
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    when "../../../../../../../../ni:name='_public_'";
                    type add-path-cap-type;
                    default "null";
                    description
                      "Enable add-path route advertisement to a peer.";
                  }
                  uses ip-prefix-filter-type;
                  uses as-path-filter-type;
                  uses peer-group-acl-name-or-num-type;
                  uses rt-update-interval-type;
                  leaf nexthop-configure {
                    type nexthop-configuration-type;
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf exp-mode {
                    when "../../../../../../../../ni:name!='_public_'";
                    type exp-mode-type;
                    default "null";
                    description
                      "Specify the ASs in which a BGP label can inherit the QoS priority carried in the outer label of public tunnel in the Core AS and the ASs in which the priorities of BGP LSPs must be restored before the LSPs are advertised to a non-core AS.";
                  }
                  leaf add-path-number {
                    when "../../../../../../../../ni:name='_public_'";
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf prefix-sid {
                    when "../../../../../../../../ni:name='_public_'";
                    type bgp:peer-comm-config-type;
                    default "default";
                    description
                  	"Enable/disable a device to exchange IPv4 prefix SIDs with a specified IPv6 peer.";
                  }
                  leaf prefix-sid-state {
                    when "../../../../../../../../ni:name='_public_'";
                    type boolean;
                    config false;
                    description
                  	"Whether the prefix-sid to a peer is enabled.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-type;
                  uses peer-independent-peer-group-type;
                  uses route-limit-accept-type;
                  uses public-as-only-type;
                  uses peer-public-as-only-import-type;
                  container entropy-label-parameter {
                    when "../../../../../../../../ni:name='_public_'";
                    description
                      "Configure information about entropy label parameter configuration in a peer.";
                    uses peer-entropy-label-type;
                  }
                  uses path-attr-map-type;
                  container add-path-policy {
                    when "../add-path-number";
                    description
                      "Configure peer add-path route-policy or route-filter. This configuration is applicable between IBGP peers only.";
                    uses add-path-policy-grouping;
                  }
                }
                container ipv4-multicast {
                  when "../type='ipv4multi'";
                  must "../../../../../../../l3vpn:afs/l3vpn:af[l3vpn:type='ipv4-unicast']";
                  description
                    "Configure IPv4 multicast options.";
                  leaf group-name {
                    type leafref {
                      path "../../../../../../peer-groups/peer-group/name";
                    }
                    must "../../../../../../peer-groups/peer-group[name = current()]/afs/af[type = 'ipv4multi']";
                    must "../../../../../../peer-groups/peer-group[name = current()]/peer-establish-mode = 'static'";
                    description
                      "Configure a name for a peer group. After a peer is deleted from the peer group, the peer is disabled from the address family. The object cannot be modified.";
                    ext:operation-exclude update {
                      description "The node cannot be modified, when the peer already belongs to a peer-group.";
                    }
                  }
                  uses default-route-advertise-type;
                  uses ip-prefix-filter-type;
                  uses as-path-filter-type;
                  uses peer-group-acl-name-or-num-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'";
                    description
                      "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-policy-filter-type;
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-type;
                  uses rt-update-interval-type;
                  uses bgp:preferred-value-type;
                  uses peer-independent-peer-group-type;
                  uses route-limit-type;
                  uses public-as-only-type;
                  uses peer-public-as-only-import-type;
                  uses path-attr-map-type;
                }
                container state {
                  config false;
                  description
                    "Operational state of peer information.";
                  uses peer-state-grouping;
                  leaf memory-priority {
                    type memory-priority;
                    description
                      "Priority that is used to determine the disconnection order of a BGP peer relationship if memory overload occurs.";
                  }
                }
              }
            }
          }
        }
        container peer-states {
          config false;
          description
            "List of BGP peers.";
          list peer-state {
            key "address af-type establish-mode";
            description
              "Operational state of BGP peer.";
            leaf address {
              type inet:ip-address-no-zone;
              description
                "Connection address of a peer, which can be an IPv4 or IPv6 address.";
            }
            leaf af-type {
              type bgp:af-type;
              description
                "The address family type of the peer.";
            }
            leaf establish-mode {
              type peer-establish-mode;
              description
                "Specify mode in which a BGP peer is established.";
            }
            uses peer-state-grouping;
          }
        }
        container peer-total-numbers {
          config false;
          description
            "List of BGP peer statistics.";
          list peer-total-number {
            key "af-type";
            description
              "Operational data of BGP peers number.";
            leaf af-type {
              type bgp:af-type;
              description
                "Address family type.";
            }
            uses peer-number-info;
          }
        }
        container peer-bfd-session-states {
          config false;
          description
            "List of BFD sessions.";
          list peer-bfd-session-state {
            key "address";
            config false;
            description
              "Operational state of BFD session.";
            leaf address {
              type inet:ip-address-no-zone;
              config false;
              description
                "Peer address of the BFD session.";
            }
            leaf local-address {
              type inet:ip-address-no-zone;
              config false;
              description
                "Local address of the BFD session.";
            }
            leaf if-name {
              type pub-type:if-name;
              config false;
              description
                "Name of an interface of the BFD session.";
            }
            leaf tx-interval {
              type uint32;
              units "ms";
              default "0";
              config false;
              description
                "Interval at which BFD packets are sent.";
            }
            leaf rx-interval {
              type uint32;
              units "ms";
              default "0";
              config false;
              description
                "Interval at which BFD packets are received.";
            }
            leaf multiplier {
              type uint32 {
                range "0..50";
              }
              config false;
              description
                "Detection multiplier.";
            }
            leaf status {
              type bfd-state;
              config false;
              description
                "State of the BFD session.";
            }
            leaf bfd-type {
              type string {
                length "0..15";
              }
              description
                "Type of enabled BFD.";
            }
            leaf track-session-name {
              type string {
                length "1..64";
              }
              description
                "Name of tracking the static BFD session.";
            }
            leaf global-bfd-enable {
              type boolean;
              config false;
              description
                "Global BFD state.";
            }
            leaf valid-ttl-hops {
                type uint8 {
                   range "1..255";
                }
                config false;
                description
                  "The valid TTL hops value.";
            }
            leaf frr-flag-enable {
              type boolean;
              description
                "Flag indicating whether BFD is associated with BGP FRR.";
            }
          }
        }
        container egress-engineer-peer-sets {
          when "../../../ni:name='_public_'";
          description
            "List of peer set information under BGP instance.";
          list egress-engineer-peer-set {
            key "peer-set-name";
            description
              "Configure peer set information.";
            leaf peer-set-name {
              type string {
                length "1..63";
              }
              description
                "The name for peer set.";
            }
            leaf static-label {
              type uint32 {
                range "16..1048575";
              }
              description
                "The static label for peer set. The value range and default value are controlled by the PAF.";
            }
            leaf label-pop {
              when "../static-label";
              type boolean;
              must "not(../relate-bfd='true' and ../label-pop='true')";
              default "false";
              description
                "Enable/disable the BGP-EPE label popping function.";
            }
            leaf relate-bfd {
              type boolean;
              must "not(../relate-bfd='true' and ../label-pop='true')";
              default "false";
              description
                "Enable/disable association between the BGP-EPE label and BFD status.";
            }
          }
        }
      }
      container instance-processs {
        description
          "List of all BGP instances.";
        list instance-process {
          key "name";
          max-elements 1;
          description
            "Configure a BGP instance.";
          ext:generated-by system {
            when "../../../ni:name = '_public_'";
            description "The BGP public instance is generated automatically when BGP instances is enabled.";
          }
          leaf name {
            type leafref {
              path "/bgp:bgp/bgp:instance-processs/bgp:instance-process/bgp:name";
            }
            description
              "Name of BGP Site.";
          }
          leaf router-id {
            type inet:ipv4-address-no-zone;
            description
              "ID of a router that is in IPv4 address format. Certain dynamic routing protocols require a router ID. If no router ID is specified for a router when these protocols are enabled, the router ID in the RM module is used by default. The default router ID in the RM module is 0.0.0.0 when the router is not configured with any interface. 
               The rules for selecting a router ID are as follows:
               1. If you set a router ID through this configuration, the set router ID is used. If the router ID is not set, you need to select a router ID according to the following rules:
               (1) If loopback interfaces configured with IP addresses exist, the largest IP address among the IP addresses of the loopback interfaces is selected as the router ID.
               (2) If no loopback interface configured with an IP address exists, the largest IP address among the IP addresses of other interfaces is selected as the router ID, regardless of whether the interface is Up.
               The router ID is reselected only when the interface address that is selected as the router ID is deleted or changed. The router ID is not reselected in any of the following cases:
               a. The interface is Down.
               b. A loopback interface is configured when the IP address of a non-loopback interface is selected as the router ID.
               c. A larger IP address of an interface is configured.
               2. Each VPN instance selects the router ID from the addresses of the interfaces of the VPN instance according to the preceding rules.
               3. When both the AMB and SMB exist on the router, the system backs up the router ID set through the related command and the router ID that is selected from IP addresses of the interfaces. After the active/standby switchover is performed, the system checks the validity of the router ID selected from the interface addresses. If the router ID is invalid, the system reselects a router ID.";
          }
          leaf effect-router-id {
            type inet:ipv4-address-no-zone;
            default "0.0.0.0";
            config false;
            description
              "Router ID that takes effect.";
          }
          container afs {
            description
              "List of BGP address family instances.";
            list af {
              key "type";
              description
                "Configure BGP address family instance.";
              leaf type {
                type bgp:instance-af-type;
                description
                  "Address family type of a BGP instance.";
              }
              container ipv4-unicast {
                when "../type = 'ipv4uni' and ../../../../../../ni:name!='_public_'";
                must "../../../../../../l3vpn:afs/l3vpn:af[l3vpn:type='ipv4-unicast']";
                description
                  "Configure IPv4 unicast options.";
                container common {
                  description
                    "Configure IPv4 unicast common options.";
                  uses common-configure;
                  uses ipv4-common-configure;
                  leaf load-balancing-local-learn-cross {
                    type boolean;
                    must ". = 'false' or (. = 'true' and ../../../../../../../../l3vpn:afs/l3vpn:af[l3vpn:type='ipv4-unicast']/l3vpn:lsp-operation = 'pop-go')";
                    default "false";
                    description
                      "Enable/disable local route for peer and cross route load balancing.";
                  }
                }
                uses bgp-route-preference-options;
                container nexthop-recursive-lookup {
                 description
                  "Configure next hop iteration.";
                  container common {
                  description
                    "Configure next hop iteration common options.";
                    uses nexthop-recursive-lookup-restrain;
                    uses nexthop-recursive-lookup-include-srv6-best-effort;
                  }
                  uses nexthop-recursive-lookup-delay;
                }
                uses ipv4-import-route;
                uses ipv4-aggregate-routes;
                uses ipv4-aggregate-default-route;
                container network-routes {
                  description
                    "List of network routes.";
                  list network-route {
                    key "address mask-length";
                    description
                      "Configure a network route in the BGP routing table.";
                    uses network-route-ipv4;
                  }
                }
                container import-ribs {
                  description
                    "List of imported RIBs configuration.";
                  list import-rib {
                    key "source-vpn source-address-family";
                    description
                      "Configure imported RIBs.";
                    leaf source-vpn {
                      type leafref {
                        path "/ni:network-instance/ni:instances/ni:instance/ni:name";
                      }
                      must "../../../../../../../../../ni:name != current()";
                      description
                        "Source VPN name.";
                    }
                    leaf source-address-family {
                      type bgp:vrf-import-rib-ipv4-safi-type;
                      must "/ni:network-instance/ni:instances/ni:instance[ni:name=current()/../bgp:source-vpn]/l3vpn:afs/l3vpn:af[l3vpn:type='ipv4-unicast']";
                      description
                        "Source address family type.";
                    }
                    leaf valid-route {
                      type boolean;
                      default "false";
                      description
                        "Enable/disable imported valid route.";
                    }
                    leaf include-label-route {
                      when "../source-address-family='ipv4uni'";
                      type boolean;
                      default "false";
                      description
                        "Enable/disable imported include label route.";
                    }
                    uses choice-policy-set;
                  }
                }
                container instance-import-ribs {
                  description
                    "List of imported RIBs from BGP instances configuration.";
                  list instance-import-rib {
                    key "source-instance source-vpn source-address-family";
                    description
                      "Configure imported RIBs.";
                    leaf source-instance {
                      type string {
                        length "1..31";
                      }
                      must "../source-instance = 'default' and /bgp:bgp/bgp:base-process/bgp:enable='true'";
                      description
                        "Configure source BGP instance.";
                    }
                    leaf source-vpn {
                      type leafref {
                        path "/ni:network-instance/ni:instances/ni:instance/ni:name";
                      }
                      must "../../../../../../../../../ni:name != current()";
                      description
                        "Source VPN name.";
                    }
                    leaf source-address-family {
                      type bgp:vrf-import-rib-ipv4-safi-type;
                      description
                        "Source address family type.";
                    }
                    leaf valid-route {
                      type boolean;
                      default "false";
                      description
                        "Enable/disable imported valid route.";
                    }
                    leaf include-label-route {
                      when "../source-address-family='ipv4uni'";
                      type boolean;
                      default "false";
                      description
                        "Enable/disable imported include label route.";
                    }
                    uses choice-policy-set;
                  }
                }
                container advertise-route-to-evpns {
                  description
                    "Configure advertise route protocol.";
                  uses advertise-route-to-evpn-type;
                }
                uses ipv4-import-filter-protocol-type;
                uses ipv4-export-filter-policys;
                uses vrf-af-dampening-routes;
                uses bgp:slow-peer-type;
                uses qos-local-id-type;
                uses bestroute-nh-relay-pri-grp-mask;
                container prefix-exempt {
                  description
                    "Configure the exempt filtering policy applied to the routes received when bgp memory-resilence occurred.";
                  uses group-exempt-ip-prefix;
                }
                container lowest-priority {
                  description
                    "Configure route lowest-priority.";
                  container aggregate-route {
                    presence "Configure aggregate-route lowest-priority.";
                    description
                      "Configure aggregate-route lowest-priority.";
                    leaf delay-time {
                      type uint32 {
                        range "1..86400";
                      }
                      units "s";
                      description
                        "Specifies the aggregate-route lowest-priority delay time.";
                    }
                  }
                }
              }
              container ipv4-vpn {
                when "../type = 'ipv4vpn' and ../../../../../../ni:name='_public_'";
                description
                  "Configure IPv4 VPNv4 options.";
                uses vpn-target-type;
                uses reflector-cluster-type;
                uses reflect-type;
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  type leafref {
                    path "/rtp:routing-policy/rtp:tunnel-selectors/rtp:tunnel-selector/rtp:name";
                  }
                  description
                    "Configure a tunnel selector and apply it to the BGP IPv4 unicast, BGP VPNv4 address families and BGP VPNv6 address families so that IPv4,VPNv4 and VPNv6 labeled routes can be iterated to tunnels based on the tunnel selector.";
                }
                leaf route-select-delay {
                  type uint16 {
                    range "0..3600";
                  }
                  units "s";
                  default "0";
                  description
                    "Route selection delay.";
                }
                leaf apply-label-mode {
                  type apply-label-type;
                  default "per-route";
                  description
                    "Method of distributing labels to VPNV4 and VPNV6 routes. The way which assigns the label depends on the paf value. If there are a large number of routes, assign a label for the routes that have same nexthop and out-label. This allows all routes which have same nexthop and out-label to use one label.";
                }
                leaf nexthop-select-depend-type {
                  type select-depend-type-ext;
                  default "depend-ip";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf default-med {
                  type uint32;
                  default "0";
                  description
                    "Specify the Multi-Exit-Discriminator (MED) of BGP routes. The value is an integer. This value is valid only for the imported routes and BGP summarized routes on the local router.";
                }
                leaf best-external {
                  type boolean;
                  default "false";
                  description
                    "Enable/disable best external route selection.";
                }
                leaf label-free-delay {
                  type uint8 {
                    range "0..180";
                  }
                  units "s";
                  default "0";
                  description
                    "Label free delay.";
                }
                leaf add-path-select-num {
                  type uint8 {
                    range "2..64";
                  }
                  description
                    "Number of Add-Path routes.";
                }
                leaf default-local-preference {
                  type uint32 {
                    range "0..4294967295";
                  }
                  default "100";
                  description
                    "The local preference of BGP routes.";
                }
                uses bestroute-med-plus-igp-type;
                uses bestroute-router-id-prior-clusterlist-type;
                leaf reflect-between-client {
                  type boolean;
                  default "true";
                  description
                    "Enable/disable route reflection between clients. If clients of a route reflector (RR) are fully meshed, you can disable route reflection among clients to reduce the cost.";
                }
                leaf activate-route-tag {
                  type boolean;
                  default "false";
                  description
                    "Enable/disable tag-based filtering.";
                }
                uses route-reflector-ext-community-filter-type;
                uses vrf-af-dampening-routes;
                container nexthop-recursive-lookup {
                 description
                  "Configure next hop iteration.";
                  container common {
                    description
                      "Configure next hop iteration common options.";
                    uses nexthop-recursive-lookup-restrain;
                    uses nexthop-recursive-lookup-include-srv6-best-effort;
                    }
                    uses nexthop-recursive-lookup-delay;
                    uses bit-error-detection-type;
                }
                uses ipv4-import-filter-protocol-type;
                uses ipv4vpn-export-filter-protocol-type;
                uses slow-peer-type;
                uses bestroute-nh-relay-pri-grp-mask;
                container prefix-exempt {
                  description
                    "Configure the exempt filtering policy applied to the routes received when bgp memory-resilence occurred.";
                  uses group-exempt-ip-prefix;
                }
              }
              container ipv6-unicast {
                when "../type = 'ipv6uni' and ../../../../../../ni:name!='_public_'";
                must "../../../../../../l3vpn:afs/l3vpn:af[l3vpn:type='ipv6-unicast']";
                description
                  "Configure IPv6 unicast options.";
                container common {
                  description
                    "Configure IPv6 unicast common options.";
                  uses common-configure;
                  uses ipv6-common-configure;
                }
                container import-ribs {
                  description
                    "List of imported RIBs configuration.";
                  list import-rib {
                    key "source-vpn source-address-family";
                    description
                      "Configure imported RIBs.";
                    leaf source-vpn {
                      type leafref {
                        path "/ni:network-instance/ni:instances/ni:instance/ni:name";
                      }
                      must "../../../../../../../../../ni:name != current()";
                      description
                        "Source VPN name.";
                    }
                    leaf source-address-family {
                      type bgp:import-rib-ipv6-safi-type;
                      must "/ni:network-instance/ni:instances/ni:instance[ni:name=current()/../bgp:source-vpn]/l3vpn:afs/l3vpn:af[l3vpn:type='ipv6-unicast']";
                      description
                        "Source address family type.";
                    }
                    uses import-ribs-options;
                    uses choice-policy-set;
                  }
                }
                uses ipv6-aggregate-default-route;
                uses ipv6-aggregate-routes;
                uses ipv6-import-route;
                container nexthop-recursive-lookup {
                  description
                    "Configure next hop iteration.";
                  container common {
                    description
                      "Configure next hop iteration common options.";
                    uses ipv6-nexthop-recursive-lookup-restrain;
                    leaf include-srv6-best-effort {
                      type empty;
                      must "../route-policy";
                      description
                        "Enable routing policy application when the iteration result of a route's next-hop's next hop points to SRv6 BE.";
                    }
                  }
                  uses nexthop-recursive-lookup-delay;
                }
                container network-routes {
                description
                  "List of network routes.";
                  list network-route {
                    key "address mask-length";
                    description
                      "Configure a network route in the BGP routing table.";
                    uses network-route-ipv6;
                  }
                }
                container advertise-route-to-evpns {
                  description
                    "Configure advertise route protocol.";
                  uses advertise-route-to-evpn-type;
                }
                uses bgp-route-preference-options;
                uses vrf-af-dampening-routes;
                uses ipv6-import-filter-protocol-type;
                uses ipv6-export-filter-protocol-type;
                uses bgp:slow-peer-type;
                container prefix-exempt {
                  description
                    "Configure the exempt filtering policy applied to the routes received when bgp memory-resilence occurred.";
                  uses group-exempt-ipv6-prefix;
                }
                container lowest-priority {
                    description
                      "Configure route lowest-priority.";
                    container aggregate-route {
                      presence "Configure aggregate-route lowest-priority.";
                      description
                        "Configure aggregate-route lowest-priority.";
                      leaf delay-time {
                        type uint32 {
                          range "1..86400";
                        }
                        units "s";
                        description
                        "Specifies the aggregate-route lowest-priority delay time.";
                      }
                    }
                  }
              }
            }
          }
          container vpn-as-number {
            when "../../../../ni:name!='_public_'";
            description
              "Configure BGP vpn as-number.";
              leaf local-ipv4 {
                type as-number-validate;
                description
                  "IPv4 as-number.";
              }
              leaf local-ipv6 {
                type as-number-validate;
                description
                  "IPv6 as-number.";
              }
              leaf ipv4-as-no-prepend {
                when "../local-ipv4";
                type empty;
                description
                  "IPv4 as-number no prepend.";
              }
              leaf ipv6-as-no-prepend {
                when "../local-ipv6";
                type empty;
                description
                  "IPv6 as-number no prepend.";
              }
          }
          container peer-groups {
            description
              "List of BGP peer groups. The BGP peer groups can help you simplify the configurations. If you want to perform the same configuration for several peers, you can create a peer group and then configure the peer group. After you add these peers to the peer group, all these peers will have the same configurations as the peer group.";
            list peer-group {
              key "name";
              description
                "Configure information about a BGP peer group.";
              leaf name {
                type string {
                  length "1..47";
                  pattern '([^\? ]+)';
                }
                description
                  "Specify the name of a peer group. The value is a string of characters, spaces not supported.";
              }
              leaf type {
                type group-type;
                mandatory true;
                description
                  "Specify the type of a peer group. The value can be IBGP or EBGP.The object cannot be modified.";
                ext:operation-exclude update {
                  description "The node cannot be modified, when node is already configured.";
                }
              }
              uses peer-local-if-type;
              uses authentication-attr-type;
              leaf tcp-ao-name {
                type leafref {
                  path "/socket:socket/socket:tcp-aos/socket:tcp-ao/socket:name";
                }
                must "not(../password-type!='null' or ../key-chain-name)";
                must "/socket:socket/socket:tcp-aos/socket:tcp-ao[socket:name=current()]/socket:accept-mismatch='false'";
                description
                  "Specify TCP-AO authentication for establishing the TCP connection between BGP peers.";
              }
              leaf description {
                type string {
                  length "1..255";
                  pattern '([^?]*)';
                }
                description
                  "Specify the description of a peer group. The value is a string, which can be letters or digits, spaces supported. By default, no description is configured.";
              }
              leaf group-as {
                when "not(../type='ibgp') and ../peer-establish-mode ='static'";
                type as-number-validate;
                description
                  "Specify the AS number of a peer group. The AS number is in either a 2-byte or 4-byte format. 
                  The two-byte format is X. X is an integer ranging from 1 to 65535.
                  The four-byte format is X.Y and X. When the format is X.Y, X and Y are both integers, with the value of X ranging from 1 to 65535, and the value of Y ranging from 0 to 65535; when the format is X, X is an integer, with the value of X ranging from 1 to 4294967295.";
              }
              leaf ebgp-max-hop {
                when "../type='ebgp'";
                type uint32 {
                  range "1..255";
                }
                must "not(../valid-ttl-hops) or (../valid-ttl-hops>=1 and not(../valid-ttl-hops>255) and ../ebgp-max-hop=1)";
                default "1";
                description
                  "Maximum number of hops in an indirect EBGP connection. By default, EBGP connections can be established only between directly connected peers. The function must be configured on both ends.";
              }
              leaf valid-ttl-hops {
                type uint16 {
                  range "1..255";
                }
                must "not(../ebgp-max-hop and ../ebgp-max-hop>1)";
                description
                  "Enable GTSM on a peer or peer group. The valid-TTL-Value parameter is used to specify the number of TTL hops to be detected. If the value is configured as hops, the valid TTL range of the detected packet is [255-hops+1, 255].";
              }
              uses peer-tracking-type;
              leaf conventional {
                type boolean;
                default "false";
                description
                  "Enable/disable general router functions on peers. In conventional mode, not all the extended router functions, such as, route refreshing, GR, and multi-address family negotiation, are available. Therefore, the router of a new version can be compatible with the routers of earlier versions.";
              }
              leaf route-refresh {
                type boolean;
                default "true";
                description
                  "Enable/disable BGP to advertise Refresh messages to peers.";
              }
              leaf four-byte-as {
                type boolean;
                default "true";
                description
                  "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
              }
              leaf ignore {
                type boolean;
                default "false";
                description
                  "Enable/disable the function to tear down sessions between peers and clear all related routing information.";
              }
              leaf connect-mode {
                when "../peer-establish-mode = 'static'";
                type connect-mode;
                default "null";
                description
                  "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              }
              leaf log-change {
                type boolean;
                default "true";
                description
                  "Enable/disable BGP to record the session status and events of the specified peer or peer group.";
              }
              leaf check-first-as {
                when "../type='ebgp'";
                type peer-cap-config-state;
                default "default";
                description
                  "Check the first AS in the AS_Path of the update messages from EBGP peers.";
              }
              leaf memory-priority {
                type memory-priority;
                default "medium";
                description
                  "Set a priority that determines the disconnection order of each BGP peer relationship in a peer group if memory overload occurs.";
              }
              leaf oscillation-dampening {
                when "../peer-establish-mode = 'static'";
                type boolean;
                default "true";
                description
                  "Enable/disable BGP to suppress the establishment of a specified peer group's peer relationships that flap continuously. By default, the capability is enabled.";
              }
              leaf peer-establish-mode {
                type inst-peer-establish-mode;
                default "static";
                description
                  "Specify mode in which a BGP peer is established.";
                ext:operation-exclude update|delete {
                  description "The node cannot be modified, deleted when node is already configured.";
                }
              }
              leaf-list listen-as {
                when "(../peer-establish-mode = 'dynamic' or ../peer-establish-mode = 'dynamic-ipv6') and ../type = 'ebgp'";
                type as-number-validate;
                max-elements 6;
                description
                  "Specify the peer AS from which a dynamic EBGP peer group listens for BGP connection requests.";
              }
              container listen-as-segments {
                when "(../peer-establish-mode = 'dynamic' or ../peer-establish-mode = 'dynamic-ipv6') and ../type = 'ebgp'";
                description
                  "List of AS number ranges for listening.";
                list listen-as-segment {
                  must "not(../../listen-as)";
                  key "begin-as end-as";
                  max-elements 16;
                  description
                    "Specify an AS number range from which a dynamic EBGP peer group listens for connection requests. The value of begin-as must be smaller than that of end-as. The value of As-Segment cannot contain the value of LocalAS or the value of fake-as. An AS number range cannot contain a confederation AS number, and any two AS number ranges cannot contain each other.";
                  leaf begin-as {
                    type as-number-validate;
                    description
                      "Specify the start AS number in an AS range.";
                  }
                  leaf end-as {
                    type as-number-validate;
                    description
                      "Specify the end AS number in an AS range.";
                  }
                }
              }
              container fake-as-parameter {
                when "../../../../../../ni:name!='_public_'";
                description
                  "Configure BGP fake-as parameters.";
                leaf fake-as {
                  when "../../bgp:type='ebgp'";
                  type bgp:as-number-validate;
                  description
                    "Fake AS number that is specified for a local peer. By default, a peer uses the actual AS number of the local end.
                    An AS number can be in either two-byte format or four-byte format:
                    The two-byte format is X. X is an integer ranging from 1 to 65535.
                    The four-byte format is X.Y and X. When the format is X.Y, X and Y are both integers, with the value of X ranging from 1 to 65535, and the value of Y ranging from 0 to 65535; when the format is X, X is an integer, with the value of X ranging from 1 to 4294967295.";
                }
                leaf dual-as {
                  when "../fake-as";
                  type boolean;
                  default "false";
                  description
                    "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
                }
                leaf prepend-global-as {
                  when "../fake-as";
                  type boolean;
                  default "false";
                  description
                    "Enable/disable the function to add the global AS number to the Update packets to be advertised.";
                }
                leaf prepend-fake-as {
                  when "../fake-as";
                  type boolean;
                  default "false";
                  description
                    "Enable/disable the function to add the Fake AS number to received Update packets.";
                }
              }
              uses group-timer-para-type;
              uses instance-group-bfd-parameter-type;
              container graceful-restart {
                when "../peer-establish-mode = 'static'";
                description
                  "Configure graceful restart.";
                uses group-graceful-restart-type;
                leaf peer-reset {
                  type boolean;
                  default "false";
                  description
                    "Enable/disable resetting BGP peer graceful.";
                }
              }
              container local-graceful-restart {
                when "../peer-establish-mode = 'static'";
                description
                  "Configure local graceful restart.";
                uses group-local-graceful-restart-type;
              }
              container memory-resilience {
                description
                  "Configure memory resiliency.";
                 uses low-memory-exempt-grouping;
              }
              container afs {
                description
                  "List of all peer groups that are enabled in a specified address family.";
                list af {
                  key "type";
                  description
                    "Configure peer group enabled in a specified address family.";
                  leaf type {
                    type bgp:instance-group-af-type;
                    must "../../../../../afs/af[type = current()]";
                    description
                      "Address family type of a BGP instance.";
                  }
                  container ipv4-unicast {
                    when "../type = 'ipv4uni' and ../../../../../../../../ni:name!='_public_'";
                    must "../../../../../../../../l3vpn:afs/l3vpn:af[l3vpn:type='ipv4-unicast']";
                    description
                      "Configure IPv4 unicast options.";
                    leaf reflect-client {
                      when "../../../../bgp:type='ibgp'";
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    leaf orf-type {
                      type bgp:bgp-orf-v4-type;
                      must "(../orf-mode='null' and ../orf-type='null') or (../orf-mode!='null' and ../orf-type!='null')";
                      default "null";
                      description
                        "ORF Type.";
                    }
                    leaf orf-mode {
                      type bgp:bgp-orf-mode-type;
                      default "null";
                      description
                        "Configure an outbound route filtering (ORF) mode.";
                    }
                    leaf label-route-capability {
                      type boolean;
                      default "false";
                      description
                        "Enable/disable a device to exchange labeled routes.";
                    }
                    leaf check-tunnel-reachable {
                      when "../label-route-capability='true'";
                      type boolean;
                      default "false";
                      description
                        "Enable/disable tunnel reachability check.";
                    }
                    uses vrf-nexthop-configure-grouping;
                    uses peer-policy-filter-type;
                    leaf allow-as-loop {
                      type uint32 {
                        range "1..10";
                      }
                      description
                        "Allow repetitive local AS numbers. By default, repetitive local AS numbers are not allowed.";
                    }
                    uses ip-prefix-filter-type;
                    uses as-path-filter-type;
                    uses peer-group-acl-name-or-num-type;
                    uses default-route-advertise-type;
                    leaf default-route-match-mode {
                      when "../default-route-advertise='true'";
                      type cra-match-mode;
                      default "null";
                      description
                        "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                    }
                    uses rt-update-interval-type;
                    uses preferred-value-type;
                    leaf substitute-as-enable {
                      when "../../../../bgp:type='ebgp'";
                      type boolean;
                      default "false";
                      description
                        "Enable/disable replace the AS number of a specified peer in the AS_Path attribute with the local AS number. On a PE where AS number replacement is enabled, if an AS number in the AS_Path attribute of a route is same as that of the CE to which the PE advertises the route, the PE replaces the AS number with its own AS number before advertising the route.";
                    }
                    uses soo-grouping;
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      when "../../../../bgp:type='ebgp'";
                      type peer-attr-enable-type;
                      default "disable";
                      description
                        "Enable/disable BGP to prevents the routes received from an EBGP peer from being broadcast to other peers with the same AS number.";
                    }
                    uses load-balancing-type;
                    uses group-independent-peer-group-type;
                    uses community-attribute;
                    uses advertise-large-community-group-type;
                    uses ipv4-default-route-match-conditions-type;
                    uses route-limit-accept-type;
                    uses public-as-only-type;
                    uses group-public-as-only-import-type;
                  }
                  container ipv4-vpn {
                    when "../type = 'ipv4vpn' and ../../../../../../../../ni:name='_public_'";
                    description
                      "Configure IPv4 vpnv4 options.";
                    leaf advertise-community {
                      type boolean;
                      default "false";
                      description
                        "Enable/disable advertise the community attribute to a peer or a peer group.";
                    }
                    leaf reflect-client {
                      when "../../../../bgp:type='ibgp'";
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    leaf orf-type {
                      type bgp:bgp-orf-v4-type;
                      must "(../orf-mode='null' and ../orf-type='null') or (../orf-mode!='null' and ../orf-type!='null')";
                      default "null";
                      description
                        "ORF Type.";
                    }
                    leaf orf-mode {
                      type bgp:bgp-orf-mode-type;
                      default "null";
                      description
                        "Configure an outbound route filtering (ORF) mode.";
                    }
                    leaf nexthop-configure {
                      type nexthop-configuration-type;
                      description
                        "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                    }
                    uses peer-policy-filter-type;
                    leaf allow-as-loop {
                      type uint32 {
                        range "1..10";
                      }
                      description
                        "Allow repetitive local AS numbers. By default, repetitive local AS numbers are not allowed.";
                    }
                    leaf aigp {
                      type boolean;
                      default "false";
                      description
                        "Enable/disable route with AIGP attribute advertisement to or from a peer.";
                    }
                    leaf add-path-mode {
                      type add-path-cap-type;
                      default "null";
                      description
                        "Enable Add-Path route advertisement to a peer.";
                    }
                    uses ip-prefix-filter-type;
                    uses as-path-filter-type;
                    uses peer-group-acl-name-or-num-type;
                    uses rt-update-interval-type;
                    uses preferred-value-type;
                    leaf add-path-number {
                      type uint8 {
                        range "2..64";
                      }
                      description
                        "Number of Add-Path routes that can be advertised to a peer.";
                    }
                    leaf upe {
                      type boolean;
                      default "false";
                      description
                        "Enable/disable the peer as an underlayer PE (UPE).";
                    }
                    leaf advertise-best-external {
                      when "../../../../bgp:type='ibgp'";
                      type boolean;
                      must "../reflect-client='false' or ../advertise-best-external='false'";
                      must "../add-path-mode='null' or not(../add-path-mode) or ../advertise-best-external='false'";
                      must "not(../add-path-number and ../advertise-best-external='true')";
                      default "false";
                      description
                        "Enable/disable the device to advertise Best External routes to peers.";
                    }
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      when "../../../../bgp:type='ebgp'";
                      type peer-attr-enable-type;
                      default "disable";
                      description
                        "Enable/disable BGP to prevents the routes received from an EBGP peer from being broadcast to other peers with the same AS number.";
                    }
                    uses group-independent-peer-group-type;
                    leaf origin-as-validation {
                      type boolean;
                      default "false";
                      description
                        "Enable/disable the BGP peer origin validation.";
                    }
                    container default-route-originates {
                      description
                        "Configure advertised default VPNv4 routes.";
                      uses default-route-originate-type;
                    }
                    uses route-limit-type;
                    uses public-as-only-type;
                    uses group-public-as-only-import-type;
                  }
                  container ipv6-unicast {
                    when "../type = 'ipv6uni' and ../../../../../../../../ni:name!='_public_'";
                    must "../../../../../../../../l3vpn:afs/l3vpn:af[l3vpn:type='ipv6-unicast']";
                    description
                      "Configure IPv6 unicast options.";
                    uses community-attribute;
                    uses advertise-large-community-group-type;
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      when "../../../../bgp:type='ebgp'";
                      type peer-attr-enable-type;
                      default "disable";
                      description
                        "Enable/disable BGP to prevents the routes received from an EBGP peer from being broadcast to other peers with the same AS number.";
                    }
                    leaf reflect-client {
                      when "../../../../bgp:type='ibgp'";
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    uses preferred-value-type;
                    uses peer-policy-filter-type;
                    leaf allow-as-loop {
                      type uint32 {
                        range "1..10";
                      }
                      description
                        "Allow repetitive local AS numbers. By default, repetitive local AS numbers are not allowed.";
                    }
                    uses vrf-nexthop-configure-grouping;
                    leaf substitute-as-enable {
                      when "../../../../bgp:type='ebgp'";
                      type boolean;
                      default "false";
                      description
                        "Enable/disable replace the AS number of a specified peer in the AS_Path attribute with the local AS number. On a PE where AS number replacement is enabled, if an AS number in the AS_Path attribute of a route is same as that of the CE to which the PE advertises the route, the PE replaces the AS number with its own AS number before advertising the route.";
                    }
                    uses soo-grouping;
                    leaf default-route-match-mode {
                      when "../default-route-advertise='true'";
                      type cra-match-mode;
                      default "null";
                      description
                        "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                    }
                    uses as-path-filter-type;
                    uses ipv6-prefix-filter-type;
                    uses peer-group-acl6-name-or-num-type;
                    uses default-route-advertise-type;
                    uses rt-update-interval-type;
                    uses ipv6-default-route-match-conditions-type;
                    uses route-limit-type;
                    uses public-as-only-type;
                    uses group-public-as-only-import-type;
                  }
                }
              }
              container ssl-policy {
                when "../../../../../../ni:name='_public_' and ../peer-establish-mode='static'";
                description
                  "Configure SSL policy for BGP group.";
                uses group-ssl-policy-grouping {
                  refine role {
                    must "(../role='client' and ../../connect-mode != 'listen-only') or (../role='server' and ../../connect-mode != 'connect-only')";
                  }
                }
              }
            }
          }
          container peers {
            description
              "List of BGP peers.";
            list peer {
              key "address";
              description
                "Configure a single BGP peer.";
              leaf address {
                type inet:ip-address-no-zone;
                description
                  "Connection address of a peer, which can be an IPv4 or IPv6 address.";
              }
              leaf remote-as {
                type as-number-validate;
                mandatory true;
                description
                  "AS number of a peer, which must be selected or group name when creating, and which can be in either two-byte format or four-byte format:
                   The two-byte format is X. X is an integer ranging from 1 to 65535.
                   The four-byte format is X.Y and X. When the format is X.Y, X and Y are both integers, with the value of X ranging from 1 to 65535, and the value of Y ranging from 0 to 65535; when the format is X, X is an integer, with the value of X ranging from 1 to 4294967295.
                   The object cannot be modified.";
                ext:operation-exclude update {
                  description "The node cannot be modified, when node is already configured.";
                }
              }
              leaf group-name {
                type leafref {
                  path "../../../peer-groups/peer-group/name";
                }
                must "../../../peer-groups/peer-group[name = current()]/peer-establish-mode = 'static'";
                description
                  "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
                ext:operation-exclude update {
                  description "The node cannot be modified, when the peer already belongs to a peer-group.";
                }
              }
              uses peer-local-if-type {
                refine local-if-address {
                  must "not(contains(., ':'))";
                }
              }
              uses authentication-attr-type;
              leaf tcp-ao-disable {
                type empty;
                description
                  "Disable the TCP-AO authentication for establishing the TCP connection between BGP peers.";
              }
              leaf tcp-ao-name {
                when "not(../tcp-ao-disable)";
                type leafref {
                  path "/socket:socket/socket:tcp-aos/socket:tcp-ao/socket:name";
                }
                must "not(../password-type!='null' or ../key-chain-name)";
                must "/socket:socket/socket:tcp-aos/socket:tcp-ao[socket:name=current()]/socket:accept-mismatch='false'";
                description
                  "Specify TCP-AO authentication for establishing the TCP connection between BGP peers.";
              }
              leaf description {
                type string {
                  length "1..255";
                  pattern '([^?]*)';
                }
                description
                  "Description of a peer, which can be letters or digits. The description is a string, spaces supported. By default, no description is configured for a peer.";
              }
              leaf ebgp-max-hop {
                type uint32 {
                  range "1..255";
                }
                must "not(../valid-ttl-hops) or (../valid-ttl-hops>=1 and ../valid-ttl-hops<=255 and ../ebgp-max-hop=1)";
                description
                  "Maximum number of hops in an indirect EBGP connection. By default, EBGP connections can be established only between directly connected peers. The function must be configured on both ends. By default, value is determined by the neighbor type, the default value of EBGP is 1 and the default value of IBGP is 0.";
                ext:dynamic-default;
              }
              uses peer-tracking-type;
              leaf conventional {
                type boolean;
                default "false";
                description
                  "Enable/disable general router functions on peers. In conventional mode, not all the extended router functions, such as, route refreshing, GR, and multi-address family negotiation, are available. Therefore, the router of a new version can be compatible with the routers of earlier versions.";
              }
              leaf route-refresh {
                type boolean;
                default "true";
                description
                  "Enable/disable BGP to advertise Refresh messages to peers.";
              }
              leaf four-byte-as {
                type boolean;
                default "true";
                description
                  "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
              }
              leaf ignore {
                type boolean;
                default "false";
                description
                  "Enable/disable the function to tear down sessions between peers and clear all related routing information.";
              }
              leaf valid-ttl-hops {
                type uint16 {
                  range "1..255";
                }
                must "not(../ebgp-max-hop and ../ebgp-max-hop>1)";
                description
                  "Enable GTSM on a peer or peer group. The valid-TTL-Value parameter is used to specify the number of TTL hops to be detected. If the value is configured as hops, the valid TTL range of the detected packet is [255-hops+1, 255].";
              }
              leaf connect-mode {
                type connect-mode;
                default "null";
                description
                  "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              }
              leaf log-change {
                type boolean;
                default "true";
                description
                  "Enable/disable BGP to record the session status and events of the specified peer or peer group.";
              }
              leaf check-first-as {
                type peer-cap-config-state;
                default "default";
                description
                  "Check the first AS in the AS_Path of the update messages from EBGP peers.";
              }
              leaf memory-priority {
                type peer-memory-priority;
                default "default";
                description
                  "Set a priority that determines the disconnection order of a BGP peer relationship if memory overload occurs.";
              }
              leaf memory-priority-capability {
                type memory-priority;
                config false;
                description
                  "Priority that is used to determine the disconnection order of a BGP peer relationship if memory overload occurs.";
              }
              leaf oscillation-dampening {
                type peer-attr-enable-type;
                description
                  "Enable/disable BGP to suppress the establishment of a specified peer relationship that flaps continuously. By default, the capability is enabled.";
              }
              uses rely-state-interface-grouping;
              container fake-as-parameter {
                when "../../../../../../ni:name!='_public_'";
                description
                  "Configure BGP fake-as parameters.";
                uses fake-as-type;
              }
              uses peer-timer-para-type;
              uses instance-peer-bfd-parameter-type {
                refine bfd-parameter/track-session-name {
                  must "(/bfd:bfd/bfd:sessions/bfd:session[bfd:name=current()]/bfd:destination-address-static-unicast-ipv4=../../address and /bfd:bfd/bfd:sessions/bfd:session[bfd:name=current()]/bfd:vrf-name-static-unicast-ipv4=../../../../../../../ni:name and /bfd:bfd/bfd:sessions/bfd:session[bfd:name=current()]/bfd:is-group-static-unicast-ipv4='true') or (/bfd:bfd/bfd:sessions/bfd:session[bfd:name=current()]/bfd:destination-address-static-ipv6=../../address and /bfd:bfd/bfd:sessions/bfd:session[bfd:name=current()]/bfd:vrf-name-static-ipv6=../../../../../../../ni:name and /bfd:bfd/bfd:sessions/bfd:session[bfd:name=current()]/bfd:is-group-static-ipv6='true')";
                }
              }
              uses peer-bfd-parameter-state-grouping;
              container graceful-restart {
                description
                  "Configure graceful restart.";
                uses peer-graceful-restart-type;
                leaf peer-reset {
                  type peer-comm-config-type;
                  default "default";
                  description
                    "Enable/disable resetting BGP peer graceful.";
                }
                leaf effect-peer-reset {
                  type boolean;
                  config false;
                  description
                    "Whether to enable/disable resetting BGP peer graceful.";
                }
              }
              container local-graceful-restart {
                description
                  "Configure local graceful restart.";
                uses peer-local-graceful-restart-type;
              }
              uses peer-memory-resilience-grouping;
              container afs {
                description
                  "List of peers in a specified address family.";
                list af {
                  key "type";
                  description
                    "Configure peer in a specified address family.";
                  leaf type {
                    type bgp:instance-af-type;
                    must "../../../../../afs/af[type = current()]";
                    description
                      "Specify the address family type to set the peer enable.";
                  }
                  container ipv4-unicast {
                    when "../type='ipv4uni' and ../../../../../../../../ni:name!='_public_'";
                    must "../../../../../../../../l3vpn:afs/l3vpn:af[l3vpn:type='ipv4-unicast']";
                    description
                      "Configure IPv4 unicast options.";
                    leaf group-name {
                      type leafref {
                        path "../../../../../../peer-groups/peer-group/name";
                      }
                      must "../../../../../../peer-groups/peer-group[name = current()]/afs/af[type = 'ipv4uni']";
                      must "../../../../../../peer-groups/peer-group[name = current()]/peer-establish-mode = 'static'";
                      description
                        "Configure a name for a peer group. After a peer is deleted from the peer group, the peer is disabled from the address family. The object cannot be modified.";
                      ext:operation-exclude update {
                        description "The node cannot be modified, when the peer already belongs to a peer-group.";
                      }
                    }
                    leaf orf-type {
                      type bgp:bgp-orf-v4-type;
                      must "(../orf-mode='null' and ../orf-type='null') or (../orf-mode!='null' and ../orf-type!='null')";
                      default "null";
                      description
                        "ORF Type.";
                    }
                    leaf orf-mode {
                      type bgp:bgp-orf-mode-type;
                      default "null";
                      description
                        "Configure an outbound route filtering (ORF) mode.";
                    }
                    leaf reflect-client {
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    leaf label-route-capability {
                      type boolean;
                      default "false";
                      description
                        "Enable/disable a device to exchange labeled routes.";
                    }
                    leaf check-tunnel-reachable {
                      when "../label-route-capability='true'";
                      type boolean;
                      default "false";
                      description
                        "Enable/disable tunnel reachability check.";
                    }
                    uses vrf-nexthop-configure-grouping;
                    uses peer-policy-filter-type;
                    leaf allow-as-loop {
                      type uint32 {
                        range "1..10";
                      }
                      description
                        "Allow repetitive local AS numbers. By default, repetitive local AS numbers are not allowed.";
                    }
                    uses default-route-advertise-type;
                    leaf default-route-match-mode {
                      when "../default-route-advertise='true'";
                      type cra-match-mode;
                      default "null";
                      description
                        "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                    }
                    uses ip-prefix-filter-type;
                    uses as-path-filter-type;
                    uses peer-group-acl-name-or-num-type;
                    uses rt-update-interval-type;
                    uses preferred-value-type;
                    leaf substitute-as-enable {
                      type boolean;
                      default "false";
                      description
                        "Enable/disable replace the AS number of a specified peer in the AS_Path attribute with the local AS number. On a PE where AS number replacement is enabled, if an AS number in the AS_Path attribute of a route is same as that of the CE to which the PE advertises the route, the PE replaces the AS number with its own AS number before advertising the route.";
                    }
                    uses soo-grouping;
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      type peer-attr-enable-type;
                      description
                        "Enable/disable BGP to prevents the routes received from an EBGP peer from being broadcast to other peers with the same AS number.";
                    }
                    uses load-balancing-type;
                    uses community-attribute;
                    uses advertise-large-community-type;
                    uses peer-independent-peer-group-type;
                    uses ipv4-default-route-match-conditions-type;
                    uses route-limit-accept-type;
                    uses public-as-only-type;
                    uses peer-public-as-only-import-type;
                    uses path-attr-map-type;
                  }
                  container ipv4-vpn {
                    when "../type = 'ipv4vpn' and ../../../../../../../../ni:name='_public_'";
                    description
                      "Configure IPv4 VPNv4 options.";
                    leaf group-name {
                      type leafref {
                        path "../../../../../../peer-groups/peer-group/name";
                      }
                      must "../../../../../../peer-groups/peer-group[name = current()]/afs/af[type = 'ipv4vpn']";
                      must "../../../../../../peer-groups/peer-group[name = current()]/peer-establish-mode = 'static'";
                      description
                        "Configure a name for a peer group. After a peer is deleted from the peer group, the peer is disabled from the address family. The object cannot be modified.";
                      ext:operation-exclude update {
                        description "The node cannot be modified, when the peer already belongs to a peer-group.";
                      }
                    }
                    leaf advertise-community {
                      type boolean;
                      default "false";
                      description
                        "Enable/disable advertise the community attribute to a peer or a peer group.";
                    }
                    leaf orf-type {
                      type bgp:bgp-orf-v4-type;
                      must "(../orf-mode='null' and ../orf-type='null') or (../orf-mode!='null' and ../orf-type!='null')";
                      default "null";
                      description
                        "ORF Type.";
                    }
                    leaf orf-mode {
                      type bgp:bgp-orf-mode-type;
                      default "null";
                      description
                        "Configure an outbound route filtering (ORF) mode.";
                    }
                    leaf reflect-client {
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    leaf nexthop-configure {
                      type nexthop-configuration-type;
                      description
                        "In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                    }
                    uses peer-policy-filter-type;
                    leaf allow-as-loop {
                      type uint32 {
                        range "1..10";
                      }
                      description
                        "Allow repetitive local AS numbers. By default, repetitive local AS numbers are not allowed.";
                    }
                    leaf aigp {
                      type boolean;
                      default "false";
                      description
                        "Enable/disable route with AIGP attribute advertisement to or from a peer.";
                    }
                    uses peer-add-path-type;
                    uses ip-prefix-filter-type;
                    uses as-path-filter-type;
                    uses peer-group-acl-name-or-num-type;
                    uses rt-update-interval-type;
                    uses preferred-value-type;
                    leaf upe {
                      type boolean;
                      default "false";
                      description
                        "Enable/disable the peer as an underlayer PE (UPE).";
                    }
                    leaf advertise-best-external {
                      type boolean;
                      must "../reflect-client='false' or ../advertise-best-external='false'";
                      must "../add-path-mode='null' or ../advertise-best-external='false'";
                      must "not(../add-path-number and ../advertise-best-external='true')";
                      default "false";
                      description
                        "Enable/disable the device to advertise Best External routes to peers.";
                    }
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      type peer-attr-enable-type;
                      description
                        "Enable/disable BGP to prevents the routes received from an EBGP peer from being broadcast to other peers with the same AS number.";
                    }
                    uses peer-independent-peer-group-type;
                    uses peer-origin-as-validation-type;
                    container default-route-originates {
                      description
                        "Configure advertised default VPNv4 routes.";
                      uses default-route-originate-type;
                    }
                    uses route-limit-type;
                    uses public-as-only-type;
                    uses peer-public-as-only-import-type;
                    uses path-attr-map-type;
                  }
                  container ipv6-unicast {
                    when "../type='ipv6uni' and ../../../../../../../../ni:name!='_public_'";
                    must "../../../../../../../../l3vpn:afs/l3vpn:af[l3vpn:type='ipv6-unicast']";
                    description
                      "Configure IPv6 unicast options.";
                    leaf group-name {
                      type leafref {
                        path "../../../../../../peer-groups/peer-group/name";
                      }
                      must "../../../../../../peer-groups/peer-group[name = current()]/afs/af[type = 'ipv6uni']";
                      must "../../../../../../peer-groups/peer-group[name = current()]/peer-establish-mode = 'static'";
                      description
                        "Configure a name for a peer group. After a peer is deleted from the peer group, the peer is disabled from the address family. The object cannot be modified.";
                      ext:operation-exclude update {
                        description "The node cannot be modified, when the peer already belongs to a peer-group.";
                      }
                    }
                    uses community-attribute;
                    uses advertise-large-community-type;
                    leaf keep-all-routes {
                      type boolean;
                      default "false";
                      description
                        "Enable/disable saving all the updated information about BGP routes from a specified peer or peer group after a BGP connection is established, even though these BGP routes fail to match the routing policy on the ingress. By default, the updated information about BGP routes from a specified peer is saved only when the routes match the routing policy on the ingress. If a router supports route refreshing, this option is not required.";
                    }
                    leaf peer-as-check {
                      type peer-attr-enable-type;
                      description
                        "Enable/disable BGP to prevents the routes received from an EBGP peer from being broadcast to other peers with the same AS number.";
                    }
                    leaf reflect-client {
                      type boolean;
                      default "false";
                      description
                        "Enable/disable the local device as a route reflector (RR) and a peer or peer group as its client. This configuration is applicable between IBGP peers only. The configurations of RRs and its clients in an address family are valid only in this address family. Therefore, it is recommended to configure RRs and its clients in the specified address family that is required.";
                    }
                    uses preferred-value-type;
                    uses peer-policy-filter-type;
                    leaf allow-as-loop {
                      type uint32 {
                        range "1..10";
                      }
                      description
                        "Allow repetitive local AS numbers. By default, repetitive local AS numbers are not allowed.";
                    }
                    uses vrf-nexthop-configure-grouping;
                    leaf substitute-as-enable {
                      type boolean;
                      default "false";
                      description
                        "Enable/disable replace the AS number of a specified peer in the AS_Path attribute with the local AS number. On a PE where AS number replacement is enabled, if an AS number in the AS_Path attribute of a route is same as that of the CE to which the PE advertises the route, the PE replaces the AS number with its own AS number before advertising the route.";
                    }
                    uses soo-grouping;
                    leaf default-route-match-mode {
                      when "../default-route-advertise='true'";
                      type cra-match-mode;
                      default "null";
                      description
                        "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                    }
                    uses as-path-filter-type;
                    uses ipv6-prefix-filter-type;
                    uses peer-group-acl6-name-or-num-type;
                    uses default-route-advertise-type;
                    uses rt-update-interval-type;
                    uses ipv6-default-route-match-conditions-type;
                    uses route-limit-type;
                    uses public-as-only-type;
                    uses peer-public-as-only-import-type;
                    uses path-attr-map-type;
                  }
                }
              }
              container ssl-policy {
                when "../../../../../../ni:name='_public_'";
                description
                  "Configure SSL policy for BGP peer.";
                uses peer-ssl-policy-grouping {
                  refine role {
                    must "(.='client' and ../../connect-mode != 'listen-only') or (.='server' and ../../connect-mode != 'connect-only') or (.= 'disable')";
                  }
                  refine server-certificate {
                    must "(../role = 'server') or (../role = 'disable') or (../role = 'client' and ../server-certificate != 'enable') or (not(../role) and not(../../bgp:group-name)) or (not(../role) and ../../bgp:group-name and  (../../../../bgp:peer-groups/bgp:peer-group[bgp:name=current()/../../bgp:group-name]/bgp:ssl-policy/bgp:role = 'server' or not(../../../../bgp:peer-groups/bgp:peer-group[bgp:name=current()/../../bgp:group-name]/bgp:ssl-policy/bgp:role))) or (not(../role) and ../../bgp:group-name and  ../../../../bgp:peer-groups/bgp:peer-group[bgp:name=current()/../../bgp:group-name]/bgp:ssl-policy/bgp:role = 'client' and ../server-certificate != 'enable')";
                  }
                }
              }
            }
          }
          container peer-states {
            config false;
            description
              "List of BGP peers.";
            list peer-state {
              key "address af-type establish-mode";
              description
                "Operational state of BGP peer.";
              leaf address {
                type inet:ip-address-no-zone;
                description
                  "Connection address of a peer, which can be an IPv4 or IPv6 address.";
              }
              leaf af-type {
                type bgp:instance-af-type;
                description
                  "The address family type of the peer.";
              }
              leaf establish-mode {
                type inst-peer-establish-mode;
                description
                  "Specify mode in which a BGP peer is established.";
              }
              uses peer-state-attr-grouping;
            }
          }
          container peer-total-numbers {
            config false;
            description
              "List of BGP peer statistics.";
            list peer-total-number {
              key "af-type";
              description
                "Operational data of BGP peers number.";
              leaf af-type {
                type bgp:instance-af-type;
                description
                  "Address family type.";
              }
              leaf static-peer-number {
                type uint32;
                description
                  "Total number of static peers.";
              }
              leaf static-peer-established-number {
                type uint32;
                description
                  "Total number of static peers that have been established.";
              }
              leaf dynamic-peer-number {
                type uint32;
                description
                  "Total number of dynamic peers.";
              }
            }
          }
          container dynamic-peer-prefixes {
            description
              "List of IP prefixes from which a dynamic BGP peer group listens for BGP connection requests.";
            list dynamic-peer-prefix {
              key "address mask-length peer-group";
              description
                "Configure an IP prefix from which a dynamic BGP peer group listens for BGP connection requests.";
              leaf address {
                type inet:ip-address-no-zone;
                description
                  "Network segment address for a dynamic peer connection.";
              }
              leaf mask-length {
                type uint8 {
                  range "0..128";
                }
                description
                  "Mask length of a network segment.";
              }
              leaf peer-group {
                type leafref {
                  path "../../../peer-groups/peer-group/name";
                }
                must "../../../peer-groups/peer-group[name = current()]/peer-establish-mode = 'dynamic'";
                must "../../../peer-groups/peer-group[name = current()]/listen-as or ../../../peer-groups/peer-group[name = current()]/listen-as-segments/listen-as-segment";
                description
                  "The peer-group within which the dynamic neighbor will be configured.";
              }
            }
          }
        }
      }
    }
  }
}
