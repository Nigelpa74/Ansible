/*
Copyright (C) 2025 Huawei Technologies Co., Ltd. All rights reserved.
*/
module huawei-netconf-client-deviations-ar5710s {
  namespace "urn:huawei:yang:huawei-netconf-client-deviations-ar5710s";
  prefix netconf-client-devs-ar5710s;

  import huawei-netconf-client {
    prefix netconf-client;
  }

  organization
    "Huawei Technologies Co., Ltd.";
  contact
    "Huawei Industrial Base
     Bantian, Longgang
     Shenzhen 518129
     People's Republic of China
     Website: http://www.huawei.com
     Email: support@huawei.com";
  description
    "This module defines deviation statements for huawei-netconf-client module.";

  revision 2025-02-24 {
    description
      "Initial revision.";
    reference "Huawei private.";
  }

  deviation "/netconf-client:netconf-client/netconf-client:connections" {
    deviate not-supported;
  }
  deviation "/netconf-client:netconf-client/netconf-client:data-sync-results" {
    deviate not-supported;
  }
}
