/*
Copyright (C) 2025 Huawei Technologies Co., Ltd. All rights reserved.
*/
module huawei-notifications-deviations-ar5710s {
  namespace "urn:huawei:yang:huawei-notifications-deviations-ar5710s";
  prefix ncEvent-devs-ar5710s;

  import notifications {
    prefix ncEvent;
  }

  organization
    "Huawei Technologies Co., Ltd.";
  contact
    "Huawei Industrial Base
     Bantian, Longgang
     Shenzhen 518129
     People's Republic of China
     Website: http://www.huawei.com
     Email: support@huawei.com";
  description
    "This module defines deviation statements for notifications module.";

  revision 2025-02-24 {
    description
      "Initial revision.";
    reference "Huawei private.";
  }

  deviation "/ncEvent:notification" {
    deviate not-supported;
  }
}
