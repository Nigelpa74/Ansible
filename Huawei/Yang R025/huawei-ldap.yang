/*
Copyright (C) 2020-2025 Huawei Technologies Co., Ltd. All rights reserved.
*/
module huawei-ldap {
  yang-version 1;
  namespace "urn:huawei:yang:huawei-ldap";
  prefix ldap;
  import ietf-inet-types {
    prefix inet;
  }
  import huawei-pub-type {
    prefix pub-type;
  }
  import huawei-extension {
    prefix ext;
  }
  import huawei-aaa {
    prefix aaa;
  }
  organization
    "Huawei Technologies Co., Ltd.";
  contact
    "Huawei Industrial Base
    Bantian, Longgang
    Shenzhen 518129
    People's Republic of China
    Website: http://www.huawei.com
    Email: support@huawei.com";
  description
    "This module contains a collection of YANG definitions for
    configuring LDAP implementations.
    Redistribution and use in source and binary forms, with or
    without modification, is permitted pursuant to, and subject
    to the license terms contained in, the Simplified BSD License
    set forth in Section 4.c of the IETF Trust's Legal Provisions
    Relating to IETF Documents.";
  revision 2025-08-23 {
    description
      "1.Add dynamic-default of port.
       2.Modify ldap-server-parameter.";
    reference
      "Huawei private.";
  }
  revision 2022-05-05 {
    description
      "Modify length of base dn and description.";
    reference
      "Huawei private.";
  }
  revision 2020-04-09 {
    description
      "Modify description.";
    reference
      "Huawei private.";
  }
  revision 2020-03-16 {
    description
      "Initial revision.";
    reference
      "Huawei private.";
  }
  ext:task-name "ldap";
  grouping ldap-server-parameter {
    description
      "Parameters of LDAP servers.";
    leaf server-ip-address {
      type inet:ip-address;
      description
        "Specifies the IP address of an LDAP authentication server.";
    }
    leaf port {
      when "../server-ip-address";
      type inet:port-number;
      ext:dynamic-default {
        ext:default-value 636 {
          when "../ssl='true'";
          description
            "The default value is 636 when ssl is true.";
        }
        ext:default-value 389 {
          when "../ssl='false'";
          description
            "The default value is 389 when ssl is false.";
        }
      }
      description
        "Specifies the port number of an LDAP authentication server.";
    }
    leaf ssl {
      when "../server-ip-address";
      type boolean;
      default "false";
      description
        "Enable/disable LDAP over SSL when the LDAP authentication between the device and LDAP server.";
    }
  }
  container ldap {
    description
      "LDAP related configuration and state data.";
    container global {
      description
        "Configure LDAP client related global function.";
      leaf-list ssl-version {
        type enumeration {
          enum "tlsv1.1" {
            value 1;
            description
              "Sets the SSL protocol version used for the interaction between the device and LDAP server to TLS1.1.";
          }
          enum "tlsv1.2" {
            value 2;
            description
              "Sets the SSL protocol version used for the interaction between the device and LDAP server to TLS1.2.";
          }
        }
        description
          "Configure the SSL protocol version used for the interaction between the device and LDAP server.";
      }
    }
    container ldap-servers {
      description
        "List of LDAP client related configuration and state data.";
      list ldap-server {
        key "name";
        description
          "Configure LDAP client related configuration and state data list.";
        leaf name {
          type string {
            length "1..32";
          }
          description
            "Specifies the name of an LDAP server template. The value is a case-sensitive.";
        }
        leaf-list base-dn {
          type string {
            length "1..129";
          }
          description
            "Configure the Base DN of an LDAP authentication server.";
        }
        leaf bind-user {
          type boolean;
          default "true";
          description
            "Enable/disable user binding during LDAP authorization.";
        }
        leaf server-type {
          type enumeration {
            enum "ad-ldap" {
              value 1;
              description
                "Sets the LDAP server type to AD LDAP.";
            }
            enum "ibm-tivoli" {
              value 2;
              description
                "Sets the LDAP server type to IBM Tivoli LDAP.";
            }
            enum "open-ldap" {
              value 3;
              description
                "Sets the LDAP server type to OPEN LDAP.";
            }
            enum "sun-one" {
              value 4;
              description
                "Sets the LDAP server type to Sun ONE LDAP.";
            }
          }
          default "ad-ldap";
          description
            "Set the LDAP server type.";
        }
        leaf user-filter {
          type string {
            length "1..63";
          }
          description
            "Specifies the user filtering field.";
        }
        leaf group-filter {
          type string {
            length "1..63";
          }
          description
            "Specifies the group filtering field.";
        }
        leaf mobile-number-filter {
          type string {
            length "1..63";
          }
          description
            "Specifies the mobile number filtering field.";
        }
        leaf time-stamp-filter {
          type string {
            length "1..63";
          }
          description
            "Specifies the timestamp attribute filtering field.";
        }
        leaf authentication-filter {
          type string {
            length "1..256";
          }
          description
            "Configure filtering parameters for the LDAP authentication server.";
        }
        container ip-address-filter {
          description
            "Configure the ip address field for an LDAP server.";
          leaf ip-field {
            type string {
              length "1..63";
            }
            description
              "Specifies the ip address filtering field.";
          }
          leaf mask-field {
            type string {
              length "1..63";
            }
            description
              "Specifies the mask filtering field.";
          }
        }
        container primary-authentication-server {
          description
            "Configure the primary LDAP authentication server.";
          uses ldap-server-parameter;
        }
        container secondary-authentication-server {
          description
            "Configure the secondary LDAP authentication server.";
          uses ldap-server-parameter;
        }
        container thirdly-authentication-server {
          description
            "Configure the third LDAP authentication server.";
          uses ldap-server-parameter;
        }
        choice access-parameters {
          description
            "Access parameters.";
          case prohibit-anonymous-access {
            description
              "Prohibit anonymous access parameters.";
            leaf with-base-dn {
              type boolean;
              default "true";
              description
                "Enable/disable attaching the Base DN to an administrator DN during LDAP authentication.";
            }
            container manager {
              description
                "Configure the administrator DN and password of an LDAP authentication server.";
              leaf manager-dn {
                type string {
                  length "1..65";
                }
                description
                  "Specifies the administrator DN of an LDAP authentication server.";
              }
              leaf password {
                type pub-type:password-extend;
                description
                  "Specifies the administrator password of an LDAP authentication server.";
              }
              leaf repassword {
                type pub-type:password-extend;
                description
                  "Re-enters the password of an LDAP administrator.";
              }
            }
            container manager-password {
              description
                "Configure to modifying the administrator password of an LDAP authentication server.";
              leaf password {
                type pub-type:password-extend;
                description
                  "Specifies the administrator password of an LDAP authentication server.";
              }
              leaf repassword {
                type pub-type:password-extend;
                description
                  "Re-enters the administrator password of an LDAP authentication server.";
              }
            }
          }
          case allow-anonymous-access {
            description
              "Allow anonymous access parameters.";
            leaf manager-anonymous-enable {
              type boolean;
              default "false";
              description
                "Enable/disable administrators to access an LDAP server anonymously.";
            }
          }
        }
        choice source-type {
          description
            "Configures the source IP address that a device uses when sending packets to the LDAP server.";
          case loopback {
            description
              "Case LOOPBACK.";
            leaf loopback-number {
              type int32 {
                range "0..2147483647";
              }
              description
                "Specifies the IP address of a loopback interface as the source IP address that the device uses when sending packets to the LDAP server.";
            }
          }
          case source-ip {
            description
              "Case source ip.";
            leaf ip-address {
              type inet:ip-address-no-zone;
              description
                "Specifies an IP address as the source IP address that the device uses when sending packets to the LDAP server.";
            }
          }
          case vlanif {
            description
              "Case VLANIF.";
            leaf vlanif-id {
              type int16 {
                range "1..4094";
              }
              description
                "Specifies the IP address of a VLANIF interface as the source IP address that the device uses when sending packets to the LDAP server.";
            }
          }
        }
      }
    }
  }
  augment /aaa:aaa/aaa:domains/aaa:domain {
    description
      "Augment this aaa domain.";
    container ldap {
      description
        "Configure an LDAP function for an authentication domain.";
      leaf ldap-server {
        type leafref {
          path "/ldap:ldap/ldap:ldap-servers/ldap:ldap-server/ldap:name";
        }
        description
          "Specifies the name of an LDAP server template.";
      }
    }
  }
}
