/*
Copyright (C) 2025 Huawei Technologies Co., Ltd. All rights reserved.
*/
module huawei-pic-notification-deviations-ar5710s {
  namespace "urn:huawei:yang:huawei-pic-notification-deviations-ar5710s";
  prefix pic-notification-devs-ar5710s;

  import huawei-pic-notification {
    prefix pic-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-pic-notification module.";

  revision 2025-02-24 {
    description
      "Initial revision.";
    reference "Huawei private.";
  }

  deviation "/pic-notification:au-hp" {
    deviate not-supported;
  }
  deviation "/pic-notification:au-hp-resume" {
    deviate not-supported;
  }
  deviation "/pic-notification:b1-default-exceed" {
    deviate not-supported;
  }
  deviation "/pic-notification:b1-default-exceed-resume" {
    deviate not-supported;
  }
  deviation "/pic-notification:bip2-default-exceed" {
    deviate not-supported;
  }
  deviation "/pic-notification:bip2-default-exceed-resume" {
    deviate not-supported;
  }
  deviation "/pic-notification:b3-default-exceed" {
    deviate not-supported;
  }
  deviation "/pic-notification:b3-default-exceed-resume" {
    deviate not-supported;
  }
  deviation "/pic-notification:channel-loopback" {
    deviate not-supported;
  }
  deviation "/pic-notification:channel-loopback-resume" {
    deviate not-supported;
  }
  deviation "/pic-notification:cpos-e1-rai-signal" {
    deviate not-supported;
  }
  deviation "/pic-notification:cpos-e1-rai-signal-resume" {
    deviate not-supported;
  }
  deviation "/pic-notification:downstream-e1-cpos" {
    deviate not-supported;
  }
  deviation "/pic-notification:downstream-e1-cpos-resume" {
    deviate not-supported;
  }
  deviation "/pic-notification:loss-of-frame-e1-cpos" {
    deviate not-supported;
  }
  deviation "/pic-notification:loss-of-frame-e1-cpos-resume" {
    deviate not-supported;
  }
  deviation "/pic-notification:loss-multiframe-e1-cpos" {
    deviate not-supported;
  }
  deviation "/pic-notification:loss-multiframe-e1-cpos-resume" {
    deviate not-supported;
  }
  deviation "/pic-notification:upstream-e1-cpos" {
    deviate not-supported;
  }
  deviation "/pic-notification:upstream-e1-cpos-resume" {
    deviate not-supported;
  }
  deviation "/pic-notification:remote-indication-e1" {
    deviate not-supported;
  }
  deviation "/pic-notification:remote-indication-e1-resume" {
    deviate not-supported;
  }
  deviation "/pic-notification:downstream-e1" {
    deviate not-supported;
  }
  deviation "/pic-notification:downstream-e1-resume" {
    deviate not-supported;
  }
  deviation "/pic-notification:errored-second-exceed" {
    deviate not-supported;
  }
  deviation "/pic-notification:errored-second-exceed-resume" {
    deviate not-supported;
  }
  deviation "/pic-notification:loss-multiframe-e1" {
    deviate not-supported;
  }
  deviation "/pic-notification:loss-multiframe-e1-resume" {
    deviate not-supported;
  }
  deviation "/pic-notification:upstream-e1" {
    deviate not-supported;
  }
  deviation "/pic-notification:upstream-e1-resume" {
    deviate not-supported;
  }
  deviation "/pic-notification:remote-e3" {
    deviate not-supported;
  }
  deviation "/pic-notification:remote-e3-resume" {
    deviate not-supported;
  }
  deviation "/pic-notification:upstream-e3" {
    deviate not-supported;
  }
  deviation "/pic-notification:upstream-e3-resume" {
    deviate not-supported;
  }
  deviation "/pic-notification:j0-trace-mismatch" {
    deviate not-supported;
  }
  deviation "/pic-notification:j0-trace-mismatch-resume" {
    deviate not-supported;
  }
  deviation "/pic-notification:signal-mismatch-lp" {
    deviate not-supported;
  }
  deviation "/pic-notification:signal-mismatch-lp-resume" {
    deviate not-supported;
  }
  deviation "/pic-notification:trace-mismatch-lp" {
    deviate not-supported;
  }
  deviation "/pic-notification:trace-mismatch-lp-resume" {
    deviate not-supported;
  }
  deviation "/pic-notification:unequipped-lp" {
    deviate not-supported;
  }
  deviation "/pic-notification:unequipped-lp-resume" {
    deviate not-supported;
  }
  deviation "/pic-notification:out-of-lock-clock" {
    deviate not-supported;
  }
  deviation "/pic-notification:out-of-lock-clock-resume" {
    deviate not-supported;
  }
  deviation "/pic-notification:tributary-unit-lp" {
    deviate not-supported;
  }
  deviation "/pic-notification:tributary-unit-lp-resume" {
    deviate not-supported;
  }
  deviation "/pic-notification:v5-virtual-container" {
    deviate not-supported;
  }
  deviation "/pic-notification:v5-virtual-container-resume" {
    deviate not-supported;
  }
  deviation "/pic-notification:loss-au-lp" {
    deviate not-supported;
  }
  deviation "/pic-notification:loss-au-lp-resume" {
    deviate not-supported;
  }
  deviation "/pic-notification:remote-defect-lp" {
    deviate not-supported;
  }
  deviation "/pic-notification:remote-defect-lp-resume" {
    deviate not-supported;
  }
  deviation "/pic-notification:remote-failure-lp" {
    deviate not-supported;
  }
  deviation "/pic-notification:remote-failure-lp-resume" {
    deviate not-supported;
  }
  deviation "/pic-notification:port-license-act-fail" {
    deviate not-supported;
  }
  deviation "/pic-notification:port-license-act-success" {
    deviate not-supported;
  }
  deviation "/pic-notification:resource-dead-line" {
    deviate not-supported;
  }
  deviation "/pic-notification:resource-dead-line-resume" {
    deviate not-supported;
  }
  deviation "/pic-notification:upstream-pcm" {
    deviate not-supported;
  }
  deviation "/pic-notification:upstream-pcm-resume" {
    deviate not-supported;
  }
  deviation "/pic-notification:au-pointer-loss-lp" {
    deviate not-supported;
  }
  deviation "/pic-notification:au-pointer-loss-lp-resume" {
    deviate not-supported;
  }
  deviation "/pic-notification:b1-configured-exceed" {
    deviate not-supported;
  }
  deviation "/pic-notification:b1-configured-exceed-resume" {
    deviate not-supported;
  }
  deviation "/pic-notification:b2-configured-exceed" {
    deviate not-supported;
  }
  deviation "/pic-notification:b2-configured-exceed-resume" {
    deviate not-supported;
  }
  deviation "/pic-notification:b3-configured-exceed" {
    deviate not-supported;
  }
  deviation "/pic-notification:b3-configured-exceed-resume" {
    deviate not-supported;
  }
  deviation "/pic-notification:fog-abnormal" {
    deviate not-supported;
  }
  deviation "/pic-notification:fog-abnormal-resume" {
    deviate not-supported;
  }
  deviation "/pic-notification:gate-abnormal" {
    deviate not-supported;
  }
  deviation "/pic-notification:gate-abnormal-resume" {
    deviate not-supported;
  }
  deviation "/pic-notification:gps-module-insert" {
    deviate not-supported;
  }
  deviation "/pic-notification:gps-module-remove" {
    deviate not-supported;
  }
  deviation "/pic-notification:trace-unstable-lp" {
    deviate not-supported;
  }
  deviation "/pic-notification:trace-unstable-lp-resume" {
    deviate not-supported;
  }
  deviation "/pic-notification:humidity-abnormal" {
    deviate not-supported;
  }
  deviation "/pic-notification:humidity-abnormal-resume" {
    deviate not-supported;
  }
  deviation "/pic-notification:bad-bytes-error-rising" {
    deviate not-supported;
  }
  deviation "/pic-notification:bad-bytes-error-resume" {
    deviate not-supported;
  }
  deviation "/pic-notification:crc-error-rising" {
    deviate not-supported;
  }
  deviation "/pic-notification:crc-error-resume" {
    deviate not-supported;
  }
  deviation "/pic-notification:pause-frame-rising" {
    deviate not-supported;
  }
  deviation "/pic-notification:pause-frame-resume" {
    deviate not-supported;
  }
  deviation "/pic-notification:post-fec-error-rising" {
    deviate not-supported;
  }
  deviation "/pic-notification:post-fec-error-resume" {
    deviate not-supported;
  }
  deviation "/pic-notification:sdh-b2-error-rising" {
    deviate not-supported;
  }
  deviation "/pic-notification:sdh-b2-error-resume" {
    deviate not-supported;
  }
  deviation "/pic-notification:sdh-error-rising" {
    deviate not-supported;
  }
  deviation "/pic-notification:sdh-error-resume" {
    deviate not-supported;
  }
  deviation "/pic-notification:symbol-error-interval" {
    deviate not-supported;
  }
  deviation "/pic-notification:symbol-error-interval-resume" {
    deviate not-supported;
  }
  deviation "/pic-notification:tx-pause-frame-exceed" {
    deviate not-supported;
  }
  deviation "/pic-notification:tx-pause-frame-exceed-resume" {
    deviate not-supported;
  }
  deviation "/pic-notification:input-error-exceed" {
    deviate not-supported;
  }
  deviation "/pic-notification:input-error-exceed-resume" {
    deviate not-supported;
  }
  deviation "/pic-notification:multi-section" {
    deviate not-supported;
  }
  deviation "/pic-notification:multi-section-resume" {
    deviate not-supported;
  }
  deviation "/pic-notification:laser-auto-shut" {
    deviate not-supported;
  }
  deviation "/pic-notification:laser-auto-shut-resume" {
    deviate not-supported;
  }
  deviation "/pic-notification:laser-no-fited" {
    deviate not-supported;
  }
  deviation "/pic-notification:laser-no-fited-resume" {
    deviate not-supported;
  }
  deviation "/pic-notification:laser-shut" {
    deviate not-supported;
  }
  deviation "/pic-notification:laser-shut-resume" {
    deviate not-supported;
  }
  deviation "/pic-notification:license-resource-lack" {
    deviate not-supported;
  }
  deviation "/pic-notification:license-resource-lack-resume" {
    deviate not-supported;
  }
  deviation "/pic-notification:local-fault" {
    deviate not-supported;
  }
  deviation "/pic-notification:local-fault-resume" {
    deviate not-supported;
  }
  deviation "/pic-notification:multi-loss-lp" {
    deviate not-supported;
  }
  deviation "/pic-notification:multi-loss-lp-resume" {
    deviate not-supported;
  }
  deviation "/pic-notification:port-loopback" {
    deviate not-supported;
  }
  deviation "/pic-notification:port-loopback-resume" {
    deviate not-supported;
  }
  deviation "/pic-notification:signal-loss" {
    deviate not-supported;
  }
  deviation "/pic-notification:signal-loss-resume" {
    deviate not-supported;
  }
  deviation "/pic-notification:remote-defect-ms" {
    deviate not-supported;
  }
  deviation "/pic-notification:remote-defect-ms-resume" {
    deviate not-supported;
  }
  deviation "/pic-notification:negotiation-failed" {
    deviate not-supported;
  }
  deviation "/pic-notification:negotiation-failed-resume" {
    deviate not-supported;
  }
  deviation "/pic-notification:odu-indication-signal" {
    deviate not-supported;
  }
  deviation "/pic-notification:odu-indication-signal-resume" {
    deviate not-supported;
  }
  deviation "/pic-notification:odu-locked-signal" {
    deviate not-supported;
  }
  deviation "/pic-notification:odu-locked-signal-resume" {
    deviate not-supported;
  }
  deviation "/pic-notification:odu-open-connection" {
    deviate not-supported;
  }
  deviation "/pic-notification:odu-open-connection-resume" {
    deviate not-supported;
  }
  deviation "/pic-notification:odu-signal-degrade" {
    deviate not-supported;
  }
  deviation "/pic-notification:odu-signal-degrade-resume" {
    deviate not-supported;
  }
  deviation "/pic-notification:out-of-frame" {
    deviate not-supported;
  }
  deviation "/pic-notification:out-of-frame-resume" {
    deviate not-supported;
  }
  deviation "/pic-notification:optical-not-match" {
    deviate not-supported;
  }
  deviation "/pic-notification:optical-not-match-resume" {
    deviate not-supported;
  }
  deviation "/pic-notification:optical-not-authorized" {
    deviate not-supported;
  }
  deviation "/pic-notification:optical-not-authorized-resume" {
    deviate not-supported;
  }
  deviation "/pic-notification:otu-indication-signal" {
    deviate not-supported;
  }
  deviation "/pic-notification:otu-indication-signal-resume" {
    deviate not-supported;
  }
  deviation "/pic-notification:otu-loss-of-multiframe" {
    deviate not-supported;
  }
  deviation "/pic-notification:otu-loss-of-multiframe-resume" {
    deviate not-supported;
  }
  deviation "/pic-notification:otu-signal-degrade" {
    deviate not-supported;
  }
  deviation "/pic-notification:otu-signal-degrade-resume" {
    deviate not-supported;
  }
  deviation "/pic-notification:otu-signal-fail" {
    deviate not-supported;
  }
  deviation "/pic-notification:otu-signal-fail-resume" {
    deviate not-supported;
  }
  deviation "/pic-notification:output-error-exceed" {
    deviate not-supported;
  }
  deviation "/pic-notification:output-error-exceed-resume" {
    deviate not-supported;
  }
  deviation "/pic-notification:signal-lp" {
    deviate not-supported;
  }
  deviation "/pic-notification:signal-lp-resume" {
    deviate not-supported;
  }
  deviation "/pic-notification:bip8-sd-error" {
    deviate not-supported;
  }
  deviation "/pic-notification:bip8-sd-error-resume" {
    deviate not-supported;
  }
  deviation "/pic-notification:crc-error-exceed" {
    deviate not-supported;
  }
  deviation "/pic-notification:crc-error-exceed-resume" {
    deviate not-supported;
  }
  deviation "/pic-notification:crc-fcs-exceed" {
    deviate not-supported;
  }
  deviation "/pic-notification:crc-fcs-exceed-resume" {
    deviate not-supported;
  }
  deviation "/pic-notification:crc-packet-error-ratio" {
    deviate not-supported;
  }
  deviation "/pic-notification:crc-packet-error-ratio-resume" {
    deviate not-supported;
  }
  deviation "/pic-notification:crc-error-warning" {
    deviate not-supported;
  }
  deviation "/pic-notification:crc-error-warning-resume" {
    deviate not-supported;
  }
  deviation "/pic-notification:crc-mac-fcs-sd" {
    deviate not-supported;
  }
  deviation "/pic-notification:crc-mac-fcs-sd-resume" {
    deviate not-supported;
  }
  deviation "/pic-notification:path-trace-mismatch" {
    deviate not-supported;
  }
  deviation "/pic-notification:path-trace-mismatch-resume" {
    deviate not-supported;
  }
  deviation "/pic-notification:trans-mode-inconsistent" {
    deviate not-supported;
  }
  deviation "/pic-notification:trans-mode-inconsistent-resume" {
    deviate not-supported;
  }
  deviation "/pic-notification:port-mode-change" {
    deviate not-supported;
  }
  deviation "/pic-notification:port-physical-down" {
    deviate not-supported;
  }
  deviation "/pic-notification:port-physical-up" {
    deviate not-supported;
  }
  deviation "/pic-notification:physical-rate-degrade" {
    deviate not-supported;
  }
  deviation "/pic-notification:physical-rate-degrade-resume" {
    deviate not-supported;
  }
  deviation "/pic-notification:traffic-fall-receive" {
    deviate not-supported;
  }
  deviation "/pic-notification:traffic-fall-receive-resume" {
    deviate not-supported;
  }
  deviation "/pic-notification:traffic-fall-transmit" {
    deviate not-supported;
  }
  deviation "/pic-notification:traffic-fall-transmit-resume" {
    deviate not-supported;
  }
  deviation "/pic-notification:port-type-change" {
    deviate not-supported;
  }
  deviation "/pic-notification:payload-mismatch-hp" {
    deviate not-supported;
  }
  deviation "/pic-notification:payload-mismatch-hp-resume" {
    deviate not-supported;
  }
  deviation "/pic-notification:remote-defect-hp" {
    deviate not-supported;
  }
  deviation "/pic-notification:remote-defect-hp-resume" {
    deviate not-supported;
  }
  deviation "/pic-notification:trace-mismatch-hp" {
    deviate not-supported;
  }
  deviation "/pic-notification:trace-mismatch-hp-resume" {
    deviate not-supported;
  }
  deviation "/pic-notification:unequipped-hp" {
    deviate not-supported;
  }
  deviation "/pic-notification:unequipped-hp-resume" {
    deviate not-supported;
  }
  deviation "/pic-notification:remote-defect" {
    deviate not-supported;
  }
  deviation "/pic-notification:remote-defect-resume" {
    deviate not-supported;
  }
  deviation "/pic-notification:remote-fault" {
    deviate not-supported;
  }
  deviation "/pic-notification:remote-fault-resume" {
    deviate not-supported;
  }
  deviation "/pic-notification:ms-b2-degrade" {
    deviate not-supported;
  }
  deviation "/pic-notification:ms-b2-degrade-resume" {
    deviate not-supported;
  }
  deviation "/pic-notification:section-alignment" {
    deviate not-supported;
  }
  deviation "/pic-notification:section-alignment-resume" {
    deviate not-supported;
  }
  deviation "/pic-notification:tim-trace-mismatch" {
    deviate not-supported;
  }
  deviation "/pic-notification:tim-trace-mismatch-resume" {
    deviate not-supported;
  }
  deviation "/pic-notification:cas-abnormal" {
    deviate not-supported;
  }
  deviation "/pic-notification:cas-abnormal-resume" {
    deviate not-supported;
  }
  deviation "/pic-notification:optical-amplifier-gain-high" {
    deviate not-supported;
  }
  deviation "/pic-notification:optical-amplifier-gain-high-resume" {
    deviate not-supported;
  }
  deviation "/pic-notification:optical-amplifier-gain-low" {
    deviate not-supported;
  }
  deviation "/pic-notification:optical-amplifier-gain-low-resume" {
    deviate not-supported;
  }
  deviation "/pic-notification:port-group-mode-invalid" {
    deviate not-supported;
  }
  deviation "/pic-notification:port-group-mode-invalid-resume" {
    deviate not-supported;
  }
  deviation "/pic-notification:physical-port-packet-loss" {
    deviate not-supported;
  }
  deviation "/pic-notification:physical-port-packet-loss-resume" {
    deviate not-supported;
  }
  deviation "/pic-notification:port-group-optical-cfg-inconsistent" {
    deviate not-supported;
  }
  deviation "/pic-notification:port-group-optical-cfg-inconsistent-resume" {
    deviate not-supported;
  }
  deviation "/pic-notification:port-group-split-type-diff" {
    deviate not-supported;
  }
  deviation "/pic-notification:port-group-split-type-diff-resume" {
    deviate not-supported;
  }
  deviation "/pic-notification:port-down-hold-time-flapping" {
    deviate not-supported;
  }
  deviation "/pic-notification:port-down-hold-time-flapping-resume" {
    deviate not-supported;
  }
  deviation "/pic-notification:port-bandwidth-limited" {
    deviate not-supported;
  }
  deviation "/pic-notification:port-bandwidth-limited-resume" {
    deviate not-supported;
  }
}
