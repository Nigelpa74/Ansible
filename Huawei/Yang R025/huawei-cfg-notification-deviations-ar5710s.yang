/*
Copyright (C) 2025 Huawei Technologies Co., Ltd. All rights reserved.
*/
module huawei-cfg-notification-deviations-ar5710s {
  namespace "urn:huawei:yang:huawei-cfg-notification-deviations-ar5710s";
  prefix cfg-notification-devs-ar5710s;

  import huawei-cfg-notification {
    prefix cfg-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-cfg-notification module.";

  revision 2025-02-24 {
    description
      "Initial revision.";
    reference "Huawei private.";
  }

  deviation "/cfg-notification:cfg-restore-fail" {
    deviate not-supported;
  }
  deviation "/cfg-notification:cfg-restore-success" {
    deviate not-supported;
  }
  deviation "/cfg-notification:config-inconsistent" {
    deviate not-supported;
  }
  deviation "/cfg-notification:config-inconsistent-resume" {
    deviate not-supported;
  }
  deviation "/cfg-notification:next-startup-file-inconsistent" {
    deviate not-supported;
  }
  deviation "/cfg-notification:next-startup-file-inconsistent-resume" {
    deviate not-supported;
  }
  deviation "/cfg-notification:cfg-backup-failure" {
    deviate not-supported;
  }
  deviation "/cfg-notification:cfg-backup-failure-clear" {
    deviate not-supported;
  }
}
