/*
Copyright (C) 2025 Huawei Technologies Co., Ltd. All rights reserved.
*/
module huawei-apn-deviations-ar5710s {
  namespace "urn:huawei:yang:huawei-apn-deviations-ar5710s";
  prefix apn-devs-ar5710s;

  import huawei-apn {
    prefix apn;
  }

  organization
    "Huawei Technologies Co., Ltd.";
  contact
    "Huawei Industrial Base
     Bantian, Longgang
     Shenzhen 518129
     People's Republic of China
     Website: http://www.huawei.com
     Email: support@huawei.com";
  description
    "This module defines deviation statements for huawei-apn module.";

  revision 2025-02-24 {
    description
      "Initial revision.";
    reference "Huawei private.";
  }

  deviation "/apn:apn" {
    deviate not-supported;
  }
}
