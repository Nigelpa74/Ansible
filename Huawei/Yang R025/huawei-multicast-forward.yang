/*
Copyright (C) 2019-2025 Huawei Technologies Co., Ltd. All rights reserved.
*/
module huawei-multicast-forward {
  yang-version 1;
  namespace "urn:huawei:yang:huawei-multicast-forward";
  prefix multicast-forward;
  import huawei-pub-type {
    prefix pub-type;
  }
  import huawei-network-instance {
    prefix ni;
  }
  import huawei-qos {
    prefix qos;
  }
  import huawei-ifm {
    prefix ifm;
  }
  import ietf-inet-types {
    prefix inet;
  }
  import huawei-extension {
    prefix ext;
  }
  import huawei-devm {
    prefix devm;
  }
  import huawei-bd {
    prefix bd;
  }
  import huawei-l2vpn {
    prefix l2vpn;
  }
  import huawei-vlan {
    prefix vlan;
  }
  import huawei-ethernet {
    prefix ethernet;
  }
  organization
    "Huawei Technologies Co., Ltd.";
  contact
    "Huawei Industrial Base
    Bantian, Longgang
    Shenzhen 518129
    People's Republic of China
    Website: http://www.huawei.com
    Email: support@huawei.com";
  description
    "Multicast forwarding table.";
  revision 2025-08-28 {
    description
      "Add a forwarding-mode node.";
    reference
      "Huawei private.";
  }
    revision 2025-05-13 {
    description
      "Add Mc M-LAG support for layer2 Eth-Trunk interface.";
    reference
      "Huawei private.";
  }
    revision 2024-05-31 {
    description
      "Add a multicast centralized gateway node.";
    reference
      "Huawei private.";
  }
    revision 2024-02-03 {
    description
      "Add support interface type to inbound node and outbound node. Modify interface type of mcnat node.";
    reference
      "Huawei private.";
  }
  revision 2024-02-02 {
    description
      "Support for 50-100GE interface types.";
    reference
      "Huawei private.";
  }
  revision 2023-07-17 {
    description
      "Modify when condition of hold-up time. Modify range of hold-up time.";
    reference
      "Huawei private.";
  }
  revision 2023-02-28 {
    description
      "Add fair-forward-enable node. Add cfc-check nodes under mpu-board.";
    reference
      "Huawei private.";
  }
  revision 2023-02-23 {
    description
      "Add must condition to inbound node and outbound node. Modify must of deny node.";
    reference
      "Huawei private.";
  }
  revision 2022-11-24 {
    description
      "Modify if-name nodes of multicast-nat. Modify the source cloning node. Modify must of trunk-back-up.";
    reference
      "Huawei private.";
  }
  revision 2022-09-23 {
    description
      "Modify range and default value of wtr.";
    reference
      "Huawei private.";
  }
  revision 2022-09-12 {
    description
      "Modify multicast-outgoing-interface-statics nodes.";
    reference
      "Huawei private.";
  }
  revision 2022-07-06 {
    description
      "Modify descriptions of some multicast NAT nodes.";
    reference
      "Huawei private.";
  }
  revision 2022-06-16 {
    description
      "Modify Description.";
    reference
      "Huawei private.";
  }
  revision 2022-06-01 {
    description
      "Add multicast-global mcast-frr-fib-wtr-time and options nodes.";
    reference
      "Huawei private.";
  }
  revision 2022-04-18 {
    description
      "Add multicast-nat softswitch nodes.";
    reference
      "Huawei private.";
  }
  revision 2022-03-19 {
    description
      "Modify multicast leaf CFC check node.";
    reference
      "Huawei private.";
  }
  revision 2021-12-20 {
    description
      "Add multicast-nat 2022-7 nodes.";
    reference
      "Huawei private.";
  }
  revision 2021-12-10 {
    description
      "Add a spatial multicast node must restriction.";
    reference
      "Huawei private.";
  }
  revision 2020-06-13 {
    description
      "Add VPN-based source addresses for NAT, multicast MAC and IP address consistency check, and the function of discarding multicast packets of specified VLANs.";
    reference
      "Huawei private.";
  }
  revision 2020-06-12 {
    description
      "Add units.";
    reference
      "Huawei private.";
  }     
  revision 2020-04-01 {
    description
      "Modify leaf others-number description.";
    reference
      "Huawei private.";
  }   
  revision 2020-03-31 {
    description
      "Modify static-frr-statuss node description.";
    reference
      "Huawei private.";
  }    
  revision 2020-03-17 {
    description
      "Modify mask type of static-frr-enables.";
    reference
      "Huawei private.";
  }    
  revision 2020-03-13 {
    description
      "Modify node description.";
    reference
      "Huawei private.";
  }
  revision 2020-03-12 {
    description
      "Modify node description.";
    reference
      "Huawei private.";
  }
  revision 2020-03-11 {
    description
      "Modify node description.";
    reference
      "Huawei private.";
  }
  revision 2020-03-10 {
    description
      "Modify multicast-outgoing-interface-statistics node.";
    reference
      "Huawei private.";
  }
  revision 2020-02-22 {
    description
      "Add random-detect static-frr node.";
    reference
      "Huawei private.";
  }    
  revision 2020-02-16 {
    description
      "Modify single-bind group-bind node.";
    reference
      "Huawei private.";
  }
  revision 2020-02-12 {
    description
      "Modify node description.";
    reference
      "Huawei private.";
  }
  revision 2020-01-22 {
    description
      "Modify VLAN-enables nodes.";
    reference
      "Huawei private.";
  }
  revision 2020-01-16 {
    description
      "Modify VLAN-enables nodes.";
    reference
      "Huawei private.";
  }    
  revision 2019-12-28 {
    description
      "Modify NAT nodes.";
    reference
      "Huawei private.";
  }    
  revision 2019-11-29 {
    description
      "Add get-multicast-forwarding-device nodes.";
    reference
      "Huawei private.";
  }
  revision 2019-11-28 {
    description
      "Modify send-igmp-packet nodes.";
    reference
      "Huawei private.";
  }
  revision 2019-11-27 {
    description
      "Add group bitmap nodes.";
    reference
      "Huawei private.";
  }    
  revision 2019-11-26 {
    description
      "Delete notification nodes.";
    reference
      "Huawei private.";
  }
  revision 2019-11-20 {
    description
      "Delete bras multicast nodes.";
    reference
      "Huawei private.";
  }
  revision 2019-11-01 {
    description
      "Add new nodes.";
    reference
      "Huawei private.";
  }
  revision 2019-10-30 {
    description
      "Add new nodes.";
    reference
      "Huawei private.";
  }     
  revision 2019-10-22 {
    description
      "Add new nodes.";
    reference
      "Huawei private.";
  }    
  revision 2019-10-10 {
    description
      "Add new nodes.";
    reference
      "Huawei private.";
  }
  revision 2019-03-30 {
    description
      "Initial revision.";
    reference
      "Huawei private.";
  }
  ext:task-name "forwarding";
  typedef af-type {
    type enumeration {
      enum "ipv4unicast" {
        value 1;
        description
          "IPv4 address family.";
      }
      enum "ipv6unicast" {
        value 2;
        description
          "IPv6 address family.";
      }
    }
    description
      "Address family type.";
  }
  typedef rule-direction {
    type enumeration {
      enum "in-bound" {
      value 0;
        description
          "Input Interface.";
      }
      enum "out-bound" {
      value 1;
        description
          "Output Interface.";
      }
    }
    description
      "Rule direction.";
  }  
  typedef cycle {
    type enumeration {
      enum "20" {
        value 20;
        description
          "Monitor cycle of 20.";
      }
      enum "40" {
        value 40;
        description
          "Monitor cycle of 40.";
      }
      enum "100" {
        value 100;
        description
          "Monitor cycle of 100.";
      }
      enum "200" {
        value 200;
        description
          "Monitor cycle of 200.";
      }
      enum "500" {
        value 500;
        description
          "Monitor cycle of 500.";
      }
    }
    description
      "Monitor cycle.";
  }
  typedef forwarding-mode {
    type enumeration {
      enum "normal-mode" {
        value 0;
        description
          "Normal mode.";
      }
      enum "fair-forward-mode" {
        value 1;
        description
          "Fair forward mode.";
      }
    }
    description
      "Forwarding mode.";
  }
  typedef queue1 {
    type enumeration {
      enum "be" {
      value 1;
        description
          "QoS queue BE.";
      }
      enum "af1" {
        value 2;  
        description
          "QoS queue AF1.";
      }
    }
    description
      "QoS queue1.";
  }
  typedef queue2 {
    type enumeration {
      enum "af2" {
        value 3;  
        description
          "QoS queue AF2.";
      }
      enum "af3" {
        value 4;  
        description
          "QoS queue AF3.";
      }
    }
    description
      "QoS queue2.";
  }
  typedef queue3 {
    type enumeration {
      enum "af4" {
        value 5;  
        description
          "QoS queue AF4.";
      }
      enum "cs6" {
        value 6;  
        description
          "QoS queue CS6.";
      }
    }
    description
      "QoS queue3.";
  }
  typedef queue4 {
    type enumeration {
      enum "ef" {
        value 7;  
        description
          "QoS queue EF.";
      }
      enum "cs7" {
        value 8;   
        description
          "QoS queue CS7.";
      }
    }
    description
      "QoS queue4.";
  }
  typedef status {
    type enumeration {
      enum "one" {
        value 1;   
        description
          "Static configuration.";
      }
 
      enum "two" {
        value 2;
        description
          "Dynamic learning.";
      }
    }
    description
      "Generation mode.";
  }
  typedef mpls-type {
    type enumeration {
      enum "p2mpte" {
        value 4;   
        description
          "P2MPTE type.";
      }
      enum "mldp" {
        value 5;   
        description
          "MLDP type.";
      }
    }
    description
      "Indicate the MPLS bandwidth type.";
  }
  typedef source-mac-change-type {
    type enumeration {
      enum "not-translate" {
        value 0;
        description
          "No translation.";
      }
      enum "auto-translate" {
        value 1;
        description
          "Auto translation.";
      }
    }
    description
      "Source MAC address modification mode.";
  }
  typedef rtp-ssrc-change-type {
    type enumeration {
      enum "not-translate" {
        value 0;
        description
          "No translation.";
      } 
      enum "auto-translate" {
        value 1;   
        description
          "Auto translation.";
      }
    }
    description
      "RTP SSRC modification mode.";
  }
  typedef switch-mode {
    type enumeration {
      enum "default-switch" {
        value 0;
        description
          "Default switch mode.";
      }
      enum "clean-switch" {
        value 1;
        description
          "Clean switch mode.";
      }      
    }
    description
      "Switch mode.";
  }
  typedef switch-field-type {
    type enumeration {
      enum "default-field" {
        value 0;
        description
          "Default field type.";
      }
      enum "first-field" {
        value 1;   
        description
          "First field type.";
      }
      enum "second-field" {
        value 2;   
        description
          "Second field type.";
      }
    }
    description
      "Switch field type.";
  }
  typedef rtp-seq-num-change-type {
    type enumeration {
      enum "not-translate" {
        value 0;   
        description
          "No translation.";
      } 
      enum "auto-translate" {
        value 1;   
        description
          "Auto translation.";
      }
    }
    description
      "Indicate that the sequence number of multicast streams is automatically translated.";
  }
  typedef rtp-ext-seq-num-change-type {
    type enumeration {
      enum "not-translate" {
        value 0;   
        description
          "No translation.";
      } 
      enum "auto-translate" {
        value 1;   
        description
          "Auto translation.";
      }
    }
    description
      "RTP extended sequence number modification mode.";
  }
  typedef video-type {
    type enumeration {
      enum "2022-6" {
        value 1;	  
        description
          "2022-6.";
      }
      enum "2110" {
        value 2;	  
        description
          "2110.";
      }
      enum "unknown" {
        value 3;
        description
          "Unknown video-type.";
      }
    }
    description
      "Video type.";
  }
  typedef stream-type {
    type enumeration {
      enum "default-stream-type" {
        value 0;
        description
          "Default stream type.";
      }
      enum "video-stream" {
        value 1;   
        description
          "Video stream.";
      }
      enum "ancillary-data" {
        value 2;   
        description
          "Ancillary data.";
      }
      enum "audio-stream" {
        value 3;   
        description
          "Audio stream.";
      }
    }
    description
      "Stream type.";
  }
  typedef resource-pool-type {
    type enumeration {
      enum "0" {
        value 0;   
        description
          "Resource pool 0. The outgoing interface of each multicast group preferentially applies for resource pool 0, and only one can be applied for.";
      }
      enum "1" {
        value 1;   
        description
          "Resource pool 1. If a multicast group has applied for an outgoing interface resource in resource pool 0, it applies for other outgoing interface resources in resource pool 1.";
      }
      enum "NULL" {
        value 255;   
        description
          "Null type.";
      }
    }
    description
      "Resource pool type.";
  }
  typedef board-type {
    type enumeration {
      enum "board-type-total" {
        value 0;
        description
          "All board types.";
      }
      enum "board-type-mpu" {
        value 1;   
        description
          "Board type of MPU.";
      }
      enum "board-type-lpu" {
        value 2;   
        description
          "Board type of LPU.";
      }
    }
    description
      "Multicast rui static board type.";
  }
  typedef service-type {
    type enumeration {
      enum "l3mcv4" {
        value 1;   
        description
          "Layer3 IPv4 multicast.";
      }
      enum "l3mcv6" {
        value 2;   
        description
          "Layer3 IPv6 multicast.";
      }
    }
    description
      "Service type.";
  }
  typedef frr-status-type {
    type enumeration {
      enum "static" {
        value 1;
        description
          "Static configuration.";
      }
      enum "dynamic" {
        value 2;
        description
          "Dynamic learning.";
      }
    }
    description
      "Fast re-router mode.";
  }
  typedef receive-status-type {
    type enumeration {
      enum "backup" {
        value 0;
        description
          "Backup status.";
      }
      enum "primary" {
        value 1;	  
        description
          "Primary status.";
      }
    }
    description
      "Receive status type.";
  }
  typedef frr-type {
    type enumeration {
      enum "init" {
        value 0;	  
        description
          "Init type.";
      }	
      enum "normal" {
        value 1;
        description
          "Normal FRR type.";
      }
      enum "ngmvpn" {
        value 2;	  
        description
          "NGMVPN type.";
      }
      enum "clone" {
        value 3;
        status obsolete;
        description
          "Clone type.";
      }
    }
    description
      "Fast re-router type.";
  }
  typedef learn-status {
    type enumeration {
      enum "success" {
        value 1;
        description
          "Stream learn success.";
      }
      enum "fail" {
        value 2;
        description
          "Stream learn fail.";
      }
      enum "unlearned" {
        value 3;
        description
          "Stream unlearned.";
      }
    }
    description
      "Learn status type.";
  }
  typedef learn-fail-reason {
    type enumeration {
      enum "stream-delay-exceed" {
        value 1;
        description
          "Stream delay exceed.";
      }
      enum "illegal-sampling-rate" {
        value 2;
        description
          "Illegal sampling rate.";
      }
      enum "illegal-frame-rate" {
        value 3;
        description
          "Illegal frame rate.";
      }
      enum "illegal-sn-per-frame" {
        value 4;
        description
          "Illegal sequence number per frame.";
      }      
      enum "illegal-ts-per-frame" {
        value 5;
        description
          "Illegal timestamp per frame.";
      }
      enum "negative-2110-stream" {
        value 6;
        description
          "Negative 2110 stream.";
      }
      enum "negative-2022d6-stream" {
        value 7;
        description
          "Negative 2022d6 stream.";
      }
      enum "stream-error" {
        value 8;
        description
          "Stream error.";
      }
    }
    description
      "Learn fail reason type.";
  }
  typedef frame-rate {
    type enumeration {
      enum "25fps" {
        value 0;
        description
          "25fps.";
      }
      enum "29.97fps" {
        value 1;
        description
          "30/1.001 (29.97)fps.";
      }
      enum "50fps" {
        value 2;
        description
          "50fps.";
      }
      enum "59.94fps" {
        value 3;
        description
          "60/1.001 (59.94)fps.";
      }
      enum "60fps" {
        value 4;
        description
          "60fps.";
      }
      enum "100fps" {
        value 5;
        description
          "100fps.";
      }
      enum "119.88fps" {
        value 6;
        description
          "120/1.001 (119.88)fps.";
      }
      enum "120fps" {
        value 7;
        description
          "120fps.";
      }
    }
    description
      "Frame rate type.";
  }
  typedef switch-status {
    type enumeration {
      enum "clean-switch-success" {
        value 1;
        description
          "Clean switch success.";
      }
      enum "forced-switch-success" {
        value 2;
        description
          "Forced switch success.";
      }
      enum "board-unregistered" {
        value 3;
        description
          "Board Unregistered.";
      }
      enum "member-status-inconsistent" {
        value 4;
        description
          "Member Status Inconsistent.";
      }
    }
    description
      "Switch status type.";
  }
  grouping switch-2022d7-para {
    description
      "The multicast-nat switching para.";
    leaf switch-field-type {
      type switch-field-type;
      mandatory true;
      description
        "Specify a switch field type.";
    }
    leaf cut-ptp {
      type uint64;
      mandatory true;
      description
        "Cut-ptp.";
    }
  }
  grouping switch-para {
    description
      "The multicast-nat switching parameters.";
    leaf switch-mode {
      type switch-mode;
      description
        "Switch mode.";
    }
    leaf switch-field-type {
      when "../switch-mode='clean-switch'";
      type switch-field-type;
      description
        "Specify a switch field type.";
    }
  }
  grouping softswitch-para {
    description
      "The multicast-nat softswitch parameters.";
    leaf switch-mode {
      type switch-mode;
      default "default-switch";
      description
        "Switch mode.";
    }
    leaf switch-field-type {
      when "../switch-mode='clean-switch'";
      type switch-field-type;
      default "default-field";
      description
        "Specify a switch field type.";
    }
  }
  grouping mcnat-outbound-common-configure {
    description
      "The multicast-nat outbound configure parameters.";
    leaf source-mac-trans-mode {
      type source-mac-change-type;
      default "not-translate";
      description
        "Source MAC address modification mode/Whether the source MAC address is automatically modified or not modified.";
    }
    leaf source-address-trans-mode {
      type boolean;
      default "false";
      description
        "Enable/disable the function of modifying the source IP address.";
    }
    leaf destination-address-trans-mode {
      type boolean;
      default "false";
      description
        "Enable/disable the function of modifying the destination IP address.";
    }
    leaf source-udp-trans-mode {
      type boolean;
      default "false";
      description
        "Enable/disable the function of modifying the source UDP port.";
    }
    leaf destination-udp-trans-mode {
      type boolean;
      default "false";
      description
        "Enable/disable the function of modifying the destination UDP port.";
    }
    leaf source-address {
      when "../source-address-trans-mode='true'";
      type inet:ipv4-address-no-zone {
        pattern '(\d|[1-9]\d|1\d{2}|2[0-1]\d|22[0-3])(\.(25[0-5]|2[0-4]\d|1\d\d|[1-9]?\d)){3}';
      }
      mandatory true;
      description
        "Multicast source address.";
    }
    leaf destination-address {
      when "../destination-address-trans-mode='true'";
      type inet:ipv4-address-no-zone {
        pattern '(22[4-9]|23\d)(\.(25[0-5]|2[0-4]\d|1\d\d|[1-9]?\d)){3}';
      }
      mandatory true;
      description
        "Destination IP address of a packet.";
    }
    leaf source-udp-port {
      when "../source-udp-trans-mode='true'";
      type uint32 {
        range "0..65535";
      }
      mandatory true;
      description
        "Source UDP port number of a packet.";
    }
    leaf destination-udp-port {
      when "../destination-udp-trans-mode='true'";
      type uint32 {
        range "0..65535";
      }
      mandatory true;
      description
        "Destination UDP port number of a packet.";
    }
  }
  grouping mcnat-outbound-common-info {
    description
      "The multicast-nat outbound info.";
    leaf outbound-name {
      type string {
        length "1..127";
      }
      description
        "Name of an outgoing flow.";
    }
    leaf src-mac-trans-mode {
      type string {
        length "1..31";
      }
      default "not-translate";
      description
        "Source MAC Address Modification Mode/Whether the source MAC address is automatically modified or not modified.";
    }
    leaf src-address-trans-mode {
      type string {
        length "1..31";
      }
      default "not-translate";
      description
        "Enable or disable the function of modifying the source IP address.";
    }
    leaf source-address {
      type inet:ipv4-address-no-zone;
      description
        "Multicast source address.";
    }
    leaf dst-address-trans-mode {
      type string {
        length "1..31";
      }
      default "not-translate";
      description
        "Enable or disable the function of modifying the destination IP address.";
    }
    leaf destination-address {
      type inet:ipv4-address-no-zone;
      description
        "Destination IP address of a packet.";
    }
    leaf source-udp-trans-mode {
      type string {
        length "1..31";
      }
      description
        "Enable or disable the function of modifying the source UDP port.";
    }
    leaf source-udp-port {
      type uint32 {
        range "0..65535";
      }
      description
        "Source UDP port number of a packet.";
    }
    leaf dst-udp-trans-mode {
      type string {
        length "1..31";
      }
      default "not-translate";
      description
        "Enable or disable the function of modifying the destination UDP port.";
    }
    leaf dst-udp-port {
      type uint32 {
        range "0..65535";
      }
      description
        "Destination UDP port number of a packet.";
    }
    leaf interface-name {
      type pub-type:if-name;
      description
        "Name of an interface.";
    }
  }
  grouping slot-config {
    description
      "The slot configuration.";
    container cfc-check {
      description
        "Configure multicast leaf CFC check.";
      leaf enable {
        type boolean;
        ext:dynamic-default;
        description
          "Enable/disable multicast leaf CFC check.";
      }
    }
  }
  container multicast-forward {
    description
      "Table of multicast-forward.";
    container global {
      description
        "Configure multicast forwarding global attributes.";
      leaf shaping-enable {
        type boolean;
        default "false";
        description
          "Enable/disable multicast shaping.";
      }
      leaf bw-car-enable {
        type boolean;
        default "false";
        description
          "Enable/disable multicast virtual scheduling information.";
      }
      leaf monitor-frr-cycle {
        type cycle;
        units ms;
        default "20";
        description
          "Set multicast frr monitor cycle.";
      }
      leaf frr-revert-disable {
        type boolean;
        default "false";
        description
          "Enable/disable multicast frr revert.";
      }
      leaf reliability-enhance-enable {
        type boolean;
        default false;
        status deprecated;
        description
          "Enable/disable multicast reliability enhancement.";
      }
      leaf qos-queue1 {
        type queue1;
        default "be";
        description
          "Multicast QoS queue1.";
      }
      leaf qos-queue2 {
        type queue2;
        default "af2";
        description
          "Multicast QoS queue2.";
      }
      leaf qos-queue3 {
        type queue3;
        default "af4";
        description
          "Multicast QoS queue3.";
      }
      leaf qos-queue4 {
        type queue4;
        default "ef";
        description
          "Multicast QoS queue4.";
      }
      leaf fragment-enable {
        type boolean;
        default false;
        description
          "Enable/disable multicast fragmentation. The configuration is performed based on a board.";
      }
      leaf rui-port {
        type uint32 {
          range "1025..65535";
        }
        description
          "Set multicast rui enhancement protocol port.";
      } 
      leaf mcast-frr-fib-wtr-time {
        type uint32 {
          range "10..280";
        }
        units "s";
        default "10";
        description
          "Configure time of multicast switchback wait time.";
      }
      leaf fair-forward-enable {
        type boolean;
        default false;
        description
          "Enable/disable multicast fair-forward.";
      }
    }
    container forwarding-mode {
      config false;
      description
        "Statistics of multicast forwarding mode.";
      leaf effective-forwarding-mode {
        type forwarding-mode;
        description
          "Effective multicast forwarding mode.";
      }
      leaf expected-forwarding-mode {
        type forwarding-mode;
        description
          "Expected multicast forwarding mode.";
      }
    }
    container nat {  
      presence "multicast NAT enable";
      description
        "Enable/disable multicast NAT configurations.";
      leaf ttl-decrease-disable {
        type boolean;
        default "false";
        description
          "Enable/disable the multicast NAT TTL decrement function.";
      }		
      container inbound-interfaces {
        description
          "List of interfaces enabled with multicast NAT.";
        list inbound-interface {
          key "interface-name";
          description
            "Configure interface on which multicast NAT is enabled.";
          leaf interface-name {
            type leafref {
              path "/ifm:ifm/ifm:interfaces/ifm:interface/ifm:name";
            }
            must "(/ifm:ifm/ifm:interfaces/ifm:interface[ifm:name=current()]/ifm:type = 'GigabitEthernet' or /ifm:ifm/ifm:interfaces/ifm:interface[ifm:name=current()]/ifm:type = '4x10GE' or /ifm:ifm/ifm:interfaces/ifm:interface[ifm:name=current()]/ifm:type = '10x10GE' or /ifm:ifm/ifm:interfaces/ifm:interface[ifm:name=current()]/ifm:type = '3x40GE' or /ifm:ifm/ifm:interfaces/ifm:interface[ifm:name=current()]/ifm:type = '4x25GE' or /ifm:ifm/ifm:interfaces/ifm:interface[ifm:name=current()]/ifm:type = 'XGigabitEthernet' or /ifm:ifm/ifm:interfaces/ifm:interface[ifm:name=current()]/ifm:type = '50GE' or /ifm:ifm/ifm:interfaces/ifm:interface[ifm:name=current()]/ifm:type = '40GE' or /ifm:ifm/ifm:interfaces/ifm:interface[ifm:name=current()]/ifm:type = '400GE' or /ifm:ifm/ifm:interfaces/ifm:interface[ifm:name=current()]/ifm:type = '25GE' or /ifm:ifm/ifm:interfaces/ifm:interface[ifm:name=current()]/ifm:type = '10GE' or /ifm:ifm/ifm:interfaces/ifm:interface[ifm:name=current()]/ifm:type = '100GE' or /ifm:ifm/ifm:interfaces/ifm:interface[ifm:name=current()]/ifm:type = '50|100GE' or /ifm:ifm/ifm:interfaces/ifm:interface[ifm:name=current()]/ifm:type = '800GE' or /ifm:ifm/ifm:interfaces/ifm:interface[ifm:name=current()]/ifm:type = '1200GE' or /ifm:ifm/ifm:interfaces/ifm:interface[ifm:name=current()]/ifm:type = 'FlexE' or /ifm:ifm/ifm:interfaces/ifm:interface[ifm:name=current()]/ifm:type = '50-100GE')";
            must "not(/ifm:ifm/ifm:interfaces/ifm:interface[ifm:name=current()]/ethernet:ethernet/ethernet:main-interface/ethernet:l2-attribute)";
            description
              "Name of an interface.";
          }
          leaf igmp-enable {
            type boolean;
            default false;
            description
              "Enable/disable multicast NAT IGMP on an interface.";
          }
        }
      }
      container instances {
        description
          "List of multicast NAT instances.";
        list instance {
          must "count(../instance)+count(../../instance-2022d7s/instance-2022d7)+count(../../instance-softswitchs/instance-softswitch)<=16000";
          key "instance-id";
          unique "instance-name";
          description
            "Configure multicast NAT instance.";
          leaf instance-id {
            type uint32 {
              range "1..16000";
            }
            must "not(../../../instance-2022d7s/instance-2022d7[instance-id = current()] or ../../../instance-softswitchs/instance-softswitch[instance-id = current()])";
            description
              "ID of a multicast NAT instance.";
          }
          leaf instance-name {
            type string {
              length "1..127";
            }
            must "not(../../../instance-2022d7s/instance-2022d7[instance-name = current()] or ../../../instance-softswitchs/instance-softswitch[instance-name = current()])";
            description
              "Name of a multicast NAT instance.";
          }
          leaf behavior-name {
            type string {
              length "1..127";
            }
            config false;
            description
              "Name of a traffic behavior to which the multicast NAT instance is bound.";
          }          
          container switching-packet-offset {                      
            description
              "Configure the offset of the packet to be switched.";
            leaf offset-value {
              type uint32 {
                range "0..65535";
              }
              default "0";
              description
                "Offset of the packet to be switched during frame switching.";
            }
          }      
          container outbounds {
            config false;
            description
              "List of output streams.";
            list outbound {
              key "outbound-id";
              description
                "Output stream state.";
              leaf outbound-id {
                type uint32 {
                  range "1..16000";
                }
                description
                  "ID of an outgoing flow.";
              }
              uses mcnat-outbound-common-info;
              leaf rtp-ssrc-trans-mode {
                type string {
                  length "1..31";
                }
                default "not-translate";
                description
                  "RTP SSRC modification mode.";
              }
              leaf rtp-seq-num-trans-mode {
                type string {
                  length "1..31";
                }
                description
                  "Indicate that the sequence number of multicast streams is automatically translated.";
              }
              leaf rtp-ext-seq-num-trans-mode {
                type string {
                  length "1..31";
                }
                description
                  "Indicate that the extended sequence number of multicast streams is automatically translated.";
              }
            }
          }
        }
      }
      container instance-2022d7s {
        description
          "List of multicast 2022d7 NAT instances.";
        list instance-2022d7{
          must "count(../instance-2022d7)+count(../../instances/instance)+count(../../instance-softswitchs/instance-softswitch)<=16000";
          key "instance-id";
          unique "instance-name";
          description
            "Configure multicast NAT 2022d7 instance.";
          leaf instance-id {
            type uint32 {
              range "1..16000";
            }
            must "not(../../../instances/instance[instance-id = current()] or ../../../instance-softswitchs/instance-softswitch[instance-id = current()])";
            description
              "ID of a multicast NAT instance.";
          }
          leaf instance-name {
            type string {
              length "1..127";
            }
            must "not(../../../instances/instance[instance-name = current()] or ../../../instance-softswitchs/instance-softswitch[instance-name = current()])";
            description
              "Name of a multicast NAT instance.";
          }
          leaf behavior-name {
            type string {
              length "1..127";
            }
            config false;
            description
              "Name of a traffic behavior to which the multicast NAT instance is bound.";
          }
          leaf transport-type {
            type video-type;
            must "../transport-type != 'unknown'";
            mandatory true;
            description
              "Transport type. (2022-6, 2110)";
          }
          leaf stream-type {
            when "../transport-type='2110'";
            type stream-type;
            must "../stream-type != 'default-stream-type'";
            mandatory true;
            description
              "Stream type. (ancillary-data, audio-stream, or video-stream)";
          }
          leaf frame-rate {
            when "not(../stream-type='audio-stream')";
            type frame-rate;
            mandatory true;
            description
              "Frame Rate.";
          }
          container outbounds {
            config false;
            description
              "List of output streams.";
            list outbound {
              key "outbound-id";
              description
                "Output stream state.";
              leaf outbound-id {
                type uint32 {
                  range "1..16000";
                }
                description
                  "ID of an outgoing flow.";
              }
              uses mcnat-outbound-common-info;
              leaf rtp-ssrc-trans-mode {
                type string {
                  length "1..31";
                }
                default "not-translate";
                description
                  "RTP SSRC modification mode.";
              }
              leaf rtp-seq-num-trans-mode {
                type string {
                  length "1..31";
                }
                description
                  "Indicate that the sequence number of multicast streams is automatically translated.";
              }
              leaf rtp-ext-seq-num-trans-mode {
                type string {
                  length "1..31";
                }
                description
                  "Indicate that the extended sequence number of multicast streams is automatically translated.";
              }
              leaf rtp-ssrc {
                type uint32;
                description
                  "Rtp Synchronization Source.";
              }
              leaf sn-offset {
                type uint32;
                description
                  "Sequence number offset.";
              }
            }
          }
        }
      }
      container instance-softswitchs {
        description
          "List of multicast NAT softswitch instances.";
        list instance-softswitch {
          must "count(../instance-softswitch)+count(../../instances/instance)+count(../../instance-2022d7s/instance-2022d7)<=16000";
          key "instance-id";
          unique "instance-name";
          description
            "Configure multicast NAT softswitch instance.";
          leaf instance-id {
            type uint32 {
              range "1..16000";
            }
            must "not(../../../instance-2022d7s/instance-2022d7[instance-id = current()] or ../../../instances/instance[instance-id = current()])";
            description
              "ID of a multicast NAT softswitch instance.";
          }
          leaf instance-name {
            type string {
              length "1..127";
            }
            must "not(../../../instances/instance[instance-name = current()] or ../../../instance-2022d7s/instance-2022d7[instance-name = current()])";
            description
              "Name of a multicast NAT softswitch instance.";
          }
          leaf behavior-name {
            type string {
              length "1..127";
            }
            config false;
            description
              "Name of a traffic behavior to which the multicast NAT softswitch instance is bound.";
          }
          leaf transport-type {
            type video-type;
            mandatory true;
            description
              "Transport type. (2022-6, 2110, unknown)";
          }
          leaf stream-type {
            when "../transport-type='2110'";
            type stream-type; 
            must "../stream-type != 'default-stream-type'";
            mandatory true;
            description
              "Stream type. (ancillary-data, audio-stream, or video-stream)";
          }
          leaf frame-rate {
            when "not(../stream-type='audio-stream') and not(../transport-type='unknown') ";
            type frame-rate;
            mandatory true;
            description
              "Frame Rate.";
          }
          container outbound-softswitchs {
            config false;
            description
              "List of output streams.";
            list outbound-softswitch {
              key "outbound-id";
              description
                "Output stream state.";
              leaf outbound-id {
                type uint32 {
                  range "1..16000";
                }
                description
                  "ID of an outgoing flow.";
              }
              uses mcnat-outbound-common-info;
              leaf rtp-ssrc {
                type uint32;
                description
                  "Rtp Synchronization Source.";
              }
              leaf sn-offset {
                type uint32;
                description
                  "Sequence number offset.";
              }
            }
          } 
        }
      }
      container outbounds {
        description
          "List of NAT configurations for multicast streams on outbound interfaces.";
        list outbound {
          must "count(../outbound)+count(../../outbound-softswitchs/outbound-softswitch)<=16000";
          key "interface-name outbound-id";
          unique "outbound-name";
          unique "outbound-id";
          description
            "Configure multicast stream translation on an outbound interface and configures multicast stream translation parameters.";
          leaf interface-name {
            type leafref {
              path "/ifm:ifm/ifm:interfaces/ifm:interface/ifm:name";
            }
            must "(/ifm:ifm/ifm:interfaces/ifm:interface[ifm:name=current()]/ifm:type = 'GigabitEthernet' or /ifm:ifm/ifm:interfaces/ifm:interface[ifm:name=current()]/ifm:type = '4x10GE' or /ifm:ifm/ifm:interfaces/ifm:interface[ifm:name=current()]/ifm:type = '10x10GE' or /ifm:ifm/ifm:interfaces/ifm:interface[ifm:name=current()]/ifm:type = '3x40GE' or /ifm:ifm/ifm:interfaces/ifm:interface[ifm:name=current()]/ifm:type = '4x25GE' or /ifm:ifm/ifm:interfaces/ifm:interface[ifm:name=current()]/ifm:type = 'XGigabitEthernet' or /ifm:ifm/ifm:interfaces/ifm:interface[ifm:name=current()]/ifm:type = '50GE' or /ifm:ifm/ifm:interfaces/ifm:interface[ifm:name=current()]/ifm:type = '40GE' or /ifm:ifm/ifm:interfaces/ifm:interface[ifm:name=current()]/ifm:type = '400GE' or /ifm:ifm/ifm:interfaces/ifm:interface[ifm:name=current()]/ifm:type = '25GE' or /ifm:ifm/ifm:interfaces/ifm:interface[ifm:name=current()]/ifm:type = '10GE' or /ifm:ifm/ifm:interfaces/ifm:interface[ifm:name=current()]/ifm:type = '100GE' or /ifm:ifm/ifm:interfaces/ifm:interface[ifm:name=current()]/ifm:type = '50|100GE' or /ifm:ifm/ifm:interfaces/ifm:interface[ifm:name=current()]/ifm:type = '800GE' or /ifm:ifm/ifm:interfaces/ifm:interface[ifm:name=current()]/ifm:type = '1200GE' or /ifm:ifm/ifm:interfaces/ifm:interface[ifm:name=current()]/ifm:type = 'FlexE' or /ifm:ifm/ifm:interfaces/ifm:interface[ifm:name=current()]/ifm:type = '50-100GE')";
            must "not(/ifm:ifm/ifm:interfaces/ifm:interface[ifm:name=current()]/ethernet:ethernet/ethernet:main-interface/ethernet:l2-attribute)";
            description
              "Name of an interface.";
          }
          leaf outbound-id {
            type uint32 {
              range "1..16000";
            }
            must "not(../../../outbound-softswitchs/outbound-softswitch[outbound-id = current()])";
            description
              "Specify the ID of an output multicast stream on an outbound interface.";
          }
          leaf outbound-name {
            type string {
              length "1..127";
            }
            must "not(../../../outbound-softswitchs/outbound-softswitch[outbound-name = current()])";
            description
              "Specify the name of an output multicast stream on an outbound interface.";
          }
          uses mcnat-outbound-common-configure;
          leaf rtp-ssrc-trans-mode {
            when "../is-2022d7='false'";
            type rtp-ssrc-change-type;
            default "not-translate";
            description
              "RTP SSRC modification mode.";
          }
          leaf rtp-seq-num-trans-mode {
            when "../is-2022d7='false'";
            type rtp-seq-num-change-type;
            default "not-translate";
            description
              "Indicate that the sequence number of multicast streams is automatically translated.";
          }
          leaf rtp-ext-seq-num-trans-mode {
            when "../is-2022d7='false' and ../rtp-seq-num-trans-mode='auto-translate'";
            type rtp-ext-seq-num-change-type;
            default "not-translate";
            description
              "RTP extended sequence number modification mode.";
          }
          leaf is-2022d7 {
            type boolean;
            default "false";
            description
              "Enable/disable 2022-7 mode.";
          }
          leaf rtp-ssrc {
            when "../is-2022d7='true'";
            type uint32;
            mandatory true;
            description
              "Rtp Synchronization Source.";
          }
        }
      }
      container outbound-softswitchs {
        description
          "List of NAT configurations for multicast streams on softswitch outbound interfaces.";
        list outbound-softswitch {
          must "count(../outbound-softswitch)+count(../../outbounds/outbound)<=16000";
          key "interface-name outbound-id";
          unique "outbound-name";
          unique "outbound-id";
          description
            "Configure multicast stream translation on a softswitch outbound interface and configures multicast stream translation parameters.";
          leaf interface-name {
            type leafref {
              path "/ifm:ifm/ifm:interfaces/ifm:interface/ifm:name";
            }
            must "(/ifm:ifm/ifm:interfaces/ifm:interface[ifm:name=current()]/ifm:type = 'GigabitEthernet' or /ifm:ifm/ifm:interfaces/ifm:interface[ifm:name=current()]/ifm:type = '4x10GE' or /ifm:ifm/ifm:interfaces/ifm:interface[ifm:name=current()]/ifm:type = '10x10GE' or /ifm:ifm/ifm:interfaces/ifm:interface[ifm:name=current()]/ifm:type = '3x40GE' or /ifm:ifm/ifm:interfaces/ifm:interface[ifm:name=current()]/ifm:type = '4x25GE' or /ifm:ifm/ifm:interfaces/ifm:interface[ifm:name=current()]/ifm:type = 'XGigabitEthernet' or /ifm:ifm/ifm:interfaces/ifm:interface[ifm:name=current()]/ifm:type = '50GE' or /ifm:ifm/ifm:interfaces/ifm:interface[ifm:name=current()]/ifm:type = '40GE' or /ifm:ifm/ifm:interfaces/ifm:interface[ifm:name=current()]/ifm:type = '400GE' or /ifm:ifm/ifm:interfaces/ifm:interface[ifm:name=current()]/ifm:type = '25GE' or /ifm:ifm/ifm:interfaces/ifm:interface[ifm:name=current()]/ifm:type = '10GE' or /ifm:ifm/ifm:interfaces/ifm:interface[ifm:name=current()]/ifm:type = '100GE' or /ifm:ifm/ifm:interfaces/ifm:interface[ifm:name=current()]/ifm:type = '50|100GE' or /ifm:ifm/ifm:interfaces/ifm:interface[ifm:name=current()]/ifm:type = '800GE' or /ifm:ifm/ifm:interfaces/ifm:interface[ifm:name=current()]/ifm:type = '1200GE' or /ifm:ifm/ifm:interfaces/ifm:interface[ifm:name=current()]/ifm:type = 'FlexE' or /ifm:ifm/ifm:interfaces/ifm:interface[ifm:name=current()]/ifm:type = '50-100GE')";
            must "not(/ifm:ifm/ifm:interfaces/ifm:interface[ifm:name=current()]/ethernet:ethernet/ethernet:main-interface/ethernet:l2-attribute)";
            description
              "Name of an interface.";
          }
          leaf outbound-id {
            type uint32 {
              range "1..16000";
            }
            must "not(../../../outbounds/outbound[outbound-id = current()])";
            description
              "Specify the ID of an output multicast stream on a softswitch outbound interface.";
          }
          leaf outbound-name {
            type string {
              length "1..127";
            }
            must "not(../../../outbounds/outbound[outbound-name = current()])";
            description
              "Specify the name of an output multicast stream on a softswitch outbound interface.";
          }
          uses mcnat-outbound-common-configure;
          leaf rtp-ssrc {
            type uint32;
            description
              "Rtp Synchronization Source.";
          }
        }
      }
      container instance-groups {
        description
          "List of multicast NAT instance groups.";
        list instance-group {
          key "group-id";
          unique "group-name";
          description
            "Configure multicast NAT instance group.";
          leaf group-id {
            type uint32 {
            range "1..4000";
            }
            description
              "ID of a multicast NAT instance group.";
          }
          leaf group-name {
            type string {
            length "1..127";
            }
            description
              "Name of a multicast NAT instance group.";
          }   
          container part-instances {
            description
              "List of multicast NAT part instances.";
            list part-instance {
              key "part-id";
              description
                "Assign an instance id to instance group.";
              leaf part-id {
                type uint32 {
                range "1..16";
                }
                description
                  "Location of a multicast NAT instance in an instance group.";
              }
              leaf instance-id {
                type uint32 {
                  range "1..16000";
                }
                must "(../../../../../instances/instance[instance-id=current()] and not(../../../../../instance-2022d7s/instance-2022d7/instance-id[. = current()/../../part-instance/instance-id]) and not(../../../../../instance-softswitchs/instance-softswitch/instance-id[. = current()/../../part-instance/instance-id])) or (../../../../../instance-2022d7s/instance-2022d7[instance-id=current()] and not(../../../../../instances/instance/instance-id[. = current()/../../part-instance/instance-id]) and not(../../../../../instance-softswitchs/instance-softswitch/instance-id[. = current()/../../part-instance/instance-id])) or (../../../../../instance-softswitchs/instance-softswitch[instance-id=current()] and not(../../../../../instances/instance/instance-id[. = current()/../../part-instance/instance-id]) and not(../../../../../instances/instance/instance-id[. = current()/../../part-instance/instance-id]))";
                mandatory true;
                description
                  "ID of a multicast NAT instance.";
              }
              leaf instance-name {
                type string {
                  length "1..127";
                }
                must "(/multicast-forward/nat/instances/instance[instance-id=current()/../instance-id][instance-name=current()]) or (/multicast-forward/nat/instance-2022d7s/instance-2022d7[instance-id=current()/../instance-id][instance-name = current()]) or (/multicast-forward/nat/instance-softswitchs/instance-softswitch[instance-id=current()/../instance-id][instance-name = current()])";
                description
                  "Name of a multicast NAT instance.";
              }
              leaf stream-type {
                type stream-type;
                must "(../stream-type='default-stream-type' and not(/multicast-forward/nat/instance-groups/instance-group/part-instances/part-instance[stream-type!='default-stream-type'])) or (../stream-type !='default-stream-type' and not(/multicast-forward/nat/instance-groups/instance-group/part-instances/part-instance[stream-type='default-stream-type']))";                
                default "default-stream-type";
                description
                  "Stream type. The default value and the specified value (ancillary-data, audio-stream, or video-stream) in the stream-type values of multiple part-instances in the same instance group cannot coexist. That is, all the values must be default or the specified values.";
              }  
            }
          }
        }
      }
   container outbound-groups {
      description
        "List of output stream groups.";
      list outbound-group {
        key "group-id";
        unique "group-name";
        description
          "Configure output stream group.";
    leaf group-id {
      type uint32 {
     range "1..4000";
      }
      description
     "ID of an output stream group.";
    }
    leaf group-name {
      type string {
     length "1..127";
      }
      description
     "Name of an output stream group.";
    }
    container part-outbounds {
      description
        "List of output part outbounds.";
      list part-outbound {
        key "part-id";
        description
          "Assign outbound id to outbound group.";
        leaf part-id {
          type uint32 {
            range "1..16";
          }
          description
        "Location of an output stream in an output stream group.";
        } 
        leaf outbound-id {
          type uint32 {
             range "1..16000";
          }
          must "(../../../../../outbounds/outbound[outbound-id=current()] and not(../../../../../outbound-softswitchs/outbound-softswitch/outbound-id[. = current()/../../part-outbound/outbound-id])) or (../../../../../outbound-softswitchs/outbound-softswitch[outbound-id=current()] and not(../../../../../outbounds/outbound/outbound-id[. = current()/../../part-outbound/outbound-id]))";
          must "count(/multicast-forward:multicast-forward/multicast-forward:nat/multicast-forward:outbound-groups/multicast-forward:outbound-group/multicast-forward:part-outbounds/multicast-forward:part-outbound[multicast-forward:outbound-id = current()]) = 1";
          mandatory true;
          description
        "ID of an outgoing flow.";
        }
        leaf outbound-name {
           type string {
               length "1..127";
           }
          must "(/multicast-forward/nat/outbounds/outbound[outbound-id=current()/../outbound-id][outbound-name=current()]) or (/multicast-forward/nat/outbound-softswitchs/outbound-softswitch[outbound-id=current()/../outbound-id][outbound-name = current()])";
          description
            "Name of an outgoing flow.";
        }
        leaf stream-type {
          type stream-type;
                must "(../stream-type='default-stream-type' and not(/multicast-forward/nat/outbound-groups/outbound-group/part-outbounds/part-outbound[stream-type!='default-stream-type'])) or (../stream-type !='default-stream-type' and not(/multicast-forward/nat/outbound-groups/outbound-group/part-outbounds/part-outbound[stream-type='default-stream-type']))";
          default "default-stream-type";
          description
                  "Stream type. The default value and the specified value (ancillary-data, audio-stream, or video-stream) in the stream-type values of multiple part-outbounds in the same outbound group cannot coexist. That is, all the values must be default or the specified values.";
        }            
      } 
    }
  }
}      
      container bind {  
        presence "multicast nat bind configuration";
        description
          "Enable/disable single or group binding configuration.";        
        container single-binds {
          description
            "List of bindings between output multicast streams and multicast NAT instances.";
          list single-bind {
            key "outbound-id";
            description
              "Configure binding between output multicast streams and multicast NAT instances.";
            leaf outbound-id {
              type leafref {
                path "/multicast-forward/nat/outbounds/outbound/outbound-id";
              }
              must "../../../../outbounds/outbound[outbound-id=current()][is-2022d7 = 'false']";
              description
                "ID of an outgoing flow.";
            }
            leaf fast-mode-enable {
              type boolean;
              default "false";
              description
                "Enable/disable the function of fast switch. Switch parameters (e.g.instance-id/switch-mode/witch-field-type) can not be modified when fast-mode-enable is true.";
            }            
            leaf outbound-name {              
              type leafref {
                path "/multicast-forward/nat/outbounds/outbound[outbound-id=current()/../outbound-id]/outbound-name";
              }
              description
                "Name of an outgoing flow.";
            }
            leaf instance-id {
              ext:operation-exclude update {
                when "../fast-mode-enable = 'true'";    
                description "The current node cannot be modified, when fast-mode-enable node is 'true'.";
              }            
              type leafref {
                path "/multicast-forward/nat/instances/instance/instance-id";
              }                            
              mandatory true;
              description
                "ID of a multicast NAT instance.";
            }
            leaf instance-name {
              type leafref {
                path "/multicast-forward/nat/instances/instance[instance-id=current()/../instance-id]/instance-name";
              }              
              description
                "Name of a multicast NAT instance.";
            }
            leaf switch-mode {              
              ext:operation-exclude update|delete {
                when "../fast-mode-enable = 'true'";    
                description "The current node cannot be modified, when fast-mode-enable node is 'true'.";
              }            
              type switch-mode;
              default "default-switch";          
              description
                "Switch mode.";
            }
              leaf switch-field-type {
              ext:operation-exclude update|delete {
                when "../fast-mode-enable = 'true'";    
                description "The current node cannot be modified, when fast-mode-enable node is 'true'.";
              }              
              when "../switch-mode='clean-switch'";
                type switch-field-type;
              default "default-field";
                description
                "Specify a switch field type.";
              }
              leaf switch-packet-offset {
              ext:operation-exclude update|delete {
                when "../fast-mode-enable = 'true'";    
                description "The current node cannot be modified, when fast-mode-enable node is 'true'.";
              }              
              when "../switch-mode='clean-switch'";
                type uint32 {
                  range "0..65535";
                }
              default "0";
                description
                "Set the offset of the packet to be switched.";
            }
          }
        }
        container group-binds {
          description
            "List of bindings between output stream groups and multicast NAT instance groups.";
          list group-bind {
            key "outbound-group-id";
            description
              "Configure binding between output stream groups and multicast NAT instance groups.
               eg. output stream group1: part count (value:outbound-count), part list[1]:outbound-1-part-1,outbound-1,outbound-1-streamtype-1, part list[2]:outbound-2-part-2,outbound-2,outbound-2-streamtype-2...; 
                instance group2:part count (value:instance-count), part list[1]:instance-1-part-1,instance-1,instance-1-streamtype-1, part list[2]:instance-2-part-2,instance-2,instance-2-streamtype-2...; 
                outbound-count == instance-count, outbound-count ~= 0, instance-count ~= 0, 
                outbound-1-part-1 == instance-1-part-1, outbound-1-streamtype-1 == instance-1-streamtype-1;outbound-2-part-2 == instance-2-part-2, outbound-2-streamtype-2 == instance-2-streamtype-2;...;outbound-n-part-n == instance-n-part-n, outbound-n-streamtype-n == instance-n-streamtype-n.";
            leaf outbound-group-id {
              type leafref {
                path "/multicast-forward/nat/outbound-groups/outbound-group/group-id";
              }
              must "count(/multicast-forward:multicast-forward/multicast-forward:nat/multicast-forward:outbound-groups/multicast-forward:outbound-group[multicast-forward:group-id = current()]/multicast-forward:part-outbounds/multicast-forward:part-outbound)>0";
              description
                "Output stream group ID.";
            }
            leaf fast-mode-enable {
              type boolean;
              default "false";
              description
                "Enable/disable the function of fast switch. Switch parameters (e.g.instance-group-id/switch-mode/switch-field-type) can not be modified when fast-mode-enable is true.";
            }             
            leaf outbound-group-name {
            type leafref {
              path "/multicast-forward/nat/outbound-groups/outbound-group[group-id=current()/../outbound-group-id]/group-name";
            }            
            description
              "Output stream group name.";
            }
            leaf instance-group-id {
              ext:operation-exclude update {
                when "../fast-mode-enable = 'true'";    
                description "The current node cannot be modified, when fast-mode-enable node is 'true'.";
              }            
              type leafref {
                path "/multicast-forward/nat/instance-groups/instance-group/group-id";
              }
              must "count(/multicast-forward:multicast-forward/multicast-forward:nat/multicast-forward:instance-groups/multicast-forward:instance-group[multicast-forward:group-id = current()]/multicast-forward:part-instances/multicast-forward:part-instance)>0";
              mandatory true;
              description
                "ID of a multicast NAT instance group.";
            }
            leaf instance-group-name {
              type leafref {
                path "/multicast-forward/nat/instance-groups/instance-group[group-id=current()/../instance-group-id]/group-name";
              }           
              description
                "Name of a multicast NAT instance group.";
            }            
            leaf switch-mode {             
              ext:operation-exclude update|delete {
                when "../fast-mode-enable = 'true'";    
                description "The current node cannot be modified, when fast-mode-enable node is 'true'.";
              }            
              type switch-mode;
              default "default-switch";          
              description
                "Switch mode.";
            }
              leaf switch-field-type {
              ext:operation-exclude update|delete {
                when "../fast-mode-enable = 'true'";    
                description "The current node cannot be modified, when fast-mode-enable node is 'true'.";
              }             
              when "../switch-mode='clean-switch'";
                type switch-field-type;
              default "default-field";
                description
                "Specify a switch field type.";
              }
              leaf switch-packet-offset {
              ext:operation-exclude update|delete {
                when "../fast-mode-enable = 'true'";    
                description "The current node cannot be modified, when fast-mode-enable node is 'true'.";
              }              
              when "../switch-mode='clean-switch'";
                type uint32 {
                  range "0..65535";
                }
                default "0";
                description
                "Set the offset of the packet to be switched.";
            }
          }
        }      
        container clean-switch-interval {
          description
            "Configure the interval between two adjacent multicast NAT clean switching commands.";
            leaf interval {
              type uint32 {
                range "300..500";
              }
              units ms;
              default "500";
              description
                "Specifies the interval between two adjacent multicast NAT clean switching commands.";
            }
        }
      }
      container bind-softswitch {  
        presence "multicast nat softswitch bind configuration";
        description
          "Enable/disable single or group binding configuration.";        
        container single-binds {
          description
            "List of bindings between output multicast softswitch streams and multicast NAT softswitch instances.";
          list single-bind {
            key "outbound-id";
            description
              "Configure binding between output multicast softswitch streams and multicast NAT softswitch instances.";
            leaf outbound-id {
              type leafref {
                path "/multicast-forward/nat/outbound-softswitchs/outbound-softswitch/outbound-id";
              }
              description
                "ID of a softswitch outgoing flow.";
            }
            leaf outbound-name {
              type leafref {
                path "/multicast-forward/nat/outbound-softswitchs/outbound-softswitch[outbound-id=current()/../outbound-id]/outbound-name";
              }
              description
                "Name of a softswitch outgoing flow.";
            }
            leaf instance-id {
              type leafref {
                path "/multicast-forward/nat/instance-softswitchs/instance-softswitch/instance-id";
              }
              mandatory true;
              description
                "ID of a multicast NAT softswitch instance.";
            }
            leaf instance-name {
              type leafref {
                path "/multicast-forward/nat/instance-softswitchs/instance-softswitch[instance-id=current()/../instance-id]/instance-name";
              }
              description
                "Name of a multicast NAT softswitch instance.";
            }
            uses softswitch-para;
          }
        }
        container group-binds {
          description
            "List of bindings between output stream groups and multicast NAT instance groups.";
          list group-bind {
            key "outbound-group-id";
            description
              "Configure binding between output stream groups and multicast NAT instance groups.
               eg. output stream group1: part count (value:outbound-count), part list[1]:outbound-1-part-1,outbound-1,outbound-1-streamtype-1, part list[2]:outbound-2-part-2,outbound-2,outbound-2-streamtype-2...; 
                instance group2:part count (value:instance-count), part list[1]:instance-1-part-1,instance-1,instance-1-streamtype-1, part list[2]:instance-2-part-2,instance-2,instance-2-streamtype-2...; 
                outbound-count == instance-count, outbound-count ~= 0, instance-count ~= 0, 
                outbound-1-part-1 == instance-1-part-1, outbound-1-streamtype-1 == instance-1-streamtype-1;outbound-2-part-2 == instance-2-part-2, outbound-2-streamtype-2 == instance-2-streamtype-2;...;outbound-n-part-n == instance-n-part-n, outbound-n-streamtype-n == instance-n-streamtype-n.";
            leaf outbound-group-id {
              type leafref {
                path "/multicast-forward/nat/outbound-groups/outbound-group/group-id";
              }
              must "count(/multicast-forward:multicast-forward/multicast-forward:nat/multicast-forward:outbound-groups/multicast-forward:outbound-group[multicast-forward:group-id = current()]/multicast-forward:part-outbounds/multicast-forward:part-outbound)>0";
              description
                "Output softswitch stream group ID.";
            }
            leaf outbound-group-name {
              type leafref {
                path "/multicast-forward/nat/outbound-groups/outbound-group[group-id=current()/../outbound-group-id]/group-name";
              }
              description
                "Output softswitch stream group name.";
            }
            leaf instance-group-id {
              type leafref {
                path "/multicast-forward/nat/instance-groups/instance-group/group-id";
              }
              must "count(/multicast-forward:multicast-forward/multicast-forward:nat/multicast-forward:instance-groups/multicast-forward:instance-group[multicast-forward:group-id = current()]/multicast-forward:part-instances/multicast-forward:part-instance)>0";
              mandatory true;              
              description
                "ID of a multicast NAT softswitch instance group.";
            }
            leaf instance-group-name {
              type leafref {
                path "/multicast-forward/nat/instance-groups/instance-group[group-id=current()/../instance-group-id]/group-name";
              }
              description
                "Name of a multicast NAT softswitch instance group.";
            }
            uses softswitch-para;
          }
        }
      }
      container stream-learn-features {
        config false;
        description
          "Statistics of stream learn features.";
        container instances {
          description
            "List of multicast NAT instances.";
          list instance {
            key "instance-id is-local";
            description
              "Statistics of stream learn features by instances.";
            leaf instance-id {
              type uint32 {
                range "1..16000";
              }
              description
                "ID of a multicast NAT instance.";
            }
            leaf is-local {
              type boolean;
              description
                "Enable/disable (local/global) stream learn features.";
            }
            leaf learn-status {
              when "../is-local='true'";
              type learn-status;
              description
                "Status of stream learn.";
            }
            leaf fail-reason {
              when "../learn-status='fail'";
              type learn-fail-reason;
              description
                "Reason of stream learn fail.";
            }
            leaf ts-frame-step {
              type uint64;
              description
                "Timestamp step per frame.";
            }
            leaf ts-pack-step {
              type uint64;
              description
                "Timestamp step per package.";
            }
            leaf sn-frame-step {
              type uint32;
              description
                "Sequence number step per frame.";
            }
            leaf sampling-pack-ptp {
              type uint64;
              description
                "Last end frame ptp time.";
            }
            leaf sampling-pack-sn {
              type uint32;
              description
                "Last end frame sequence number.";
            }
            leaf sampling-pack-ts {
              type uint32;
              description
                "Last end frame rtp time.";
            }
            leaf sampling-pack-absolute-ts {
              type uint64;
              description
                "Last end frame absolute rtp time.";
            }
            leaf sampling-pack-field {
              type switch-field-type;
              description
                "Specify a switch field type.";
            }
            leaf sampling-rate {
              type uint32;
              description
                "Specify a sampling rate.";
            }
            leaf last-update-time {
              type uint64;
              description
                "Last update time.";
            }
          }
        }
      }   
      container switch-2022d7-status {
        config false;
        description
          "Statistics of switch status.";
        container outbounds {
          description
            "List of multicast NAT outbounds.";
          list outbound {
            key outbound-id;
            description
              "Statistics of switch status by outbounds.";
            leaf outbound-id {
              type leafref {
                path "/multicast-forward/nat/outbounds/outbound/outbound-id";
              }
              description
                "ID of an outgoing flow.";
            }
            leaf switch-status {
              type switch-status;
              description
                "Switch-status (Clean/forced switch success).";
            }
            leaf cut-ptp {
              type uint64;
              description
                "Cut-ptp.";
            }
            leaf instance-id {
              type uint32;
              description
                "ID of a multicast NAT instance.";
            }
            leaf sn-offset {
              type uint32;
              description
                "Sequence number offset.";
            }
          }
        }
        container outbound-groups {
          description
          "List of output stream groups.";
          list outbound-group {
            key "outbound-group-id";
            description
            "Statistics of switch status by outbound-groups.";
            leaf outbound-group-id {
              type leafref {
                path "/multicast-forward/nat/outbound-groups/outbound-group/group-id";
              } 
              description
                "Output stream group ID.";
            }
            leaf switch-status {
              type switch-status;
              description
                "Switch-status (Clean/forced switch success).";
            }
            leaf cut-ptp {
              type uint64;
              description
                "Cut-ptp.";
            }
            container binds {
              description
                "List of single-flow switching sn-offset.";
              list bind {
                key "outbound-id";
                description
                  "Statistics of single-flow switching sn-offset.";
                leaf outbound-id {
                  type uint32;
                  description
                    "ID of an outgoing flow.";
                }
                leaf instance-id {
                  type uint32;
                  description
                    "ID of a multicast NAT instance.";
                }
                leaf sn-offset {
                  type uint32;
                  description
                    "Sequence number offset.";
                }
              }
            }
          }
        }
      }
      container source-addresses {
        description
            "List of VPN-based source addresses for NAT.";
        list source-address {
          key "vpn-name";
          description
            "Configure a VPN name.";
          leaf vpn-name {
            type leafref {
              path "/ni:network-instance/ni:instances/ni:instance/ni:name";
            }
            description
              "Source vpn name.";
          }
          leaf address {
            type inet:ipv4-address-no-zone;
            description
              "Source IPv4 address for NAT.";
          }
        }
      }
    }
    container multicast-shaping {
      presence "Configuration of multicast shaping.";
      description
        "Enable/disable multicast shaping configuration.";
      container multicast-lists {
      description
        "List of configuration of the multicast shaping parameters.";
        list multicast-list {
          key "index";
          description
            "Configure the multicast shaping parameters of a specified multicast program list.";
          leaf index {
            type uint32 {
              range "0..8191";
            }
            description
              "The index of a multicast program. The configured multicast program list index must have been created.";
          }
          leaf name {
            type string {
              length "1..32";
            }
            description
              "The name of a multicast program. The configured multicast program list name must be the same as the name of the program list corresponding to the actual index.";
          }
          leaf cir {
            type uint32 {
              range "8..4294967295";
            }
            mandatory true;
            description
              "The guaranteed bandwidth for multicast shaping.";
          }
          leaf pir {
            type uint32 {
              range "8..4294967295";
            }
            must "../pir >= ../cir";
            description
              "The peak bandwidth for multicast shaping.";
          }
          leaf queue-length {
            type uint32 {
              range "2000..128000";
            }
            description
              "The length of a multicast shaping packet.";
          }
        }
      }
    }
    container egress-forward-mode {
      description
        "Configure switch downstream multicast traffic replication by NP to replication by TM. The configuration is performed based on a board.";
      container global {
        description
         "Configure on all boards."; 
        leaf enable {
          type empty;
          description
            "Globally enable the configuration of switching downstream multicast traffic replication by NP to replication by TM. The configuration is performed based on a board.";
        }
      }
      leaf-list slot {
        type string {
          length "1..16";
        }
        must "not(../global)";
        description
          "Specify the slot ID of the board where the target port to which downstream multicast traffic is to be replicated on the TM resides.";
      }
    }
    container mcfwd-entrys {
      config false;
      description
        "List of multicast forwarding table.";
      list mcfwd-entry {
        key "vrf-name address-family";
        description
          "Configure multicast forwarding table state.";
        leaf vrf-name {
          type leafref {
            path "/ni:network-instance/ni:instances/ni:instance/ni:name";
          }
          description
            "Virtual private network.";
        }
        leaf address-family {
          type af-type;
          description
            "Multicast address family type.";
        }
        container forward-infors {
          description
            "List of multicast forwarding information.";
          list forward-infor {
            key "source-address group-address oif-name";
            description
              "Multicast forwarding information state.";
            leaf source-address {
              type inet:ip-address-no-zone;
              description
                "Multicast source address.";
            }
            leaf group-address {
              type inet:ip-address-no-zone;
              description
                "Multicast group address.";
            }
            leaf oif-name {
              type string {
                length "1..255";
              }
              description
                "The name of outgoing interface. If there is no multicast forwarding outbound interface, this field is displayed as --.";
            }
            leaf mid {
              type uint32;
              description
                "ID of multicast forwarding.";
            }
            leaf flag {
              type string {
                length "1..255";
              }
              description
                "Flag of multicast forwarding.";
            }
            leaf sg-up-time {
              type string {
                length "1..255";
              }
              description
                "Living time of multicast forwarding table.";
            }
            leaf sg-up-exp-time {
              type string {
                length "1..255";
              }
              description
                "Overtime of multicast forwarding table.";
            }
            leaf sg-iif-name {
              type string {
                length "1..255";
              }
              description
                "The name of incoming interface.";
            }
            leaf sg-up-neighbor {
              type inet:ip-address-no-zone;
              description
                "Root ip.";
            }
            leaf mtoken {
              type pub-type:hex-binary;
              default "0x0";
              description
                "Mtoken of the tunnel.";
            }
            leaf active-time {
              type string {
                length "1..255";
              }
              description
                "Active time.";
            }
            leaf token {
              type pub-type:hex-binary;
              default "0x0";
              description
                "The token information of the tunnel.";
            }
            leaf forward-rate-pps {
              type uint64;
              units pps;
              description
                "Packet forwarding rate.";
            }
            leaf forward-rate-bps {
              type uint64;
              units bit/s;
              description
                "Bit forwarding rate.";
            }
            leaf match-packet {
              type uint64;
              description
                "The statistics of matched packets.";
            }
            leaf match-byte {
              type uint64;
              units Byte;
              description
                "The statistics of matched bytes.";
            }
            leaf wrongif-packet {
              type uint64;
              description
                "The statistics of wrongif packets.";
            }
            leaf forward-packet {
              type uint64;
              description
                "The statistics of multicast forwarding packets.";
            }
            leaf forward-byte {
              type uint64;
              units Byte;
              description
                "The statistics of multicast forwarding bytes.";
            }
            leaf bas-flag {
              type uint32;
              description
                "Broadband access server flag.";
            }
            leaf clone-source-adress {
              type inet:ip-address-no-zone;
              status obsolete;
              description
                "Cloned source address.";
            }
          }
        }
      }
    }
    container multicast-speed-states {
      config false;
      status deprecated;
      description
        "List of multicast speed statistic information. This node is deprecated and get-multicast-speed-statistics is recommended.";
      list multicast-speed-state {
        key "source-address group-address interface-name flow-direction vlan-id pe-vid ce-vid";
        status deprecated;
        description
          "Multicast speed statistics.";
        leaf source-address {
          type inet:ipv4-address-no-zone;
          status deprecated;
          description
            "Multicast source address.";
        }
        leaf group-address {
          type inet:ipv4-address-no-zone;
          status deprecated;
          description
            "Multicast group address.";
        }
        leaf interface-name {
          type leafref {
            path "/ifm:ifm/ifm:interfaces/ifm:interface/ifm:name";
          }
          status deprecated;
          description
            "Name of the interface which the rate statistics.";
        }
        leaf flow-direction {
          type rule-direction;
          status deprecated;
          description
            "Data flow direction of interface.";
        }
        leaf vlan-id {
          type uint32 {
            range "1..4094";
          }
          status deprecated;
          description
            "VLAN ID.";
        }
        leaf pe-vid {
          type uint32 {
            range "1..4094";
          }
          status deprecated;
          description
            "Outer VLAN ID.";
        }
        leaf ce-vid {
          type uint32 {
            range "1..4094";
          }
          status deprecated;
          description
            "Inner VLAN ID.";
        }
        container interface-statistics {
          status deprecated;
          description
            "Multicast speed statistics.";
          leaf receive-byte {
            type uint64;
            units  Byte;
            status deprecated;
            description
              "Bytes received in 2 seconds.";
          }
          leaf receive-byte-rate {
            type uint64;
            units  Byte/s;
            status deprecated;
            description
              "Byte-rate received in 2 seconds.";
          }
          leaf receive-packet {
            type uint64;
            status deprecated;
            description
              "Packets received in 2 seconds.";
          }
          leaf receive-packet-rate {
            type uint64;
            units pps;
            status deprecated;
            description
              "Packet-rate received in 2 seconds.";
          }
        }
      }
    }
    container spatial-multicast {
   presence "spatial multicast enable";
      description
        "Enable/disable spatial multicast."; 
      container ipv4-multicast-bandwidths {
        description
          "List of IPv4 multicast bandwidth configurations.";
        list ipv4-multicast-bandwidth {
          key "vrf-name group-address group-address-mask source-address";
          description
            "Configure IPv4 multicast smc bandwidth configuration.";
          leaf vrf-name {
            type leafref {
              path "/ni:network-instance/ni:instances/ni:instance/ni:name";
            }
            description
              "VPN instance name.";
          }
          leaf group-address {
            type inet:ipv4-address-no-zone {
              pattern '(22[4-9]|23\d)(\.(25[0-5]|2[0-4]\d|1\d\d|[1-9]?\d)){3}';
            }
            description
              "Multicast group address.";
          }
          leaf group-address-mask {
            type uint32 {
              range "4..32";
            }
            description
              "Length of multicast group address mask. Please ensure the length of multicast group address mask is proper and the multicast group address after a bitwise AND operation is performed with the mask length is the same as the multicast group address before the bitwise AND operation. For example, for multicast group address 225.0.0.0, the mask length ranges from 8 to 32. For the multicast group address 225.0.0.1, the mask length must be 32.";
          }
          leaf source-address {
            type inet:ipv4-address-no-zone {
              pattern '(\d|[1-9]\d|1\d{2}|2[0-1]\d|22[0-3])(\.(25[0-5]|2[0-4]\d|1\d\d|[1-9]?\d)){3}';
            }
            description
              "Multicast source address.";
          }
          leaf bandwidth {
            type uint64 {
              range "1..62500000";
            }
            units kbit/s;
            mandatory true;
            description
              "Bandwidth based on which load balancing is performed for IPv4 Layer 3 multicast flows.";
          }
        }
      }
      container vlan-multicast-bandwidths {
        description
          "List of VLAN Layer 2 multicast bandwidth configurations.";
        list vlan-multicast-bandwidth {
          must "(not(./source-address != '0.0.0.0' and ./group-address = '0.0.0.0'))";
          key "vlan-id group-address group-address-mask source-address";
          description
            "Configure VLAN Layer 2 multicast bandwidth configuration.";
          leaf vlan-id {
            type leafref {
              path "/vlan:vlan/vlan:vlans/vlan:vlan/vlan:id";
            }
            must "/vlan:vlan/vlan:vlans/vlan:vlan[vlan:id=current()]/vlan:type !='super'";
            description
              "VLAN ID.";
          }
          leaf group-address {
            type inet:ipv4-address-no-zone {
              pattern '(22[4-9]|23\d)(\.(25[0-5]|2[0-4]\d|1\d\d|[1-9]?\d)){3}|0(\.0){3}';
            }
            description
              "Multicast group address.";
          }
          leaf group-address-mask {
            type uint32 {
              range "4..32";
            }
            description
              "Length of multicast group address mask. Please ensure the length of multicast group address mask is proper and the multicast group address after a bitwise AND operation is performed with the mask length is the same as the multicast group address before the bitwise AND operation. For example, for multicast group address 225.0.0.0, the mask length ranges from 8 to 32. For the multicast group address 225.0.0.1, the mask length must be 32.";
          }
          leaf source-address {
            type inet:ipv4-address-no-zone {
              pattern '(\d|[1-9]\d|1\d{2}|2[0-1]\d|22[0-3])(\.(25[0-5]|2[0-4]\d|1\d\d|[1-9]?\d)){3}';
            }
            description
              "Multicast source address.";
          }
          leaf bandwidth {
            type uint64 {
              range "1..62500000";
            }
            units kbit/s;
            mandatory true;
            description
              "Bandwidth based on which load balancing is performed for VLAN Layer 2 multicast flows.";
          }
        }
      }
      container vsi-multicast-bandwidths {
        description
          "List of VSI Layer 2 multicast bandwidth configurations.";
        list vsi-multicast-bandwidth {
          must "(not(./source-address != '0.0.0.0' and ./group-address = '0.0.0.0'))";
          key "vsi-name group-address group-address-mask source-address";
          description
            "Configure VSI Layer 2 multicast bandwidth configuration.";
          leaf vsi-name {
            type string {
              length "1..31";
            }
            description
              "VSI instance name.";
          }
          leaf group-address {
            type inet:ipv4-address-no-zone {
              pattern '(22[4-9]|23\d)(\.(25[0-5]|2[0-4]\d|1\d\d|[1-9]?\d)){3}|0(\.0){3}';
            }
            description
              "Multicast group address.";
          }
          leaf group-address-mask {
            type uint32 {
              range "4..32";
            }
            description
              "Length of multicast group address mask. Please ensure the length of multicast group address mask is proper and the multicast group address after a bitwise AND operation is performed with the mask length is the same as the multicast group address before the bitwise AND operation. For example, for multicast group address 225.0.0.0, the mask length ranges from 8 to 32. For the multicast group address 225.0.0.1, the mask length must be 32.";
          }
          leaf source-address {
            type inet:ipv4-address-no-zone {
              pattern '(\d|[1-9]\d|1\d{2}|2[0-1]\d|22[0-3])(\.(25[0-5]|2[0-4]\d|1\d\d|[1-9]?\d)){3}';
            }
            description
              "Multicast source address.";
          }
          leaf bandwidth {
            type uint64 {
              range "1..62500000";
            }
            units kbit/s;
            mandatory true;
            description
              "Bandwidth based on which load balancing is performed for VSI Layer 2 multicast flows.";
          }
        }
      }
      container mpls-bandwidths {
        description
          "List of MPLS bandwidth configurations.";
        list mpls-bandwidth {
          key "service-type";
          description
            "Configure MPLS bandwidth configuration.";
          leaf service-type {
            type mpls-type;
            description
              "Service-type: P2MP or MLDP.";
          }
          leaf bandwidth {
            type uint64 {
              range "1..62500000";
            }
            units kbit/s;
            mandatory true;
            description
              "Bandwidth based on which load balancing is performed for P2MP TE or MLDP flows.";
          }
        }
      }
      container board-enables {
        description
          "List of enable spatial multicast for specified boards.";
        list board-enable {
          key "slot";
          description
            "Configure spatial multicast enabled on a board.";
          leaf slot {
            type leafref {
              path "/devm:devm/devm:lpu-boards/devm:lpu-board/devm:position";
            }
            description
              "Slot ID.";
          }    
        }
      } 
      container channel-bandwiths {
        config false;
        description
          "List of each replication channel's bandwidth information of the SFUs in a spatial multicast scenario.";
        list channel-bandwith {
          key "sc-id";
          description
            "Display each replication channel's bandwidth information of the SFUs in a spatial multicast scenario state.";
          leaf sc-id {
            type uint32;
            description
              "ID of the channel used for multicast traffic replication on an SFU.";
          }
          leaf bandwith-use {
            type uint64;
            units kbit/s;
            description
              "Bandwidth consumed for multicast traffic replication in a channel, in kbit/s.";
          }
          leaf bandwith-free {
            type uint64;
            units kbit/s;
            description
              "Bandwidth available for multicast traffic replication in a channel, in kbit/s.";
          }
        }
      }
      container vlan-multicast-bandwidth-states {
        config false;
        description
          "List of the bandwidth based on which load balancing is performed for Layer 2 multicast flows of a VLAN in a spatial multicast scenario.";
        list vlan-multicast-bandwidth-state {
          key "vlan-id group-address source-address";
          description
            "Display the bandwidth based on which load balancing is performed for Layer 2 multicast flows of a VLAN in a spatial multicast scenario state.";
          leaf vlan-id {
            type uint32 {
              range "1..4094";
            }
            description
              "VLAN ID.";
          }
          leaf group-address {
            type inet:ipv4-address-no-zone;
            description
              "Multicast group address.";
          }
          leaf source-address {
            type inet:ipv4-address-no-zone;
            description
              "Multicast source address.";
          }   
          leaf sc-id {
            type uint32;
            description
              "ID of the channel used for multicast traffic replication on an SFU.";
          }
          leaf bandwidth {
            type uint64 {
              range "1..62500000";
            }
            units kbit/s;
            mandatory true;
            description
              "Bandwidth based on which load balancing is performed for VLAN Layer 2 multicast flows.";
          }
        }
      }
      container vsi-multicast-bandwidth-states {
        config false;
        description
          "List of the bandwidth based on which load balancing is performed for Layer 2 multicast flows of a VSI in a spatial multicast scenario.";
        list vsi-multicast-bandwidth-state {
          key "vsi-name group-address source-address";
          description
            "Display the bandwidth based on which load balancing is performed for Layer 2 multicast flows of a VSI in a spatial multicast scenario state.";
          leaf vsi-name {
            type string {
              length "1..31";
            }
            description
              "VSI instance name.";
          }
          leaf group-address {
            type inet:ipv4-address-no-zone;
            description
              "Multicast group address.";
          }
          leaf source-address {
            type inet:ipv4-address-no-zone;
            description
              "Multicast source address.";
          }   
          leaf sc-id {
            type uint32;
            description
              "ID of the channel used for multicast traffic replication on an SFU.";
          }
          leaf bandwidth {
            type uint64 {
              range "1..62500000";
            }
            units kbit/s;
            mandatory true;
            description
              "Bandwidth based on which load balancing is performed for VSI Layer 2 multicast flows.";
          }
        }
      }
      container ipv4-multicast-bandwidth-states {
        config false;
        description
          "List of the bandwidth based on which load balancing is performed for IPv4 Layer 3 multicast flows of a VPN instance in a spatial multicast scenario.";
        list ipv4-multicast-bandwidth-state {
          key "vrf-name group-address source-address";
          description
            "Display the bandwidth based on which load balancing is performed for IPv4 Layer 3 multicast flows of a VPN instance in a spatial multicast scenario state.";
          leaf vrf-name {
            type string {
              length "1..31";
            }
            description
              "VPN instance name.";
          }
          leaf group-address {
            type inet:ipv4-address-no-zone;
            description
              "Multicast group address.";
          }
          leaf source-address {
            type inet:ipv4-address-no-zone;
            description
              "Multicast source address.";
          }   
          leaf sc-id {
            type uint32;
            description
              "ID of the channel used for multicast traffic replication on an SFU.";
          }
          leaf bandwidth {
            type uint64 {
              range "1..62500000";
            }
            units kbit/s;
            mandatory true;
            description
              "Bandwidth based on which load balancing is performed for IPv4 Layer 3 multicast flows.";
          }
        }
      }        
    }
    container multicast-outgoing-interface-statics {
      config false;
      description
        "List of statistics about the usage of multicast outbound interfaces on a specified board.";
      list multicast-outgoing-interface-static {
        key "slot device-id";
        description
          "Statistics of the usage of multicast outbound interfaces on a specified board.";
        leaf slot {
          type string {
            length "1..15";
          }
          description
            "Slot ID of an interface board. The value range varies according to router hardware.";
        }
        leaf device-id {
          type uint32;
          description
            "Forwarding engine index.";
        }
        leaf resource-pool-index {
          type resource-pool-type;
          description
            "Index of the resource pool on a board where the multicast outbound interface resides.";
        }
        leaf total-number {
          type uint32;
          description
            "Maximum number of multicast outbound interfaces supported by the forwarding engine.";
        }
        leaf left-number {
          type uint32;
          description
            "Number of multicast outbound interfaces that are not in use in the forwarding engine.";
        }
        leaf used-number {
          type uint32;
          description
            "Number of multicast outbound interfaces that are in use in the forwarding engine.";
        }
        leaf ipv4-used-number {
          type string {
            length "1..15";
          }
          description
            "Number of Layer 3 IPv4 multicast outbound interfaces that are in use in the forwarding engine.";
        }
        leaf ipv6-used-number {
          type string {
            length "1..15";
          }
          description
            "Number of Layer 3 IPv6 multicast outbound interfaces that are in use in the forwarding engine.";
        }
        leaf others-number {
          type string {
            length "1..15";
          }
          description
            "Number of multicast outbound interfaces used by services except Layer 3 IPv4 multicast and Layer 3 IPv6 multicast.";
        }
      }
    }
    container l3-egress-statistics {
      description
        "Configure Layer 3 IPv4 multicast downstream packet statistics.";
      container enable-slots {
       description
         "List of Layer 3 IPv4 multicast downstream packet statistics based on slots.";
       list enable-slot {
         key "slot-id";
         description
            "Configure Layer 3 IPv4 multicast downstream packet statistics based on slots.";
         leaf slot-id {
        type string {
          length "1..15";
      }
      description
        "Slot ID.";
     }
   }
  }
  container vpn-enables {
   description
     "List of Layer 3 IPv4 multicast downstream packet statistics based on multicast groups and slots.";
   list vpn-enable {
     key "slot-id vpn-name source-address group-address";
     description
		"Configure Layer 3 IPv4 multicast downstream packet statistics based on multicast groups and slots.";
     leaf slot-id {
    type string {
      length "1..15";
    }
    description
      "Slot ID.";
     }
     leaf vpn-name {
    type leafref {
     path "/ni:network-instance/ni:instances/ni:instance/ni:name";
    }
    description
      "Name of a VPN instance.";
     }
     leaf source-address {
    type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
    }    
    description
      "Multicast source IP address.";
     }
     leaf group-address {
    type inet:ipv4-address-no-zone {
        pattern '(22[4-9]|23\d)(\.(25[0-5]|2[0-4]\d|1\d\d|[1-9]?\d)){3}';
    }
    description
      "Multicast group IP address, the value ranges from 224.0.1.0 to 239.255.255.255.";
     }
   }
  }
  container vpn-statistics {
   config false;
   description
     "List of statistics on Layer 3 IPv4 multicast downstream packets based on multicast groups and slots.";
   list vpn-statistic {
     key "slot-id vpn-name source-address group-address";
     description
		"Statistics of Layer 3 IPv4 multicast downstream packets based on multicast groups and slots.";
     leaf slot-id {
    type string {
      length "1..15";
    }
    description
      "Slot ID.";
     }
     leaf vpn-name {
    type leafref {
     path "/ni:network-instance/ni:instances/ni:instance/ni:name";
    }
    description
      "Name of a VPN instance.";
     }
     leaf source-address {
    type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
    }
    description
      "Multicast source IP address.";
     }
     leaf group-address {
    type inet:ipv4-address-no-zone {
        pattern '(22[4-9]|23\d)(\.(25[0-5]|2[0-4]\d|1\d\d|[1-9]?\d)){3}';
    }
    description
      "Multicast group IP address, the value ranges from 224.0.1.0 to 239.255.255.255.";
     }
     leaf interface-name {
    type string {
      length "1..255";
    }
    description
      "Name of an outbound interface.";
     }
     leaf packet-number {
    type uint64;
    description
      "Number of forwarded packets.";
     }
     leaf byte-number {
    type uint64;
    description
      "Number of forwarded bytes.";
     }
     leaf packet-rate {
    type uint64;
    units pps;
    description
      "Packet forwarding rate.";
     }
     leaf bit-rate {
    type uint64;
    units bit/s;
    description
      "Bit forwarding rate.";
     }
   }
  } 
 }
    container l2-egress-statistics {
      description
        "Configure Layer 2 IPv4 multicast downstream packet statistics.";
      container enable-slots {
        description
          "List of statistics about downstream Layer 2 IPv4 multicast packets based on slots.";
        list enable-slot {
          key "slot-id";
          description
            "Configure statistics about downstream Layer 2 IPv4 multicast packets based on slots.";
          leaf slot-id {
            type string {
              length "1..15";
            }
            description
              "Slot ID.";
          }
        }
      }
      container vlan-statistics {
        config false;
        description
          "List of statistics on Layer 2 VLAN IPv4 multicast downstream packets.";
        list vlan-statistic {
          key "slot-id vlan-id source-address group-address";
          description
            "Statistics of Layer 2 VLAN IPv4 multicast downstream packets.";
          leaf slot-id {
            type string {
              length "1..15";
            }
            description
              "Slot ID.";
          }
          leaf vlan-id {
            type leafref {
              path "/vlan:vlan/vlan:vlans/vlan:vlan/vlan:id";
            }
            description
              "VLAN ID.";
          }
          leaf source-address {
            type inet:ipv4-address-no-zone {
              pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
            }
            description
              "Multicast source IP address.";
          }
          leaf group-address {
            type inet:ipv4-address-no-zone {
              pattern '(22[4-9]|23\d)(\.(25[0-5]|2[0-4]\d|1\d\d|[1-9]?\d)){3}';
            }
            description
              "Multicast group IP address, the value ranges from 224.0.1.0 to 239.255.255.255.";
          }
          leaf interface-type {
            type string {
              length "1..15";
            }
            description
              "Type of an outbound interface. Switch: main interface of l2; Sub: sub-interface (non-termination); Qinq: qinq termination sub-interface; PW: VSI-PW.";
          }
          leaf interface-name {
            type string {
              length "1..255";
            }
            description
              "Name of an outbound interface.";
          }
          leaf packet-number {
            type uint64;
            description
              "Number of forwarded packets.";
          }
          leaf byte-number {
            type uint64;
            description
              "Number of forwarded bytes.";
          }
          leaf packet-rate {
            type uint64;
            units pps;
            description
              "Packet forwarding rate.";
          }
          leaf bit-rate {
            type uint64;
            units bit/s;
            description
              "Bit forwarding rate.";
          }
        }
      }
      container vsi-statistics {
        config false;
        description
          "List of statistics on Layer 2 VSI IPv4 multicast downstream packets.";
        list vsi-statistic {
          key "slot-id vsi-name source-address group-address";
          description
            "Statistics of Layer 2 VSI IPv4 multicast downstream packets.";
          leaf slot-id {
            type string {
              length "1..15";
            }
            description
              "Slot ID.";
          }
          leaf vsi-name {
            type leafref {
              path "/l2vpn:l2vpn/l2vpn:instances/l2vpn:instance/l2vpn:name";
            }
            description
              "VSI name.";
          }
          leaf source-address {
            type inet:ipv4-address-no-zone {
              pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
            }
            description
              "Multicast source IP address.";
          }
          leaf group-address {
            type inet:ipv4-address-no-zone {
              pattern '(22[4-9]|23\d)(\.(25[0-5]|2[0-4]\d|1\d\d|[1-9]?\d)){3}';
            }
            description
              "Multicast group IP address, the value ranges from 224.0.1.0 to 239.255.255.255.";
          }
          leaf interface-type {
            type string {
              length "1..15";
            }
            description
              "Type of an outbound interface. Switch: main interface of l2; Sub: sub-interface (non-termination); Qinq: qinq termination sub-interface; PW: VSI-PW.";
          }
          leaf interface-name {
            type string {
              length "1..255";
            }
            description
              "Name of an outbound interface.";
          }
          leaf packet-number {
            type uint64;
            description
              "Number of forwarded packets.";
          }
          leaf byte-number {
            type uint64;
            description
              "Number of forwarded bytes.";
          }
          leaf packet-rate {
            type uint64;
            units pps;
            description
              "Packet forwarding rate.";
          }
          leaf bit-rate {
            type uint64;
            units bit/s;
            description
              "Bit forwarding rate.";
          }
        }
      }
      container bd-statistics {
        config false;
        description
          "List of statistics on Layer 2 BD IPv4 multicast downstream packets.";
        list bd-statistic {
          key "slot-id bd-id source-address group-address";
          description
            "Statistics of Layer 2 BD IPv4 multicast downstream packets.";
          leaf slot-id {
            type string {
              length "1..15";
            }
            description
              "Slot ID.";
          }
          leaf bd-id {
            type leafref {
              path "/bd:bd/bd:instances/bd:instance/bd:id";
            }
            description
              "Bridge domain instance ID.";
          }
          leaf source-address {
            type inet:ipv4-address-no-zone {
              pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
            }
            description
              "Multicast source IP address.";
          }
          leaf group-address {
            type inet:ipv4-address-no-zone {
              pattern '(22[4-9]|23\d)(\.(25[0-5]|2[0-4]\d|1\d\d|[1-9]?\d)){3}';
            }
            description
              "Multicast group IP address, the value ranges from 224.0.1.0 to 239.255.255.255.";
          }
          leaf interface-type {
            type string {
              length "1..15";
            }
            description
              "Type of an outbound interface. Switch: main interface of l2; Sub: sub-interface (non-termination); Qinq: qinq termination sub-interface; PW: VSI-PW.";
          }
          leaf interface-name {
            type string {
              length "1..255";
            }
            description
              "Name of an outbound interface.";
          }
          leaf packet-number {
            type uint64;
            description
              "Number of forwarded packets.";
          }
          leaf byte-number {
            type uint64;
            description
              "Number of forwarded bytes.";
          }
          leaf packet-rate {
            type uint64;
            units pps;
            description
              "Packet forwarding rate.";
          }
          leaf bit-rate {
            type uint64;
            units bit/s;
            description
              "Bit forwarding rate.";
          }
        }
      }
    } 
    container random-detect {
      description
        "Configure multicast random detection.";
      leaf enable {
        type boolean;
        default "true";
        description
          "Enable/disable multicast random-detect IPv4 group.";
      }     
      container rules {
        description
          "List of multicast random detection rules.";
        list rule {
          key "source-address group-address vpn-name";
          max-elements "40";
          description
            "Configure multicast random detection rule.";
          leaf source-address {
            type inet:ipv4-address-no-zone {
              pattern '(\d|[1-9]\d|1\d{2}|2[0-1]\d|22[0-3])(\.(25[0-5]|2[0-4]\d|1\d\d|[1-9]?\d)){3}';
            }
            description
              "Multicast source address.";
          }
          leaf group-address {
            type inet:ipv4-address-no-zone {
              pattern '(22[4-9]|23\d)(\.(25[0-5]|2[0-4]\d|1\d\d|[1-9]?\d)){3}';
            } 
            description
              "Multicast group address.";
          }
          leaf vpn-name {
            type leafref {
              path "/ni:network-instance/ni:instances/ni:instance/ni:name";
            }
            description
              "Name of a VPN instance.";
          } 
          leaf mask {
            type inet:ipv4-address-no-zone {
              pattern '(24\d|25[0-5])(\.(25[0-5]|2[0-4]\d|1\d\d|[1-9]?\d)){3}';
            } 
            default "255.255.255.255";
            description
              "Specifiy the mask of a multicast group address.";
          }
        }
      }  
      container select-results {
        config false;
        description
          "List of multicast random detection selection results.";
        list select-result {
          key "slot source-address group-address vpn-name";
          description
            "Multicast random detection selection result state.";
          leaf slot {
            type string {
              length "1..15";
            }
            description
              "Slot ID.";
          }
          leaf source-address {
            type inet:ipv4-address-no-zone {
              pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
            }
            description
              "Multicast source address.";
          }
          leaf group-address {
            type inet:ipv4-address-no-zone {
              pattern '(22[4-9]|23\d)(\.(25[0-5]|2[0-4]\d|1\d\d|[1-9]?\d)){3}';
            } 
            description
              "Multicast group address.";
          }
          leaf vpn-name {
            type leafref {
              path "/ni:network-instance/ni:instances/ni:instance/ni:name";
            }
            description
              "Name of a VPN instance.";
          }
          leaf multicast-group-id {
            type uint32;
            description
              "ID of the multicast source and group.";
          }  
        }
      }
    }    
    container static-frr {
      description
        "Configure multicast static fast re-router.";
      container static-frr-enables {
        description
          "List of multicast static fast re-router enables.";
        list static-frr-enable {
          key "source-address group-address vpn-name";
          description
            "Configure multicast static fast re-router function.";
          leaf source-address {
            type inet:ipv4-address-no-zone {
              pattern '(\d|[1-9]\d|1\d{2}|2[0-1]\d|22[0-3])(\.(25[0-5]|2[0-4]\d|1\d\d|[1-9]?\d)){3}';
            }
            description
              "Multicast source address.";
          }
          leaf group-address {
            type inet:ipv4-address-no-zone {
              pattern '(22[4-9]|23\d)(\.(25[0-5]|2[0-4]\d|1\d\d|[1-9]?\d)){3}';
            }            
            description
              "Address of a multicast group. The start address of the group is the result of the bitwise AND operation of the configured groupaddr and mask. 
              The end address of the multicast group is the start address of the multicast group plus the result of the bitwise NOT operation on the configured mask, and puls 1.
              After the configuration takes effect, the group address used by services ranges from the start group address to the end group address.";
          }
          leaf vpn-name {
            type leafref {
              path "/ni:network-instance/ni:instances/ni:instance/ni:name";
            }
            description
              "Name of a VPN instance.";
          } 
          leaf mask {            
            type inet:ipv4-address-no-zone;            
		    default "255.255.255.255";
            description
              "Network mask. The length of the mask ranges from 1 to 32. A maximum of 2000 protected multicast source groups can be configured.";
          }	  
        }
      }
      container static-frr-statuss {
        config false;
        description
          "List of configure multicast fast re-router status.";
        list static-frr-status {
          key "source-address group-address vpn-name";
          description
            "Multicast static fast re-router state.";
          leaf source-address {
            type inet:ip-address-no-zone;
            description
              "Multicast source address.";
          }
          leaf group-address {
            type inet:ip-address-no-zone;
            description
              "Address of a multicast group.";
          }
          leaf vpn-name {
            type leafref {
              path "/ni:network-instance/ni:instances/ni:instance/ni:name";
            }
            description
              "Name of a VPN instance.";
          }
          leaf address-family {
            type inet:ip-version;
            description
              "Ip family type.";
            ext:support-filter "true";
          }
          leaf status {
            type frr-status-type;
            description
              "Status.";
          }
          leaf frr-type {
            type frr-type;
            description
              "Fast re-router type.";
          }
          leaf master-id {
            type uint32;
            description
              "ID of the master MDT.";
          }
          leaf backup-id {
            type uint32;
            description
              "ID of the backup MDT.";
          }
          leaf primary-interface-name {
            when "../frr-type='init' or ../frr-type='normal'";
            type pub-type:if-name;            
            description
              "Master inbound interface.";
          }
          leaf backup-interface-name {
            when "../frr-type='init' or ../frr-type='normal'";
            type pub-type:if-name;
            description
              "Backup inbound interface.";
          }
          leaf primary-source-address {
            when "../frr-type='clone'";
            type inet:ip-address-no-zone;
            status obsolete;
            description
              "Multicast source of the primary link.";
          }
          leaf backup-source-address {
            when "../frr-type='clone'";
            type inet:ip-address-no-zone;
            status obsolete;
            description
              "Multicast source of the backup link.";
          }
          leaf primary-root-address {
            when "../frr-type='ngmvpn'";
            type inet:ip-address-no-zone;
            description
              "Multicast root of the primary link.";
          }
          leaf backup-root-address {
            when "../frr-type='ngmvpn'";
            type inet:ip-address-no-zone;
            description
              "Multicast root of the backup link.";
          }
          leaf receive-status {
            type receive-status-type;
            description
              "Primary or backup.";
          }
        }
      }    
    }    
    container mac-ip-check {
      description
        "Configure multicast MAC and IP address consistency check.";
      leaf mac-ip-check-enable {
        type boolean;
        default "false";
        description
          "Enable/disable multicast MAC and IP address consistency check.";
      }
    }
  }
  rpc send-igmp-packet {
    description
      "Send IGMP packets.";
    input {
      leaf interface-name {
        type leafref {
          path "/ifm:ifm/ifm:interfaces/ifm:interface/ifm:name";
        }        
        mandatory true;
        description
          "Name of an interface.";
      }
      leaf igmp-packet {
        type string {
          length "1..512";
        }
        mandatory true;
        description
          "Igmp packet.";
      }
    }
  }  

  rpc reset-l3-egress-all-statistics {
    description
      "Clears statistics about downstream Layer 3 IPv4 multicast packets based on slots.";
    ext:node-ref "/multicast-forward:multicast-forward/multicast-forward:l3-egress-statistics";
    input {
      leaf slot-id {
        type string {
          length "1..15";
        }
        mandatory true;
        description
          "Slot ID.";
      }
    }
  } 
  rpc reset-l3-egress-statistics {
    description
      "Clears statistics about Layer 3 IPv4 multicast downstream packets.";
    ext:node-ref "/multicast-forward:multicast-forward/multicast-forward:l3-egress-statistics/multicast-forward:vpn-statistics";
    input {
      leaf slot-id {
        type string {
          length "1..15";
        }
        mandatory true;
        description
          "Slot ID.";
      }
      leaf vpn-name {
        type leafref {
            path "/ni:network-instance/ni:instances/ni:instance/ni:name";
        }
        mandatory true;
        description
          "Name of a VPN instance.";
      }
      leaf source-address {
        type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
        }
        mandatory true;
        description
          "Multicast source IP address.";
      }
      leaf group-address {
        type inet:ipv4-address-no-zone {
          pattern '(22[4-9]|23\d)(\.(25[0-5]|2[0-4]\d|1\d\d|[1-9]?\d)){3}';
        }
        mandatory true;
        description
          "Multicast group IP address, the value ranges from 224.0.1.0 to 239.255.255.255.";
      }
    }
  }
  rpc reset-l2-egress-all-statistics {
    description
      "Clears statistics about downstream Layer 2 IPv4 multicast packets.";
    ext:node-ref "/multicast-forward:multicast-forward/multicast-forward:l2-egress-statistics";
    input {
      leaf slot-id {
        type string {
          length "1..15";
        }
        mandatory true;
        description
          "Slot ID.";
      }
    }
  }
  rpc reset-vlan-egress-statistics {
    description
      "Clears statistics about Layer 2 VLAN IPv4 multicast downstream packets.";
    ext:node-ref "/multicast-forward:multicast-forward/multicast-forward:l2-egress-statistics/multicast-forward:vlan-statistics";
    input {
      leaf slot-id {
        type string {
          length "1..15";
        }
        mandatory true;
        description
          "Slot ID.";
      }
      leaf vlan-id {
        type leafref {
          path "/vlan:vlan/vlan:vlans/vlan:vlan/vlan:id";
        }
        mandatory true;
        description
          "VLAN ID.";
      }
      leaf source-address {
        type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
        }
        mandatory true;
        description
          "Multicast source IP address.";
      }
      leaf group-address {
        type inet:ipv4-address-no-zone {
          pattern '(22[4-9]|23\d)(\.(25[0-5]|2[0-4]\d|1\d\d|[1-9]?\d)){3}';
        }
        mandatory true;
        description
          "Multicast group IP address, the value ranges from 224.0.1.0 to 239.255.255.255.";
      }
    }
  }
  rpc reset-vsi-egress-statistics {
    description
      "Clears statistics about Layer 2 VSI IPv4 multicast downstream packets.";
    ext:node-ref "/multicast-forward:multicast-forward/multicast-forward:l2-egress-statistics/multicast-forward:vsi-statistics";
    input {
      leaf slot-id {
        type string {
          length "1..15";
        }
        mandatory true;
        description
          "Slot ID.";
      }
      leaf vsi-name {
        type leafref {
          path "/l2vpn:l2vpn/l2vpn:instances/l2vpn:instance/l2vpn:name";
        }
        mandatory true;
        description
          "VSI name.";
      }
      leaf source-address {
        type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
        }
        mandatory true;
        description
          "Multicast source IP address.";
      }
      leaf group-address {
        type inet:ipv4-address-no-zone {
          pattern '(22[4-9]|23\d)(\.(25[0-5]|2[0-4]\d|1\d\d|[1-9]?\d)){3}';
        }
        mandatory true;
        description
          "Multicast group IP address, the value ranges from 224.0.1.0 to 239.255.255.255.";
      }
    }
  }
  
  rpc reset-bd-egress-statistics {
    description
      "Clears statistics about Layer 2 BD IPv4 multicast downstream packets.";
    ext:node-ref "/multicast-forward:multicast-forward/multicast-forward:l2-egress-statistics/multicast-forward:bd-statistics";
    input {
      leaf slot-id {
        type string {
          length "1..15";
        }
        mandatory true;
        description
          "Slot ID.";
      }
      leaf bd-id {
        type leafref {
          path "/bd:bd/bd:instances/bd:instance/bd:id";
        }
        mandatory true;
        description
          "Bridge domain instance ID.";
      }
      leaf source-address {
        type inet:ipv4-address-no-zone {
          pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}|0(\.0){3}';
        }
        mandatory true;
        description
          "Multicast source IP address.";
      }
      leaf group-address {
        type inet:ipv4-address-no-zone {
          pattern '(22[4-9]|23\d)(\.(25[0-5]|2[0-4]\d|1\d\d|[1-9]?\d)){3}';
        }
        mandatory true;
        description
          "Multicast group IP address, the value ranges from 224.0.1.0 to 239.255.255.255.";
      }
    }
  }
  rpc set-stream-learn {
    description
      "Set Stream Learn.";
    input {
      container set-stream-learn-lists {
        description
          "List of set stream learn operations.";
        list set-stream-learn-list {
          key "instance-id";
          description
            "Set Stream Learn operation.";
          leaf instance-id {
            type uint32 {
              range "1..16000";
            }
            description
              "ID of a multicast NAT instance.";
          }
        }
      }
    }
  }   
  rpc set-stream-learn-global {
    description
      "Set Stream Global Features.";
    input {
      container set-stream-learn-global-lists {
        description
          "List of set stream learn global operations.";
        list set-stream-learn-global-list {
          key "instance-id";
          description
            "Set stream learn global operations.";
          leaf instance-id {
            type uint32 {
              range "1..16000";
            }
            description
              "ID of a multicast NAT instance.";
          }
          leaf ts-frame-step {
            type uint64;
            mandatory true;
            description
              "Timestamp step per frame.";
          }
          leaf ts-pack-step {
            type uint64;
            mandatory true;
            description
              "Timestamp step per package.";
          }
          leaf sn-frame-step {
            type uint32;
            mandatory true;
            description
              "Sequence number step per frame.";
          }
          leaf sampling-pack-ptp {
            type uint64;
            mandatory true;
            description
              "Last end frame ptp time.";
          }
          leaf sampling-pack-sn {
            type uint32;
            mandatory true;
            description
              "Last end frame sequence number.";
          }
          leaf sampling-pack-ts {
            type uint32;
            mandatory true;
            description
              "Last end frame rtp time.";
          }
          leaf sampling-pack-absolute-ts {
            type uint64;
            mandatory true;
            description
              "Last end frame absolute rtp time.";
          }
          leaf sampling-pack-field {
            type switch-field-type;
            mandatory true;
            description
              "Specify a switch field type.";
          }
          leaf sampling-rate {
            type uint32;
            mandatory true;
            description
              "Specify a sampling rate.";
          }
        }
      }
    }
  }
  rpc single-2022d7-reset {
    description
      "Reset outbound bind.";
    input {
      container single-2022d7-reset-lists {
        description
          "List of reset outbound bind operations.";
        list single-2022d7-reset-list {
          key "outbound-id";
          description
            "Reset outbound bind operations.";
          leaf outbound-id {
            type leafref {
              path "/multicast-forward/nat/outbounds/outbound/outbound-id";
            }
            description
              "ID of an outgoing flow.";
          }
        }
      }
    }
  }
  rpc single-fast-switch {
    description
      "Set single-flow clean switching.";
    ext:node-ref "/multicast-forward:multicast-forward/multicast-forward:nat/multicast-forward:bind/multicast-forward:single-binds/multicast-forward:single-bind";
    input {
      leaf outbound-id {
        type leafref {
          path "/multicast-forward/nat/outbounds/outbound/outbound-id";
        }
        mandatory true;
        description
          "ID of an outgoing flow.";
      }
      leaf instance-id {
        type leafref {
          path "/multicast-forward/nat/instances/instance/instance-id";
        }
        mandatory true;
        description
          "ID of a multicast NAT instance.";
      }
      leaf switch-mode {
        type switch-mode;
        description
          "Switch mode.";
      }
      leaf switch-field-type {
        when "../switch-mode='clean-switch'";
        type switch-field-type;
        description
          "Specify a switch field type.";
      }      
    }
  }
  rpc group-fast-switch {
    description
      "Set group-flow clean switching.";
    ext:node-ref "/multicast-forward:multicast-forward/multicast-forward:nat/multicast-forward:bind/multicast-forward:group-binds/multicast-forward:group-bind";
    input {
      leaf outbound-group-id {
        type leafref {
          path "/multicast-forward/nat/outbound-groups/outbound-group/group-id";
        }
        mandatory true;
        description
          "Output stream group ID.";
      }
      leaf instance-group-id {
        type leafref {
          path "/multicast-forward/nat/instance-groups/instance-group/group-id";
        } 
        mandatory true;
        description
          "ID of a multicast NAT instance group.";
      }
      leaf switch-mode {
        type switch-mode;
        description
          "Switch mode.";
      }
      leaf switch-field-type {
        when "../switch-mode='clean-switch'";
        type switch-field-type;
        description
          "Specify a switch field type.";
      }
    }
  }
  rpc single-2022d7-restore {
    description
      "Restore single-flow NAT forwarding with sn-offset.";
    input {
      container single-forward-restore-lists {
      description
        "List of restore single-flow NAT forwarding with sn-offset operations.";
        list single-forward-restore-list {
          key "outbound-id instance-id";
          description
            "Restore single-flow NAT forwarding with sn-offset operations.";
          leaf outbound-id {
            type leafref {
              path "/multicast-forward/nat/outbounds/outbound/outbound-id";
            }
            description
              "ID of an outgoing flow.";
          }
          leaf instance-id {
            type leafref {
              path "/multicast-forward/nat/instance-2022d7s/instance-2022d7/instance-id";
            }
            description
              "ID of a multicast NAT instance.";
          }
          leaf sn-offset {
            type uint32;
            mandatory true;
            description
              "Sequence number offset.";
          }
        }
      }
    }
  }
  rpc single-2022d7-switch {
    description
      "Set single-flow 2022-7 switch.";
    input {
      container single-bind-switch-lists {
        description
          "List of single-flow 2022-7 switching setting operations.";
        list single-bind-switch-list {       
          key "outbound-id instance-id";
          description
            "Single-flow 2022-7 switching setting operation.";
          leaf outbound-id {
            type leafref {
              path "/multicast-forward/nat/outbounds/outbound/outbound-id";
            }
            description
              "ID of an outgoing flow.";
          }
          leaf instance-id {
            type leafref {
              path "/multicast-forward/nat/instance-2022d7s/instance-2022d7/instance-id";
            }
            description
              "ID of a multicast NAT instance.";
          }
          uses switch-2022d7-para;
        }
      }
    }
  }
  rpc single-fast-switch-in-batches {
    description
      "Set single-flow clean switching in batches.";
    ext:node-ref "/multicast-forward:multicast-forward/multicast-forward:nat/multicast-forward:bind/multicast-forward:single-binds/multicast-forward:single-bind";
    input {
      container single-fast-switch-lists {
        description
          "List of single-flow clean switching setting operations.";
        list single-fast-switch-list {
          key "outbound-id instance-id";
          description
            "Single-flow clean switching setting operation.";
          leaf outbound-id {
            type leafref {
              path "/multicast-forward/nat/outbounds/outbound/outbound-id";
            }
            description
              "ID of an outgoing flow.";
          }
          leaf instance-id {
            type leafref {
              path "/multicast-forward/nat/instances/instance/instance-id";
            }
            description
              "ID of a multicast NAT instance.";
          }
          uses switch-para;
        }
      }
    }
  }   
  rpc group-2022d7-switch {
    description
      "Set group-flow 2022-7 switch.";
    input {
      container group-bind-switch-lists {
        description
          "List of group-flow 2022-7 switching setting operations.";
        list group-bind-switch-list {
          key "outbound-group-id instance-group-id";
          description
            "List of group-flow 2022-7 switching setting operations.";
          leaf outbound-group-id {
            type leafref {
              path "/multicast-forward/nat/outbound-groups/outbound-group/group-id";
            }
            description
              "Output stream group ID.";
          }
          leaf instance-group-id {
            type leafref {
              path "/multicast-forward/nat/instance-groups/instance-group/group-id";
            }
            description
              "ID of a multicast NAT instance group.";
          }
          uses switch-2022d7-para;
        }
      }
    }
  }   
  rpc group-fast-switch-in-batches {
    description
      "Set group-flow clean switching in batches.";
    ext:node-ref "/multicast-forward:multicast-forward/multicast-forward:nat/multicast-forward:bind/multicast-forward:group-binds/multicast-forward:group-bind";
    input {
      container group-fast-switch-lists {
        description
          "List of group-flow clean switching setting operations.";
        list group-fast-switch-list {
          key "outbound-group-id instance-group-id";
          description
            "Group-flow clean switching setting operation.";
          leaf outbound-group-id {
            type leafref {
              path "/multicast-forward/nat/outbound-groups/outbound-group/group-id";
            }
            description
              "Output stream group ID.";
          }
          leaf instance-group-id {
            type leafref {
              path "/multicast-forward/nat/instance-groups/instance-group/group-id";
            }
            description
              "ID of a multicast NAT instance group.";
          }
          uses switch-para;
        }
      }
    }
  }
  rpc get-multicast-forwarding-device {
    description
      "Query whether the traffic of a specified multicast group is forwarded by the local device.";
    input {
        leaf source-address {
          type inet:ip-address-no-zone;
          mandatory true;
          description
            "Multicast source address.";
        }
        leaf group-address {
          type inet:ip-address-no-zone;
          mandatory true;
          description
            "Multicast group address.";
        }
        leaf trunk-id {
          type uint32 {
            range "0..65535";
          }
          mandatory true;
          description
            "Specify the ID of an Eth-Trunk interface.";
        }
        leaf vrf-name {
          type leafref {
            path "/ni:network-instance/ni:instances/ni:instance/ni:name";
          }
          description
            "Name of virtual private network.";
        }
    }
    output {
        leaf flow {
          type string {
            length "1..127";
          }
          description
            "Flow information.";
        }
    }
  }
  rpc get-multicast-speed-statistics {
    description
      "Query multicast speed statistics.";
    input {
        leaf source-address {
          type inet:ipv4-address-no-zone;
          mandatory true;
          description
            "Multicast source address.";
        }
        leaf group-address {
          type inet:ipv4-address-no-zone;
          mandatory true;
          description
            "Multicast group address.";
        }
        leaf interface-name {
          type leafref {
            path "/ifm:ifm/ifm:interfaces/ifm:interface/ifm:name";
          }
          mandatory true;
          description
            "Specify interface-name.";
        }
        leaf flow-direction {
          type rule-direction;
          mandatory true;
          description
            "Data flow direction of interface.";
        }
        choice query-type {
          description
            "Multicast speed query type.";
          case vlan {
            description
            "Query by VLAN.";
            leaf vlan-id {
              type uint32 {
                range "1..4094";
              }
              mandatory true;
              description
                "VLAN ID.";
            }
          }
          case pe-ce {
            description
            "Query by outer VLAN and inner VLAN.";
            leaf pe-vid {
              type uint32 {
                range "1..4094";
              }
              mandatory true;
              description
                "Outer VLAN ID.";
            }
            leaf ce-vid {
              type uint32 {
                range "1..4094";
              }
              mandatory true;
              description
                "Inner VLAN ID.";
            }
          }
        }
      }
      output {
          leaf receive-byte {
            type uint64;
            units Byte;
            description
              "Bytes received in 2 seconds.";
          }
          leaf receive-byte-rate {
            type uint64;
            units Byte/s;
            description
              "Byte-rate received in 2 seconds.";
          }
          leaf receive-packet {
            type uint64;
            description
              "Packets received in 2 seconds.";
          }
          leaf receive-packet-rate {
            type uint64;
            units pps;
            description
              "Packet-rate received in 2 seconds.";
          }
      }
  }
  augment "/devm:devm/devm:mpu-boards/devm:mpu-board" {
    description
      "Configure multicast leaf CFC check to the devm module.";
    container multicast-forward {
      description
        "Configure multicast forward list.";
      uses slot-config;
    }
  }
  augment "/devm:devm/devm:lpu-boards/devm:lpu-board" {
    description
      "Configure multicast leaf CFC check to the devm module.";
    container multicast-forward {
      description
        "Configure multicast forward list.";
      uses slot-config;
    }
  }
  augment "/ifm:ifm/ifm:interfaces/ifm:interface" {
    description
      "Multicast forward configuration to the ifm module.";  
    container multicast-forward {
      description
        "Configure multicast forward list.";
      container shaping {
        description
          "Configure multicast shaping of interface.";
        leaf shaping-enable {
          when "../../../ifm:type='GigabitEthernet' or ../../../ifm:type='Eth-Trunk' or ../../../ifm:type='Ip-Trunk' or ../../../ifm:type='Pos' or ../../../ifm:type='100GE' or ../../../ifm:type='200GE' or ../../../ifm:type='40GE' or ../../../ifm:type='10GE' or ../../../ifm:type='4x10GE' or ../../../ifm:type='10x10GE' or ../../../ifm:type='3x40GE' or ../../../ifm:type='4x25GE' or ../../../ifm:type='25GE' or ../../../ifm:type='ATM' or ../../../ifm:type='XGigabitEthernet' or ../../../ifm:type='FlexE' or ../../../ifm:type='50|100GE' or ../../../ifm:type='50GE' or ../../../ifm:type='400GE' or ../../../ifm:type='1200GE' or ../../../ifm:type='50-100GE'";
          type boolean;
          default "false";
          description
            "Enable/disable multicast shaping on an interface.";
        }
      }
      container hold-up {
        description
          "Configure the member interface that changes from down to up to forward multicast traffic.";
        leaf time {
          when "../../../ifm:type='Eth-Trunk' or ../../../ifm:type='Ip-Trunk' or ../../../ifm:type='Global-VE'";
          type uint32 {
            range "2..1800";
          }
          units s;
          default 2;
          description
            "Delay for an interface to go Up.";
        }
      }
      container backup {
          description
          "Configure master/backup protection for trunk member interfaces.";
        leaf ipv4-enable {
          when "../../../ifm:type='Eth-Trunk' or ../../../ifm:type='Global-VE'";
          type boolean;
          default false;
          description
            "Enable/disable master/backup protection for trunk member interfaces in Layer 3 IPv4 multicast scenarios.";
        }
        leaf ipv6-enable {
          when "../../../ifm:type='Eth-Trunk' or ../../../ifm:type='Global-VE'";
          type boolean;
          default false;
          description
            "Enable/disable master/backup protection for trunk member interfaces in Layer 3 IPv6 multicast scenarios.";
        }
      }
      container deny-vlan {
        when "(../../ifm:type='Eth-Trunk')or(../../ifm:type='GigabitEthernet')or(../../ifm:type='10GE')or(../../ifm:type='25GE')or(../../ifm:type='40GE')or(../../ifm:type='100GE')or(../../ifm:type='MultiGE')or(../../ifm:type='4x10GE')or(../../ifm:type='10x10GE')or(../../ifm:type='3x40GE')or(../../ifm:type='4x25GE')or(../../ifm:type='50|100GE')or(../../ifm:type='Ethernet')or(../../ifm:type='50GE')or(../../ifm:type='XGigabitEthernet')or(../../ifm:type='GEBrief')or(../../ifm:type='200GE')or(../../ifm:type='400GE')";
        description
          "Configure the function of discarding multicast packets of specified VLANs.";
        leaf vlan-list {
          type pub-type:vlan-range;
          description
            "VLAN list.";
        }
      }
      container options {
        description
          "Configure multicast forward available options under port.";
        leaf  vxlan-multicast-group {
          when "../../../ifm:type = 'Vlanif'";
          type empty;
          description
            "Add the interface to the multicast group.";
        }
        leaf multicast-centralized-gateway {
          when "../../../ifm:type = 'Vbdif'";
          type empty;
          description
            "Add the interface to the multicast centralized gateway.";
        }
      }
      container mlag-standby {
        when "../../ifm:type='Eth-Trunk'";
        description
          "Configure the function of multicast m-lag active-standby mode.";
        leaf m-lag-standby-enable {
          type empty;
          must "../../../ethernet:ethernet/ethernet:main-interface/ethernet:l2-attribute";
          description
            "Enable multicast m-lag active-standby mode.";
        }
      }
    }
  }  
  augment "/ni:network-instance/ni:instances/ni:instance" {
    description
      "Configure multicast fast re-router.";  
    container multicast-forward {
   description
        "Configure multicast forwarding table.";
      container multicast-fast-re-routers {
        description
          "List of multicast fast re-router.";
        list multicast-fast-re-router {
          key "source-address group-address";
          description
            "Configure multicast static source and group.";
          leaf source-address {
            type inet:ipv4-address-no-zone;
            description
              "Multicast source address.";
          }
          leaf group-address {
            type inet:ipv4-address-no-zone;
            description
              "Address of a multicast group. In IPv4, the value ranges from 224.0.1.0 to 239.255.255.255, in dotted decimal notation.";
          }
          leaf mask {
            type inet:ipv4-address-no-zone;
   default "255.255.255.255";
            description
              "Mask of network.";
          }
          leaf status {
            type status;
            config false;
            description
              "Status: Dynamic or static multicast fast-re-routers.";
          }    
        }
      }
    }
  }
  augment "/qos:qos/qos:classifier-template/qos:traffic-behaviors/qos:traffic-behavior" {
    description
      "Multicast forward configuration to the QoS module."; 
    container behavior-bind-multicast-nat-instance {
      when "/multicast-forward:multicast-forward/multicast-forward:nat";
      description
        "Configure multicast NAT instances and bind them to the traffic behavior.";
      list behavior-bind-multicast-nat {
        key "instance-id";
        max-elements "1";
        description
          "Configure a multicast NAT instance and bind it to the traffic behavior.";
        leaf instance-id {
          type uint32 {
            range "1..16000";
          }
          must "(/multicast-forward:multicast-forward/multicast-forward:nat/multicast-forward:instances/multicast-forward:instance[multicast-forward:instance-id=current()]) or (/multicast-forward:multicast-forward/multicast-forward:nat/multicast-forward:instance-2022d7s/multicast-forward:instance-2022d7[multicast-forward:instance-id=current()]) or (/multicast-forward:multicast-forward/multicast-forward:nat/multicast-forward:instance-softswitchs/multicast-forward:instance-softswitch[multicast-forward:instance-id=current()])";
          description
            "ID of a multicast NAT instance.";
        }
        leaf instance-name {
          type string {
            length "1..127";
          }
          must "(/multicast-forward:multicast-forward/multicast-forward:nat/multicast-forward:instances/multicast-forward:instance[multicast-forward:instance-id=current()/../multicast-forward:instance-id][multicast-forward:instance-name=current()]) or (/multicast-forward:multicast-forward/multicast-forward:nat/multicast-forward:instance-2022d7s/multicast-forward:instance-2022d7[multicast-forward:instance-id=current()/../multicast-forward:instance-id][multicast-forward:instance-name = current()]) or (/multicast-forward:multicast-forward/multicast-forward:nat/multicast-forward:instance-softswitchs/multicast-forward:instance-softswitch[multicast-forward:instance-id=current()/../multicast-forward:instance-id][multicast-forward:instance-name = current()])";
          description
            "Name of a multicast NAT instance.";
        }
      }
    }
  } 
}
