/*
Copyright (C) 2020-2025 Huawei Technologies Co., Ltd. All rights reserved.
*/
module huawei-storm-control {
  namespace "urn:huawei:yang:huawei-storm-control";
  prefix storm-control;
  import huawei-ifm {
    prefix ifm;
  }
  import huawei-extension {
    prefix ext;
  }
  import huawei-bd {
    prefix bd;
  }
  import ietf-yang-types {
      prefix yang;
  }
  import huawei-vlan {
    prefix vlan;
  }
  import huawei-l2vpn {
    prefix l2vpn;
  }
  organization
    "Huawei Technologies Co., Ltd.";
  contact
    "Huawei Industrial Base
    Bantian, Longgang
    Shenzhen 518129
    People's Republic of China
    Website: http://www.huawei.com
    Email: support@huawei.com";
  description
    "This module contains a collection of YANG definitions for managing storm control.";
  revision 2025-08-25 {
    description
      "Adaptation for 800GE Interface.";
    reference
      "Huawei private.";
  }
  revision 2025-08-07 {
    description
      "Change the line ending format to Unix-style.";
    reference
      "Huawei private.";
  }
  revision 2024-11-01 {
    description
      "Revert 'when' condition of VGE for storm-suppress.";
    reference
      "Huawei private.";
  }
  revision 2024-10-14 {
    description
      "Add 'when' condition of VGE for storm-suppress.";
    reference
      "Huawei private.";
  }
  revision 2024-07-23 {
    description
      "Modify pps-min-rate and pps-max-rate condition.";
    reference
      "Huawei private.";
  }
  revision 2024-05-14 {
    description
      "Add vsi storm-suppress.";
    reference
      "Huawei private.";
  }
  revision 2024-04-15 {
    description
      "Modify cir range for storm-suppress-mac-flapping of VLAN.";
    reference
      "Huawei private.";
  }
  revision 2024-03-23 {
    description
      "Modify cir range for storm-suppress-mac-flapping of VLAN.";
    reference
      "Huawei private.";
  }
  revision 2024-01-11 {
    description
      "Add 'presence' condition for storm-suppress-mac-flapping of VLAN.";
    reference
      "Huawei private.";
  }
  revision 2024-01-10 {
    description
      "Add 'when' condition for storm-control and storm-suppress.";
    reference
      "Huawei private.";
  }
  revision 2024-01-08 {
    description
      "Add storm-suppress-mac-flapping of VLAN.";
    reference
      "Huawei private.";
  }
  revision 2023-11-29 {
    description
      "Delete 'when' condition for storm-control and storm-suppress.";
    reference
      "Huawei private.";
  }
  revision 2023-07-08 {
    description
      "Add storm-suppress-action and storm-suppress of VLAN, add 'when' condition for storm-control and storm-suppress.";
    reference
      "Huawei private.";
  }
  revision 2022-07-05 {
    description
      "Add global storm-suppress.";
    reference
      "Huawei private.";
  }
  revision 2022-03-31 {
    description
      "The storm function under the interface depends on the interface being L2.";
    reference
      "Huawei private.";
  }
  revision 2022-03-30 {
    description
      "Modify the range of cir and percent in storm-suppress.";
    reference
      "Huawei private.";
  }
  revision 2022-02-07 {
    description
      "Modify task-name to cpu-defend.";
    reference
      "Huawei private.";
  }
  revision 2021-07-01 {
    description
      "Add remaining information for storm-control-state.";
    reference
      "Huawei private.";
  }
  revision 2021-03-09 {
    description
      "Add the range of cbs for storm suppress.";
    reference
      "Huawei private.";
  }
  revision 2020-12-26 {
    description
      "Use the 'must' statement instead of 'mandatory'.";
    reference
      "Huawei private.";
  }
  revision 2020-11-13 {
    description
      "Add packet type of flood for storm suppress.";
    reference
      "Huawei private.";
  }
  revision 2020-07-13 {
    description
      "Add rate type of pps for storm suppress.";
    reference
      "Huawei private.";
  }
  revision 2020-05-22 {
    description
      "Add storm suppress.";
    reference
      "Huawei private.";
  }
  revision 2020-01-02 {
    description
      "Initial revision.";
    reference
      "Huawei private.";
  }
  typedef packet-type {
    type enumeration {
      enum "broadcast" {
        value 1;
        description
          "This value is used for performing on broadcast packets.";
      }
      enum "unknown-multicast" {
        value 2;
        description
          "This value is used for performing on unknown-multicast packets.";
      }
      enum "unicast" {
        value 3;
        description
          "This value is used for performing on unicast packets.";
      }
      enum "unknown-unicast" {
        value 4;
        description
          "This value is used for performing on unknown-unicast packets.";
      }
      enum "flood" {
        value 5;
        description
          "This value is used for performing on flood packets.";
      }
    }
    description
      "Type of packets going through an interface.";
  }
  typedef action {
    type enumeration {
      enum "error-down" {
        value 1;
        description
          "Error down an interface.";
      }
      enum "block" {
        value 2;
        description
          "Block packet.";
      }
      enum "suppress" {
        value 3;
        description
          "Suppress packets.";
      }
    }
    description
      "Action of storm control.";
  }
  typedef mode-state {
    type enumeration {
      enum "pps" {
        value 1;
        description
          "Packet mode.";
      }
      enum "per" {
        value 2;
        description
          "Percent mode.";
      }
      enum "kbps" {
        value 3;
        description
          "Cir mode.";
      }
    }
    description
      "The mode of the storm control.";
  }
  typedef punish-status {
    type enumeration {
      enum "normal" {
        value 1;
        description
          "Normal.";
      }
      enum "err-down" {
        value 2;
        description
          "Error-down the interface.";
      }
      enum "block" {
        value 3;
        description
          "Block packet.";
      }
      enum "suppress" {
        value 4;
        description
          "Suppress packet.";
      }
    }
    description
      "The packet's state of the current interface.";
  }
  typedef switch-status {
    type enumeration {
      enum off {
        value 0;
        description "The status is off.";
      }
      enum on {
        value 1;
        description "The status is on.";
      }
    }
    description "The switch status of storm-control.";
  }
  grouping storm-control-config{
      description "Config storm control function.";
      container storm-rates {
        description
          "List of storm rate config.";
        list storm-rate {
          key "packet-type";
          description
            "Configure packet-type which storm control support.";
          leaf packet-type {
            type packet-type;
            must "../pps-min-rate or ../per-min-rate or ../cir-min-rate";
            description
              "Type of packets going through an interface.";
          }
          choice rate-type {
            description
              "Type of min-rate and max-rate parameters.";
            case packet {
              description
                "Packet mode.";
              leaf pps-min-rate {
		type uint32 {
                  range "1..595240000";
                }
                units "pps";
		must "../pps-max-rate and (../pps-min-rate<=../pps-max-rate)";
                description
                  "Specifies the lower threshold.";
              }
              leaf pps-max-rate {
				type uint32 {
                  range "1..595240000";
                }
                units "pps";
		must "../pps-min-rate and (../pps-max-rate>=../pps-min-rate)";
                description
                  "Specifies the upper threshold.";
              }
            }
            case cir {
              description
                "Cir mode.";
              leaf cir-min-rate {
                type uint32 {
                  range "1..800000000";
                }
                units "kbit/s";
	        must "../cir-max-rate and (../cir-min-rate<=../cir-max-rate)";
                description
                  "Specifies the lower threshold.";
              }
              leaf cir-max-rate {
                type uint32 {
                  range "1..800000000";
                }
                units "kbit/s";
		must "(../cir-max-rate>=../cir-min-rate) and ../cir-min-rate";
                description
                  "Specifies the upper threshold.";
              }
            }
            case percent {
              description
                "Percent mode.";
              leaf per-min-rate {
                type uint32 {
                  range "1..100";
                }
                units "%";
		must "../per-max-rate and (../per-min-rate<=../per-max-rate)";
                description
                  "Specifies the lower threshold.";
              }
              leaf per-max-rate {
                type uint32 {
                  range "1..100";
                }
                units "%";
		must "../per-min-rate and (../per-max-rate>=../per-min-rate)";
                description
                  "Specifies the upper threshold.";
              }
            }
          }
        }
      }
  }

  grouping storm-suppress-config{
      description "Config storm suppress function.";
      container storm-rates {
        description
          "List of storm suppress rate config.";
        list storm-rate {
          key "packet-type";
          description
            "Configure packet-type which storm suppress support.";
          leaf packet-type {
            type packet-type;
            must "../pps or ../cir or ../percent or (../cir and ../cbs)";
            description
              "Type of packets going through an interface.";
          }
          choice rate-type {
            description
              "Type of rate parameters.";
            case packet {
                description
                    "Packet mode.";
                leaf pps {
                    type uint32 {
			range "0..595240000";
		    }
                    units "pps";
                    description
                      "Pps value.";
                }
            }
            case rate {
              description
                "Cir mode.";
              leaf cir {
                type uint32 {
                  range "0..4294967295";
                }
                units "kbit/s";
                description
                  "Cir value.";
              }
              leaf cbs {
                type uint32{
                  range "10000..4294967295";
                }
                units "kbit/s";
		must "../cir";
                description
                  "Cbs value.";
              }
            }
            case percent {
              description
                "Percent mode.";
              leaf percent {
                type uint32 {
                  range "0..100";
                }
                units "%";
                description
                  "Percent type.";
              }
            }
          }
        }
      }

      container storm-suppress-action {
        description
          "Configure action of storm-suppress.";
          leaf log {
              type boolean;
              default "false";
              description
                "Enable/disable the log recording function.";
          }
          leaf trap {
              type boolean;
              default "false";
              description
                "Enable/disable the trap reporting function.";
          }      
      }
  }
  
  grouping storm-suppress-mac-flapping {
    description
      "Configure storm suppression when mac flapping.";
    container vlan-suppress {
      presence "Enable VLAN storm suppress";
      description
        "Configure VLAN storm suppression when mac flapping.";
  	  leaf force {
        type boolean;
        default "false";
        description
          "Enable/disable VLAN storm suppress force.";
      }
      leaf cir {
        type uint32 {
          range "64..4294967295";
        }
        units "kbit/s";
        mandatory true;
        description
          "VLAN storm suppress Cbs value.";
      }
    }
  }

  ext:task-name "cpu-defend";
  container storm-control {
    description
    "Configure of storm-control.";
    
    uses storm-suppress-mac-flapping;

    uses storm-control-config;

    container storm-control-action {
    description
        "Configure action of storm-control.";
        leaf action {
            type action;
            description
            "Action of storm control.";
        }
        leaf log {
            type boolean;
            default "false";
            description
            "Enable/disable the log recording function.";
        }
        leaf trap {
            type boolean;
            default "false";
            description
            "Enable/disable the trap reporting function.";
        }
        leaf interval {
            type uint16 {
                range "1..180";
            }
            units "s";
            default "5";
            description
            "Specifies the storm detection interval (units seconds).";
        }
    }
  }
  augment /ifm:ifm/ifm:interfaces/ifm:interface {
    description
      "This module contains a collection of YANG definitions for
      managing network interfaces.";
    container storm-control {
      when "(../ifm:type='800GE' or ../ifm:type='400GE' or ../ifm:type='200GE' or ../ifm:type='100GE' or  ../ifm:type='50GE' or ../ifm:type='40GE' or ../ifm:type='25GE' or ../ifm:type='10GE' or ../ifm:type='GigabitEthernet' or ../ifm:type='GEBrief' or ../ifm:type='MultiGE' or ../ifm:type='XGigabitEthernet')";
      description
        "Configure of storm-control applies only to L2 physical interfaces or L2 trunk member interfaces.";

      uses storm-control-config;

      container storm-control-action { 
        description
          "Configure action of storm-control.";
          leaf action {
              type action;
              description
                "Action of storm control.";
          }
          leaf log {
              type boolean;
              default "false";
              description
                "Enable/disable the log recording function.";
          }
          leaf trap {
              type boolean;
              default "false";
              description
                "Enable/disable the trap reporting function.";
          }
          leaf interval {
              type uint16 {
                  range "1..180";
              }
              units "s";
              default "5";
              description
                "Specifies the storm detection interval (units seconds).";
          }
      }
      container storm-control-state {
          config false;
          description
            "Show The storm-control's state.";
          leaf packet-type {
              type packet-type;
              description
                "Type of packets going through an interface.";
          }
          leaf punish {
              type punish-status;
              description
                "Punish status of storm-control table.";
          }
          leaf last-punish-time {
              type yang:date-and-time;
              description
                "Last punish time of storm-control table.";
          }
          leaf mode {
              type mode-state;
              description
                "Mode of storm-control table.";
          }
          leaf port-name {
              type string {
                length "1..255";
              }
              description
                "Interface name.";
          }
          leaf min-rate{
              type uint32;
              description
                "The minimum threshold.";
          } 
          leaf max-rate{
              type uint32;
              description
                "The maximum threshold.";
          }
          leaf action-state{
              type action;
              description
                "Storm control actions.";
          }
          leaf trap-state{
              type switch-status;
              description
                "Alarm switch status.";
          }
          leaf log-state{
              type switch-status;
              description
                "Log switch status.";
          }
          leaf interval{
              type uint16 {
                range "1..180";
              }
              units "s";
              description
                "The detection interval of the storm control.";
          }
      }
    }
  
    container storm-suppress {
      when "(../ifm:type='800GE' or ../ifm:type='400GE' or ../ifm:type='200GE' or ../ifm:type='100GE' or  ../ifm:type='50GE' or ../ifm:type='40GE' or ../ifm:type='25GE' or ../ifm:type='10GE' or ../ifm:type='GigabitEthernet' or ../ifm:type='GEBrief' or ../ifm:type='MultiGE' or ../ifm:type='XGigabitEthernet')";
      description
        "Configure of storm-control applies only to L2 physical interfaces or L2 trunk member interfaces.";
      uses storm-suppress-config;
    }
  }

  augment "/bd:bd/bd:instances/bd:instance" {
    description
      "Add storm in bridge domain.";
    container storm-control {
      description
        "Configure of storm-control in bridge domain.";
      uses storm-control-config;
    }

    container storm-suppress {
      description
        "Configure of storm-suppress in bridge domain.";
      uses storm-suppress-config;
    }
  }

  augment "/vlan:vlan/vlan:vlans/vlan:vlan" {
    description
      "Add storm VLAN.";
    container storm-suppress {
      description
        "Configure of storm-suppress in VLAN.";
      uses storm-suppress-config;
    }
  }

  augment "/l2vpn:l2vpn/l2vpn:instances/l2vpn:instance/l2vpn:vpls" {
    description
      "Add storm VSI.";
    container storm-suppress {
      description
        "Configure of storm-suppress in VSI.";
      uses storm-suppress-config;
    }
  }
}
