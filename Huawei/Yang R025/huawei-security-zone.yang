/*
Copyright (C) 2020-2024 Huawei Technologies Co., Ltd. All rights reserved.
*/
module huawei-security-zone {
  namespace "urn:huawei:yang:huawei-security-zone";
  prefix hw-security-zone;

  import huawei-ifm {
    prefix ifm;
  }
  import huawei-extension {
    prefix ext;
  }

  organization
  "Huawei Technologies Co., Ltd.";

  contact
    "Huawei Industrial Base
    Bantian, Longgang
    Shenzhen 518129
    People's Republic of China
    Website: http://www.huawei.com
    Email: support@huawei.com";

  description
  "This module contains a collection of YANG definitions for
  managing security zone.";

  revision 2024-01-23 {
    description
      "Add the configuration mode for adding an interface to a security zone.";
    reference "";
  }
  revision 2023-01-10 {
    description
      "Change zone desc length.";
    reference "";
  }
  revision 2020-02-17 {
    description
    "Initial revision.";
    reference
    "A YANG Data Model for Security Zone.";
  }

  typedef security-zone-name {
	  type string {
		  length "1..32";
	  }
	  description "This type represents a security zone name of the device. Predefined zone contains trust, untrust, dmz and local.";
  }
  
  typedef security-zone-name-ref {
    type leafref {
      path "/hw-security-zone:security-zone/hw-security-zone:zone-instances/hw-security-zone:zone-instance/hw-security-zone:name";
    }
    description
      "This type is used by data models that need to reference
       configured security-zone.";
  }

  ext:task-name "security-zone";
  container security-zone {
    description 
      "Describe a security zone.";
    container global {
      description
        "Configure the security-zone configurations.";
      leaf interface-assignment-mode {
        type enumeration {
          enum "both" {
            value 0;
            description
              "Indicate that the method is huawei-security-zone and huawei-ifm path.";
          }
          enum "security-zone" {
            value 1;
            description
              "Indicate that the method is huawei-security-zone path.";
          }
          enum "interface" {
            value 2;
            description
              "Indicate that the method is huawei-ifm path.";
          }
        }
        default "both";
        description
          "Indicates the configuration mode for adding an interface to a security zone.";
      }
    }
    container zone-instances {
      description 
        "List of zone instance.";
      list zone-instance {
        key "name";
        unique "id";
        unique "priority";
        description 
          "Configure a security-zone.";
        ext:generated-by system {
          ext:filter "name = 'dmz' or name = 'local' or name = 'trust' or name = 'untrust'";
          description "The dmz local trust untrust is generated automatically.";
        }
        leaf name {
          type security-zone-name;
          description
            "Indicate zone name.";
        }

        leaf id {
          ext:operation-exclude update;
          type uint32 {
            range "0..999";
          }
          description
            "Indicate zone id.";
        }

        leaf desc {
          type string {
            length "1..128";
          }
          description
            "Indicate description of zone.";        
        }

        leaf priority {
          type uint8 {
            range "1..100";
          }
          description 
            "Indicate the security zone priority.";
        }

        leaf-list assign-interface {
          type string {                                                                                                             
            length "1..63";                                                                                                         
          }
          description 
            "Assign port to zone.";
        }
      } 
    }
  }

  augment "/ifm:ifm/ifm:interfaces/ifm:interface" {
    description
      "Data nodes for the operational on interfaces.";

    container security-zone {
      description 
        "Configure of security zone parameters for interfaces.";
      leaf zone {
        type security-zone-name-ref;
        description 
          "Describe a security zone.";
      }      
    }
  }
}
