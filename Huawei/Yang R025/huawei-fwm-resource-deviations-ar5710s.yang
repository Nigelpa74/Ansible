/*
Copyright (C) 2025 Huawei Technologies Co., Ltd. All rights reserved.
*/
module huawei-fwm-resource-deviations-ar5710s {
  namespace "urn:huawei:yang:huawei-fwm-resource-deviations-ar5710s";
  prefix fwm-resource-devs-ar5710s;

  import huawei-fwm-resource {
    prefix fwm-resource;
  }

  organization
    "Huawei Technologies Co., Ltd.";
  contact
    "Huawei Industrial Base
     Bantian, Longgang
     Shenzhen 518129
     People's Republic of China
     Website: http://www.huawei.com
     Email: support@huawei.com";
  description
    "This module defines deviation statements for huawei-fwm-resource module.";

  revision 2025-02-24 {
    description
      "Initial revision.";
    reference "Huawei private.";
  }

  deviation "/fwm-resource:fwm-resource" {
    deviate not-supported;
  }
}
