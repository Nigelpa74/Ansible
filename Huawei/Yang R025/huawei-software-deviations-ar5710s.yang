/*
Copyright (C) 2023 Huawei Technologies Co., Ltd. All rights reserved.
*/
module huawei-software-deviations-ar5710s {
  namespace "urn:huawei:yang:huawei-software-deviations-ar5710s";
  prefix software-devs-ar5710s;

  import huawei-software {
    prefix software;
  }

  organization
    "Huawei Technologies Co., Ltd.";
  contact
    "Huawei Industrial Base
     Bantian, Longgang
     Shenzhen 518129
     People's Republic of China
     Website: http://www.huawei.com
     Email: support@huawei.com";
  description
    "This module defines deviation statements for huawei-software module.";

  revision 2023-10-27 {
    description
      "Initial revision.";
    reference "Huawei private.";
  }

  deviation "/software:software/software:startup-packages/software:startup-package/software:current-package-partition" {
    deviate not-supported;
  }
  deviation "/software:software/software:upgrade-rollback-versions" {
    deviate not-supported;
  }
  deviation "/software:software/software:upgrade-package-infos" {
    deviate not-supported;
  }
  deviation "/software:software/software:upgrade-action-results" {
    deviate not-supported;
  }
  deviation "/software:software/software:download-result" {
    deviate not-supported;
  }
  deviation "/software:refresh-startup-secure-version-configuration" {
    deviate not-supported;
  }
  deviation "/software:in-service-upgrade-feature-software" {
    deviate not-supported;
  }
  deviation "/software:rollback-feature-software" {
    deviate not-supported;
  }
  deviation "/software:download-upgrade-package" {
    deviate not-supported;
  }
  deviation "/software:load-upgrade-package" {
    deviate not-supported;
  }
  deviation "/software:activate-upgrade-package" {
    deviate not-supported;
  }
  deviation "/software:rollback-upgrade-package" {
    deviate not-supported;
  }
  deviation "/software:delete-upgrade-package" {
    deviate not-supported;
  }
  deviation "/software:clean-discarded-package" {
    deviate not-supported;
  }
  deviation "/software:cancel-download-upgrade-package" {
    deviate not-supported;
  }
  deviation "/software:software/software:integrated-infos" {
    deviate not-supported;
  }
  deviation "/software:integrate-software-package" {
    deviate not-supported;
  }
  deviation "/software:restore-software-package" {
    deviate not-supported;
  }
}
