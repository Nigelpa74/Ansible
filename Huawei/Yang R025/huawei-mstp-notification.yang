/*
Copyright (C) 2019-2025 Huawei Technologies Co., Ltd. All rights reserved.
*/
module huawei-mstp-notification {
  yang-version 1;
  namespace "urn:huawei:yang:huawei-mstp-notification";
  prefix mstp-notification;
  import huawei-pub-type {
    prefix pub-type;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of MSTP.";
  revision 2025-05-07 {
    description
      "Add notification vstp-mac-different-rising and vstp-mac-different-resume.";
    reference
      "Huawei private.";
  }
  revision 2024-08-23 {
    description
      "Add notification port-state-forwarding and port-state-discarding.";
    reference
      "Huawei private.";
  }
    revision 2022-08-05 {
    description
      "Add notification protocol-loopback-detected-rising and protocol-loopback-detected-resume.";
    reference
      "Huawei private.";
  }
  revision 2019-07-08 {
    description
      "Initial revision.";
    reference
      "Huawei private.";
  }
  ext:task-name "mstp";
  notification tc-flap-receive {
    description
      "The local device received many TC BPDUs from neighbors.";
    leaf process-id {
      type uint32;
      description
        "Process ID.";
    }
    leaf instance-id {
      type uint32;
      description
        "MSTP instance ID.";
    }
    leaf if-index {
      type uint32;
      description
        "Interface index.";
    }
    leaf if-name {
      type pub-type:if-name;
      description
        "Interface name.";
    }
    leaf pw-name {
      type string {
        length "1..15";
      }
      description
        "PW name.";
    }
    leaf src-mac {
      type pub-type:mac-address;
      description
        "Source MAC address.";
    }
  }
  notification tc-flap {
    description
      "The local device proactively detected that its STP topology was flapping.";
    leaf process-id {
      type uint32;
      description
        "MSTP process ID.";
    }
    leaf instance-id {
      type uint32;
      description
        "Multiple spanning tree instance (MSTI) ID.";
    }
  }
  notification tc-flap-resume {
    description
      "The STP topology of the local device stopped flapping.";
    leaf process-id {
      type uint32;
      description
        "MSTP process ID.";
    }
    leaf instance-id {
      type uint32;
      description
        "Multiple spanning tree instance (MSTI) ID.";
    }
  }
  notification process-loopback-detected {
    description
      "When port detected loopback, block the port and arise trap.";
    leaf process-id {
      type uint32;
      description
        "Process ID.";
    }
    leaf instance-id {
      type uint32;
      description
        "MSTP instance ID.";
    }
    leaf port-index {
      type uint32;
      description
        "Port index.";
    }
    leaf vr-id {
      type uint32;
      description
        "Virtual router ID.";
    }
    leaf vsi-id {
      type uint32;
      description
        "VSI ID.";
    }
    leaf ext-port-index {
      type uint32;
      description
        "Extend port ID.";
    }
    leaf port-flag {
      type uint32;
      description
        "Port Flag.";
    }
    leaf port-state {
      type uint32;
      description
        "Port State.";
    }
    leaf if-index {
      type uint32;
      description
        "Interface index.";
    }
    leaf if-name {
      type pub-type:if-name;
      description
        "Interface name.";
    }
    leaf pw-name {
      type string {
        length "1..15";
      }
      description
        "PW name.";
    }
  }
  notification protocol-loopback-detected-rising {
    description
      "The MSTP process's port has been set to discarding state because loopback of protocol packets is detected.";
    leaf process-id {
      type uint32;
      description
        "Process ID.";
    }
    leaf instance-id {
      type uint32;
      description
        "MSTP instance ID.";
    }
    leaf port-index {
      type uint32;
      description
        "Port index.";
    }
    leaf vr-id {
      type uint32;
      description
        "Virtual router ID.";
    }
    leaf vsi-id {
      type uint32;
      description
        "VSI ID.";
    }
    leaf ext-port-index {
      type uint32;
      description
        "Extend port ID.";
    }
    leaf port-flag {
      type uint32;
      description
        "Port Flag.";
    }
    leaf port-state {
      type uint32;
      description
        "Port State.";
    }
    leaf if-index {
      type uint32;
      description
        "Interface index.";
    }
    leaf if-name {
      type pub-type:if-name;
      description
        "Interface name.";
    }
    leaf pw-name {
      type string {
        length "1..15";
      }
      description
        "PW name.";
    }
  }
  notification protocol-loopback-detected-resume {
    description
      "The MSTP process's port has been set to forwarding state because loopback of protocol packets is not detected for a long time.";
    leaf process-id {
      type uint32;
      description
        "Process ID.";
    }
    leaf instance-id {
      type uint32;
      description
        "MSTP instance ID.";
    }
    leaf port-index {
      type uint32;
      description
        "Port index.";
    }
    leaf vr-id {
      type uint32;
      description
        "Virtual router ID.";
    }
    leaf vsi-id {
      type uint32;
      description
        "VSI ID.";
    }
    leaf ext-port-index {
      type uint32;
      description
        "Extend port ID.";
    }
    leaf port-flag {
      type uint32;
      description
        "Port Flag.";
    }
    leaf port-state {
      type uint32;
      description
        "Port State.";
    }
    leaf if-index {
      type uint32;
      description
        "Interface index.";
    }
    leaf if-name {
      type pub-type:if-name;
      description
        "Interface name.";
    }
    leaf pw-name {
      type string {
        length "1..15";
      }
      description
        "PW name.";
    }
  }
  notification port-state-forwarding {
    description
    "The MSTP process's port has been set to forwarding state.";
    leaf process-id {
      type uint32;
      description
        "MSTP process ID.";
    }
    leaf instance-id {
      type uint32;
      description
        "MSTP instance ID.";
    }
    leaf port-index {
      type uint32;
      description
        "Port index.";
    }
    leaf if-index {
      type uint32;
      description
        "Interface index.";
    }
    leaf if-name {
      type pub-type:if-name;
      description
        "Interface name.";
    }
    leaf pw-name {
      type string {
        length "1..15";
      }
      description
        "PW name.";
    }
  }
  notification port-state-disacarding {
    description
    "The MSTP process's port has been set to disacarding state.";
    leaf process-id {
      type uint32;
      description
        "MSTP process ID.";
    }
    leaf instance-id {
      type uint32;
      description
        "MSTP instance ID.";
    }
    leaf port-index {
      type uint32;
      description
        "Port index.";
    }
    leaf if-index {
      type uint32;
      description
        "Interface index.";
    }
    leaf if-name {
      type pub-type:if-name;
      description
        "Interface name.";
    }
    leaf pw-name {
      type string {
        length "1..15";
      }
    description
      "PW name.";
    }
  }
  notification vstp-mac-different-rising {
    description
    "The bridge MAC addresses of master and backup devices in V-STP mode are different.";
    leaf master-mac {
      type pub-type:mac-address;
      description
        "Bridge MAC addresses of master device in V-STP mode.";
    }
    leaf backup-mac {
      type pub-type:mac-address;
      description
        "Bridge MAC addresses of backup device in V-STP mode.";
    }
  }
  notification vstp-mac-different-resume {
    description
    "The bridge MAC addresses of master and backup devices in V-STP mode are the same.";
    leaf master-mac {
      type pub-type:mac-address;
      description
        "Bridge MAC addresses of master device in V-STP mode.";
    }
    leaf backup-mac {
      type pub-type:mac-address;
      description
        "Bridge MAC addresses of backup device in V-STP mode.";
    }
  }
}
