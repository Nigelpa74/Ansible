/*
Copyright (C) 2019-2024 Huawei Technologies Co., Ltd. All rights reserved.
*/
submodule huawei-dhcpv6-relay {
  belongs-to huawei-dhcpv6 {
    prefix dhcpv6;
  }
  import ietf-inet-types {
    prefix inet;
  }
  import huawei-ifm {
    prefix ifm;
  }
  import huawei-vlan {
    prefix vlan;
  }
  import huawei-network-instance {
    prefix ni;
  }
  import huawei-pub-type {
    prefix pub-type;
  }
  import ietf-yang-types {
    prefix yang;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "This module contains a collection of YANG definitions for managing DHCPv6 relay.";
  revision 2024-08-22 {
    description
      "Modify save-file-name type, delete pattern.";
    reference
      "Huawei private.";
  }
  revision 2024-06-15 {
    description
      "Expand the type of fail cause.";
    reference
      "Huawei private.";
  }
  revision 2022-07-04 {
    description
      "Add unit to packet statistics.";
    reference
      "Huawei private.";
  }
  revision 2022-02-19 {
    description
      "Modify userinfos node.";
    reference
      "Huawei private.";
  }
  revision 2022-02-18 {
    description
      "Modify ip prefix description for client-infos and client-fail-infos nodes.";
    reference
      "Huawei private.";
  }
  revision 2022-02-14 {
    description
      "Add client-infos and client-fail-infos nodes.";
    reference
      "Huawei private.";
  }
  revision 2022-01-25 {
    description
      "Delete reset dhcpv6 relay user node.";
    reference
      "Huawei private.";
  }
  revision 2022-01-05 {
    description
      "Remove redundant config false.";
    reference
      "Huawei private.";
  }
  revision 2021-12-13 {
    description
      "Modify pattern.";
    reference
      "Huawei private.";
  }
  revision 2021-05-13 {
    description
      "Add vpn-name node to the server-group.";
    reference
      "Huawei private.";
  }
  revision 2020-04-17 {
    description
      "Add node.";
    reference
      "Huawei private.";
  }
  revision 2020-03-09 {
    description
      "Modify description.";
    reference
      "Huawei private.";
  }
  revision 2019-12-16 {
    description
      "Initial revision.";
    reference
      "Huawei private.";
  }
  typedef rapid-commit-flag-type {
    type enumeration {
      enum "off" {
        value 0;
        description
          "Disable rapid commit.";
      }
      enum "on" {
        value 1;
        description
          "Enable rapid commit.";
      }
    }
    description
      "The type of rapid commit flag.";
  }
  typedef relay-table-status {
    type enumeration {
      enum "init" {
        value 0;
        description
          "Init status.";
      }
      enum "solicit" {
        value 1;
        description
          "Send solicit packet to server.";
      }
      enum "advertise" {
        value 2;
        description
          "Send Advertise packet to client.";
      }
      enum "request" {
        value 3;
        description
          "Send request packet to server.";
      }
      enum "renewrebind" {
        value 4;
        description
          "Send renew or rebind packet to server.";
      }
      enum "confirm" {
        value 5;
        description
          "Send confirm packet to server.";
      }
      enum "decline" {
        value 6;
        description
          "Send decline packet to server.";
      }
      enum "release" {
        value 7;
        description
          "Send release packet to server.";
      }
      enum "up" {
        value 8;
        description
          "Stable status.";
      }
      enum "error" {
        value 9;
        description
          "Error status.";
      }
    }
    description
      "The type of relay table status.";
  }
  typedef ia-type {
    type enumeration {
      enum "iainvalid" {
        value 0;
        description
          "Invalid identity association.";
      }
      enum "iana" {
        value 1;
        description
          "Identity association for non-temporary addresses.";
      }
      enum "iata" {
        value 2;
        description
          "Identity association for temporary addresses.";
      }
      enum "iapd" {
        value 3;
        description
          "Identity association for prefix delegation.";
      }
    }
    description
      "The type of identity association.";
  }
  typedef fail-cause {
    type enumeration {
      enum "useless" {
        value 0;
        description
          "Invalid status.";
      }
      enum "info-request-packet-delete" {
        value 1;
        description
          "DHCPv6 information request entries created using information-request packets and deleted after packet exchange.";
      }
      enum "address-allocation-failure" {
        value 2;
        description
          "IPv6 address allocation failure.";
      }
      enum "prefix-allocation-failure" {
        value 3;
        description
          "IPv6 prefix allocation failure.";
      }
      enum "address-renewal-failure" {
        value 4;
        description
          "IPv6 address renewal failure.";
      }
      enum "prefix-renewal-failure" {
        value 5;
        description
          "IPv6 prefix renewal failure.";
      }
      enum "confirm-packet-delete" {
        value 6;
        description
          "A user created by confirm packets is deleted after the status code in reply messages sent by the server returns fail.";
      }
      enum "client-decline-address" {
        value 8;
        description
          "Users send DHCP decline packets to release conflicted addresses.";
      }
      enum "client-release-address" {
        value 9;
        description
          "Users send DHCP release packets to release conflicted addresses.";
      }
      enum "relay-interface-delete" {
        value 10;
        description
          "A user is deleted after the relay interface is deleted.";
      }
      enum "vpn-configuration-delete" {
        value 11;
        description
          "A user is deleted after the relay interface is unbound from a VPN instance.";
      }
      enum "user-timeout" {
        value 12;
        description
          "A relay user entry times out.";
      }
      enum "resend-solicit" {
        value 13;
        description
          "A client resends solicit packets to request the IA option.";
      }
      enum "address-conflict" {
        value 14;
        description
          "The IPv6 address assigned by the server is used by another client.";
      }
      enum "lease-timeout" {
        value 15;
        description
          "The valid lifetime expired.";
      }
      enum "add-pd-route-failure" {
        value 16;
        description
          "Failed to add PD routes.";
      }
      enum "mac-duid-mismatch" {
        value 17;
        description
          "The user MAC address or DUID does not match that of an online user.";
      }
      enum "reach-limit" {
        value 18;
        description
          "The interface or VLAN limit is reached.";
      }
      enum "entry-resource-allocation-failure" {
        value 19;
        description
          "Failed to allocate DHCPv6 relay user entry resources.";
      }
      enum "index-resource-allocation-failure" {
        value 20;
        description
          "Failed to allocate DHCPv6 relay user table index resources.";
      }
      enum "update-user-entry-failure" {
        value 21;
        description
          "Failed to update DHCPv6 relay user entries.";
      }
      enum "add-user-entry-failure" {
        value 22;
        description
          "Failed to add DHCPv6 relay user entries on a board, causing a PD option release.";
      }
      enum "command-reset" {
        value 23;
        description
          "User entries are deleted by the reset dhcpv6 relay command.";
      }
      enum "interface-information-changed" {
        value 24;
        description
          "The relay interface information changed.";
      }
      enum "duid-changed" {
        value 25;
        description
          "The client DUID changed.";
      }
      enum "max-session-reached" {
        value 26;
        description
          "The global max session reached.";
      }
      enum "remote-backup-user-age" {
        value 27;
        description
          "The remote backup user is aged.";
      }
      enum "remote-backup-user-release" {
        value 28;
        description
          "The remote backup user is released.";
      }
      enum "remote-backup-ip-full" {
        value 29;
        description
          "The number of remote backup IP tables reaches limit.";
      }
      enum "remote-backup-user-conflict" {
        value 30;
        description
          "The remote backup user is conflicted.";
      }
      enum "nd-detect-offline" {
        value 31;
        description
          "The user is deleted after ND detect.";
      }
      enum "no-user-for-reply" {
        value 32;
        description
          "No user can be found in reply message.";
      }
      enum "other-reason" {
        value 33;
        description
          "Other reason.";
      }
    }
    description
      "The type of fail cause.";
  }
  typedef address-state {
    type enumeration {
      enum "init" {
        value 0;
        description
          "Init state.";
      }
      enum "solicit" {
        value 1;
        description
          "Send solicit packet.";
      }
      enum "advertise" {
        value 2;
        description
          "Send advertise packet.";
      }
      enum "request" {
        value 3;
        description
          "Send request packet.";
      }
      enum "renew-rebind" {
        value 4;
        description
          "Send renew or rebind packet.";
      }
      enum "confirm" {
        value 5;
        description
          "Send confirm packet.";
      }
      enum "decline" {
        value 6;
        description
          "Send decline packet.";
      }
      enum "release" {
        value 7;
        description
          "Send release packet.";
      }
      enum "up" {
        value 8;
        description
          "Stable status.";
      }
      enum "error" {
        value 9;
        description
          "Error status.";
      }
    }
    description
      "The type of address status.";
  }
  typedef relay-file-authentication-mode {
    type enumeration {
      enum "check" {
        value 0;
        description
          "Check.";
      }
      enum "no-check" {
        value 1;
        description
          "No-check.";
      }
      enum "force-check" {
        value 2;
        description
          "Force-check.";
      }
    }
    description
      "The type of file authentication mode.";
  }
  grouping dhcpv6-relay-type {
    description
      "DHCPv6 relay.";
    container global {
      description
        "Configure global function of DHCPv6 relay.";
      leaf insert-option79 {
        type boolean;
        default "false";
        description
          "Enable/disable inserting the Option79 field into DHCPv6 messages.";
      }
      leaf source-interface {
        type leafref {
          path "/ifm:ifm/ifm:interfaces/ifm:interface/ifm:name";
        }
        description
          "Configure the IPv6 address of an interface as the source IPv6 address of packets.";
      }
    }
    container pd-route {
      description
        "Configure DHCPv6 PD route.";
      leaf export {
        type boolean;
        default "false";
        description
          "Enable/disable DHCPv6 export PD route.";
      }
      leaf save-file-name {
        type string {
          length "10..69";
        }
        description
          "Name of the file for saving PD routes. For example, the name can be in the format of cfcard:/dhcp/xxx.pd or home:/dhcp/xxx.pd, where xxx can be any characters.";
      }
      leaf write-route-delay {
        type uint32 {
          range "1..1440";
        }
        units "min";
        default "5";
        description
          "The delay time for saving PD routes.";
      }
      leaf write-route-number {
        type uint32 {
          range "40960..1310720";
        }
        default "40960";
        description
          "The number for saving PD routes. Only 40960 userinfo table items can be written to a board with memory less than 16 GB, and other boards support 1310720 userinfo table items.";
      }
      leaf access-limit {
        type uint32 {
          range "40960..655360";
        }
        description
          "Maximum number of access users.";
      }
      leaf file-authentication-mode {
        type relay-file-authentication-mode;
        default "check";
        description
          "Set file authentication mode.";
      }
    }
    container option18-formats {
      description
        "List of the format of the Option 18 field in a DHCPv6 message.";
      list option18-format {
        key "vlan ce-vlan";
        description
          "Configure the format of the Option 18 field in a DHCPv6 message.";
        leaf vlan {
          type uint16 {
            range "0..4094";
          }
          description
            "Specify the outer VLAN ID. Zero is no VLAN.";
        }
        leaf ce-vlan {
          type uint16 {
            range "0..4096";
          }
          description
            "Specify the inner VLAN ID.Zero is no ce VLAN.";
        }
        leaf user-defined {
          type string {
            length "1..251";
          }
          description
            "Indicate the user-defined format of the Option 18 field.";
        }
      }
    }
    container option37-formats {
      description
        "List of the format of the Option 37 field in a DHCPv6 message.";
      list option37-format {
        key "vlan ce-vlan";
        description
          "Configure the format of the Option 37 field in a DHCPv6 message.";
        leaf vlan {
          type uint16 {
            range "0..4094";
          }
          description
            "Specify the outer VLAN ID. Zero is no VLAN.";
        }
        leaf ce-vlan {
          type uint16 {
            range "0..4096";
          }
          description
            "Specify the inner VLAN ID.Zero is no ce VLAN.";
        }
        leaf user-defined {
          type string {
            length "1..251";
          }
          description
            "Indicate the user-defined format of the Option 37 field.";
        }
      }
    }
    container server-groups {
      description
        "List of DHCPv6 relay server groups.";
      list server-group {
        key "name";
        max-elements "10";
        description
          "Configure a DHCPv6 relay server group.";
        leaf name {
          type string {
            length "1..32";
          }
          description
            "DHCPv6 relay server group name.";
        }
        leaf vpn-name {
          type leafref {
            path "/ni:network-instance/ni:instances/ni:instance/ni:name";
          }
          description
            "VPN name.";
        }
        container server-addresses {
          description
            "List of DHCPv6 relay destination servers in a server group.";
          list server-address {
            key "server";
            max-elements "20";
            description
              "Configure a DHCPv6 relay destination server in a server group.";
            leaf server {
              type inet:ipv6-address-no-zone;
              description
                "DHCPv6 relay destination server address in a server group.";
            }
            leaf interface-name {
              type leafref {
                path "/ifm:ifm/ifm:interfaces/ifm:interface/ifm:name";
              }
              description
                "Specify the type and number of an outbound interface for DHCPv6 packets.";
            }
          }
        }
        container server-address-ifs {
          description
            "List of DHCPv6 relay destination servers with interface-name in a server group.";
          list server-address-if {
            key "server-address interface-name";
            max-elements "20";
            description
              "Configure a DHCPv6 relay destination server in a server group.";
            leaf server-address {
              type inet:ipv6-address-no-zone;
              description
                "DHCPv6 relay destination server address in a server group.";
            }
            leaf interface-name {
              type leafref {
                path "/ifm:ifm/ifm:interfaces/ifm:interface/ifm:name";
              }
              description
                "Specify the type and number of an outbound interface for DHCPv6 packets.";
            }
          }
        }
      }
    }
    container global-packet-statistics {
      config false;
      description
        "Statistics of a DHCPv6 relay global packet.";
      leaf received-from-clients {
        type uint32;
        units packet;
        description
          "Packets received from clients.";
      }
      leaf solicit-received {
        type uint32;
        units packet;
        description
          "Solicit packets received from clients.";
      }
      leaf request-received {
        type uint32;
        units packet;
        description
          "Request packets received from clients.";
      }
      leaf confirm-received {
        type uint32;
        units packet;
        description
          "Confirm packets received from clients.";
      }
      leaf renew-received {
        type uint32;
        units packet;
        description
          "Renew packets received from clients.";
      }
      leaf rebind-received {
        type uint32;
        units packet;
        description
          "Rebind packets received from clients.";
      }
      leaf decline-received {
        type uint32;
        units packet;
        description
          "Decline packets received from clients.";
      }
      leaf release-received {
        type uint32;
        units packet;
        description
          "Release packets received from clients.";
      }
      leaf inform-received {
        type uint32;
        units packet;
        description
          "Information-request packets received from clients.";
      }
      leaf received-from-relay-agents-or-servers {
        type uint32;
        units packet;
        description
          "Packets received from relay agents or servers.";
      }
      leaf relay-forward-received {
        type uint32;
        units packet;
        description
          "Relay-forward packets received from relay agents or servers.";
      }
      leaf relay-reply-received {
        type uint32;
        units packet;
        description
          "Relay-reply packets received from relay agents or servers.";
      }
      leaf sent-to-clients {
        type uint32;
        units packet;
        description
          "Packets sent to clients.";
      }
      leaf advertise-send {
        type uint32;
        units packet;
        description
          "Advertise packets sent to clients.";
      }
      leaf reply-send {
        type uint32;
        units packet;
        description
          "Relay-reply packets sent to clients.";
      }
      leaf reconfig-send {
        type uint32;
        units packet;
        description
          "Reconfigure packets sent to clients.";
      }
      leaf sent-to-relay-agents-or-servers {
        type uint32;
        units packet;
        description
          "Packets sent to relay agents or servers.";
      }
      leaf relay-forward-send {
        type uint32;
        units packet;
        description
          "Relay-forward packets sent to relay agents or servers.";
      }
      leaf relay-reply-send {
        type uint32;
        units packet;
        description
          "Relay-reply packets sent to relay agents or servers.";
      }
      leaf bad-packets-received {
        type uint32;
        units packet;
        description
          "Error packets received.";
      }
      leaf total-drop-packets {
        type uint32;
        units packet;
        description
          "Total dropped packets.";
      }
      leaf drop-packets-for-table-full {
        type uint32;
        units packet;
        description
          "Packets discarded because the table is full.";
      }
      leaf drop-packets-for-general-error {
        type uint32;
        units packet;
        description
          "Packets discarded due to general errors.";
      }
      leaf drop-packets-for-ipsec-authentication-fail {
        type uint32;
        units packet;
        description
          "Packets discarded due to IPsec authentication failures.";
      }
    }
    container access-vlans {
      config false;
      description
        "List of maximum number of access users that send VLAN tagged packets.";
      list access-vlan {
        key "access-limit pe-vlan ce-vlan";
        max-elements "8";
        description
          "Operational state of maximum number of access users that send VLAN tagged packets.";
        leaf access-limit {
          type uint32 {
            range "0..65536";
          }
          description
            "Maximum number of access users.";
        }
        leaf pe-vlan {
          type uint16;
          description
            "PE VLAN ID in QinQ.";
        }
        leaf ce-vlan {
          type boolean;
          description
            "Permit packets with any inner VLAN IDs.";
        }
        leaf vlan-batch {
          type pub-type:vlan-range;
          description
            "VLAN list.";
        }
      }
    }
    container user-infos {
      config false;
      description
        "List of user information.";
      list user-info {
        key "index";
        description
          "Operational state of user information.";
        leaf index {
          type uint32;
          description
            "User index.";
        }
        leaf client-duid {
          type string {
            length "1..256";
          }
          description
            "Client DUID.";
          ext:support-filter "true";
        }
        leaf iaid {
          type uint32;
          description
            "Identity association identifier.";
        }
        leaf ia-type {
          type ia-type;
          description
            "Identity association type.";
        }
        leaf server-duid {
          type string {
            length "1..256";
          }
          description
            "Server DUID.";
          ext:support-filter "true";
        }
        leaf server-address {
          type inet:ipv6-address-no-zone;
          description
            "Server IPv6 address.";
          ext:support-filter "true";
        }
        leaf if-name {
          type leafref {
            path "/ifm:ifm/ifm:interfaces/ifm:interface/ifm:name";
          }
          description
            "Interface name.";
          ext:support-filter "true";
        }
        leaf pe-vlan {
          type uint16 {
            range "0..4094";
          }
          description
            "PE VLAN ID.";
        }
        leaf ce-vlan {
          type uint16 {
            range "0..4094";
          }
          description
            "CE VLAN ID.";
        }
        leaf vpn-name {
          type leafref {
            path "/ni:network-instance/ni:instances/ni:instance/ni:name";
          }
          description
            "VPN name.";
          ext:support-filter "true";
        }
        leaf client-mac {
          type pub-type:mac-address;
          description
            "Client MAC address.";
          ext:support-filter "true";
        }
        leaf rapid-commit {
          type rapid-commit-flag-type;
          description
            "Rapid Commit option.";
        }
        leaf transaction-id {
          type uint32;
          description
            "Transaction ID.";
        }
        leaf info-transaction-id {
          type uint32;
          description
            "Info transaction ID.";
        }
        container iana-infos {
          description
            "List of identifying association for non-temporary addresses.";
          list iana-info {
            key "ipv6-address";
            description
              "Operational state of identifying association for non-temporary addresses.";
            leaf ipv6-address {
              type inet:ipv6-address-no-zone;
              description
                "IPv6 address.";
              ext:support-filter "true";
            }
            leaf server-duid {
              type string {
                length "1..256";
              }
              description
                "Server DUID.";
            }
            leaf server-address {
              type inet:ipv6-address-no-zone;
              description
                "Server IPv6 address.";
            }
            leaf valid-time {
              type string {
                length "0..30";
              }
              description
                "Valid time.";
            }
            leaf lease {
              type uint32;
              units s;
              description
                "Lease time.";
            }
            leaf remain-lease {
              type uint32;
              units s;
              description
                "Remaining lease.";
            }
            leaf status {
              type relay-table-status;
              description
                "Table status.";
            }
          }
        }
        container iapd-infos {
          description
            "List of identifying association for prefix delegation.";
          list iapd-info {
            key "ipv6-address";
            description
              "Operational state of identifying association for prefix delegation.";
            leaf ipv6-address {
              type inet:ipv6-address-no-zone;
              description
                "IPv6 address.";
              ext:support-filter "true";
            }
            leaf prefix {
              type uint32;
              description
                "IPv6 address prefix.";
            }
            leaf server-duid {
              type string {
                length "1..256";
              }
              description
                "Server DUID.";
            }
            leaf server-address {
              type inet:ipv6-address-no-zone;
              description
                "Server IPv6 address.";
            }
            leaf valid-time {
              type string {
                length "0..30";
              }
              description
                "Valid time.";
            }
            leaf lease {
              type uint32;
              units s;
              description
                "Lease time.";
            }
            leaf remain-lease {
              type uint32;
              units s;
              description
                "Remaining lease.";
            }
            leaf status {
              type relay-table-status;
              description
                "Table status.";
            }
          }
        }
      }
    }
    container client-infos {
      config false;
      description
        "List of client logout information.";
      list client-info {
        key "index";
        description
          "Operational state of client logout information.";
        leaf index {
          type uint32;
          description
            "Index.";
        }
        leaf client-duid {
          type string {
            length "1..256";
          }
          description
            "Client DUID.";
          ext:support-filter "true";
        }
        leaf ia-type {
          type ia-type;
          description
            "Identity association type.";
        }
        leaf iaid {
          type uint32;
          description
            "Identity association identifier.";
        }
        leaf if-name {
          type leafref {
            path "/ifm:ifm/ifm:interfaces/ifm:interface/ifm:name";
          }
          description
            "Interface name.";
          ext:support-filter "true";
        }
        leaf pevlan {
          type uint16 {
            range "0..4094";
          }
          description
            "PE VLAN ID.";
          ext:support-filter "true";
        }
        leaf cevlan {
          type uint16 {
            range "0..4094";
          }
          description
            "CE VLAN ID.";
          ext:support-filter "true";
        }
        leaf vpn-name {
          type leafref {
            path "/ni:network-instance/ni:instances/ni:instance/ni:name";
          }
          description
            "VPN name.";
        }
        leaf client-mac {
          type pub-type:mac-address {
            length "0..255";
          }
          description
            "Client MAC address.";
          ext:support-filter "true";
        }
        container iana-infos {
          description
            "List of identifying association for non-temporary addresses.";
          list iana-info {
            key "ipv6-address";
            description
              "Operational state of identifying association for non-temporary addresses.";
            leaf ipv6-address {
              type inet:ipv6-address-no-zone;
              description
                "IPv6 address.";
            }
            leaf release-cause {
              type fail-cause;
              description
                "Release cause.";
            }
            leaf release-status {
              type address-state;
              description
                "Release status.";
            }
            leaf release-time {
              type yang:date-and-time;
              description
                "Release time.";
            }
          }
        }
        container iapd-infos {
          description
            "List of identifying association for prefix delegation.";
          list iapd-info {
            key "ipv6-address";
            description
              "Operational state of identifying association for prefix delegation.";
            leaf ipv6-address {
              type inet:ipv6-address-no-zone;
              description
                "IPv6 address.";
            }
            leaf prefix {
              type uint32;
              description
                "IPv6 prefix.";
            }
            leaf release-cause {
              type fail-cause;
              description
                "Release cause.";
            }
            leaf release-status {
              type address-state;
              description
                "Release status.";
            }
            leaf release-time {
              type yang:date-and-time;
              description
                "Release time.";
            }
          }
        }
      }
    }
    container client-fail-infos {
      config false;
      description
        "List of client login failure information.";
      list client-fail-info {
        key "index";
        description
          "Operational state of client login failure information.";
        leaf index {
          type uint32;
          description
            "Index.";
        }
        leaf client-duid {
          type string {
            length "1..256";
          }
          description
            "Client DUID.";
          ext:support-filter "true";
        }
        leaf ia-type {
          type ia-type;
          description
            "Identity association type.";
        }
        leaf iaid {
          type uint32;
          description
            "Identity association identifier.";
        }
        leaf if-name {
          type leafref {
            path "/ifm:ifm/ifm:interfaces/ifm:interface/ifm:name";
          }
          description
            "Interface name.";
          ext:support-filter "true";
        }
        leaf pevlan {
          type uint16 {
            range "0..4094";
          }
          description
            "PE VLAN ID.";
          ext:support-filter "true";
        }
        leaf cevlan {
          type uint16 {
            range "0..4094";
          }
          description
            "CE VLAN ID.";
          ext:support-filter "true";
        }
        leaf vpn-name {
          type leafref {
            path "/ni:network-instance/ni:instances/ni:instance/ni:name";
          }
          description
            "VPN name.";
        }
        leaf client-mac {
          type pub-type:mac-address {
            length "0..255";
          }
          description
            "Client MAC address.";
          ext:support-filter "true";
        }
        container iana-infos {
          description
            "List of identifying association for non-temporary addresses.";
          list iana-info {
            key "ipv6-address";
            description
              "Operational state of identifying association for non-temporary addresses.";
            leaf ipv6-address {
              type inet:ipv6-address-no-zone;
              description
                "IPv6 address.";
            }
            leaf fail-cause {
              type fail-cause;
              description
                "Login failure cause.";
            }
            leaf fail-time {
              type yang:date-and-time;
              description
                "Login failure time.";
            }
          }
        }
        container iapd-infos {
          description
            "List of identifying association for prefix delegation.";
          list iapd-info {
            key "ipv6-address";
            description
              "Operational state of identifying association for prefix delegation.";
            leaf ipv6-address {
              type inet:ipv6-address-no-zone;
              description
                "IPv6 address.";
            }
            leaf prefix {
              type uint32;
              description
                "IPv6 prefix.";
            }
            leaf fail-cause {
              type fail-cause;
              description
                "Login failure cause.";
            }
            leaf fail-time {
              type yang:date-and-time;
              description
                "Login failure time.";
            }
          }
        }
      }
    }
  }
  augment /vlan:vlan/vlan:vlans/vlan:vlan {
    description
      "Extend VLAN attribute.";
    container dhcpv6-relay-vlan {
      description
        "Configure DHCPv6 relay attributes in a VLAN.";
      container option18 {
        description
          "Configure option 18 field in a DHCPv6 message.";
        leaf insert-enable {
          type boolean;
          default "false";
          description
            "Enable/disable the device to insert the Option 18 field to a DHCPv6 message.";
        }
        leaf rebuild-enable {
          type boolean;
          default "false";
          description
            "Enable/disable the device to forcibly insert the Option 18 field to a DHCPv6 message.";
        }
        leaf user-defined {
          type string {
            length "1..251";
          }
          description
            "Indicate the user-defined format of the Option 18 field.";
        }
      }
      container option37 {
        description
          "Configure option 37 field in a DHCPv6 message.";
        leaf insert-enable {
          type boolean;
          default "false";
          description
            "Enable/disable the device to insert the Option 37 field to a DHCPv6 message.";
        }
        leaf rebuild-enable {
          type boolean;
          default "false";
          description
            "Enable/disable the device to forcibly insert the Option 37 field to a DHCPv6 message.";
        }
        leaf user-defined {
          type string {
            length "1..251";
          }
          description
            "Indicate the user-defined format of the Option 37 field.";
        }
      }
    }
  }
}
