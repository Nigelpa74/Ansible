/*
* Copyright (C) 2022-2025 Huawei Technologies Co., Ltd. All rights reserved.
*/
module huawei-wlan-ap-radio {
  yang-version 1;
  namespace "urn:huawei:yang:huawei-wlan-ap-radio";
  prefix hw-ap-radio;
  import huawei-wlan-ap {
    prefix hw-wlan-ap;
  }
  import huawei-pub-type {
    prefix pub-type;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "AP radio service package.";
  revision 2025-08-06 {
    description
      "Modify leaf asfn-roam.";
    reference
      "Huawei private.";
  }
  revision 2025-08-04 {
    description
      "Modify leaf asfn-roam.";
    reference
      "Huawei private.";
  }
  revision 2025-07-21 {
    description
      "Add leaf asfn-roam.";
    reference
      "Huawei private.";
  }
  revision 2025-04-01 {
    description
      "Add leaf radio-run-state.";
    reference
      "Huawei private.";
  }

  revision 2025-03-04 {
    description
      "Add leaf reference-data-analysis.";
    reference
      "Huawei private.";
  }
  revision 2025-02-24 {
    description
      "Extend radio-id.";
    reference
      "Huawei private.";
  }
  revision 2024-12-27 {
    description
      "Add leaf reference-data-analysis.";
    reference
      "Huawei private.";
  }
  revision 2024-09-29 {
    description
      "Fix spelling error.";
    reference
      "Huawei private.";
  }
  revision 2024-08-23 {
    description
      "Modify radio 1 support frequency configuration.";
    reference
      "Huawei private.";
  }
  revision 2024-08-15 {
    description
      "Modify the type of unusd spectrum-analysis-switch.";
    reference
      "Huawei private.";
  }
  revision 2024-07-16 {
    description
      "Add spectrum report configuration.";
    reference
      "Huawei private.";
  }
  revision 2024-07-09 {
    description
      "Add coverage distance configuration.";
    reference
      "Huawei private.";
  }
  revision 2024-06-11 {
    description
      "Modify YANG description.";
    reference
      "Huawei private.";
  }
  revision 2024-05-10 {
    description
      "Modify channel config check.";
    reference
      "Huawei private.";
  }
  revision 2024-03-05 {
    description
      "Modify radio instances as generated-by system.";
    reference
      "Huawei private.";
  }
  revision 2023-11-20 {
    description
      "Fix bandwidth-320mhz case bug.";
    reference
      "Huawei private.";
  }
  revision 2023-08-02 {
    description
      "Add the rpc of rf-ping and get-rf-ping-result.";
    reference
      "Huawei private.";
  }
  revision 2023-02-01 {
    description
      "Add interference-visualization default value.";
    reference
      "Huawei private.";
  }
  revision 2022-12-29 {
    description
      "Add bandwidth-320mhz.";
    reference
      "Huawei private.";
  }

  revision 2022-12-28 {
    description
      "Add interference-visualization enable.";
    reference
      "Huawei private.";
  }
  revision 2022-12-22 {
    description
      "Add spectrum-analysis switch and 3d-data calibrate switch.";
    reference
      "Huawei private.";
  }

  revision 2022-11-19 {
    description
      "Fix bandwidth-40mhz-minus description.";
    reference
      "Huawei private.";
  }
  revision 2022-09-23 {
    description
      "Add work-mode.";
    reference
      "Huawei private.";
  }
  revision 2022-08-19 {
    description
      "Add YANG configuration of V6R22C10.";
    reference
      "Huawei private.";
  }
  revision 2022-07-15 {
    description
      "Add freq when check.";
    reference
      "Huawei private.";
  }
  revision 2022-06-15 {
    description
      "Fix task name.";
    reference
      "Huawei private.";
  }
  revision 2022-04-11 {
    description
      "Initial revision.";
    reference
      "Huawei private.";
  }
  grouping radio-instances {
    description
      "Radio instances.";
    list radio-instance {
      ext:generated-by "system" {
        description
          "The radio instance is generated by system.";
      }
      key "radio-id";
      description
        "Configure radio instance.";
      leaf radio-id {
        type uint8 {
          range "0..4";
        }
        description
          "Radio id.";
      }
      leaf radio-switch {
        type enumeration {
          enum "disable" {
            value 0;
            description
              "Disable.";
          }
          enum "enable" {
            value 1;
            description
              "Enable.";
          }
        }
        description
          "Set radio enable or disable.";
      }
      leaf eirp {
        type uint8 {
          range "1..127 | 255";
        }
        default "255";
        description
          "Eirp configuration.";
      }
      container channel-info {
        presence "Set bandwidth and channel of ap individual configuration if it is none means ap get this config from group.";
        choice bandwidth {
          mandatory true;
          description
            "Bandwidth of each channel.";
          case bandwidth-20mhz {
            leaf bandwidth-20mhz {
              type empty;
              description
                "20mhz.";
            }
            description
              "20mhz.";
          }
          case bandwidth-40mhz-minus {
            leaf bandwidth-40mhz-minus {
              type empty;
              description
                "40mhz-minus.";
            }
            description
              "40mhz-minus.";
          }
          case bandwidth-40mhz-plus {
            leaf bandwidth-40mhz-plus {
              type empty;
              description
                "40mhz-plus.";
            }
            description
              "40mhz-plus.";
          }
          case bandwidth-80mhz {
            when "not (../frequency = '2G')";
            leaf bandwidth-80mhz {
              type empty;
              description
                "80mhz.";
            }
            description
              "80mhz.";
          }
          case bandwidth-80plus80mhz {
            when "not (../frequency = '2G')";
            leaf bandwidth-80plus80mhz {
              type empty;
              description
                "80plus80mhz.";
            }
            description
              "80plus80mhz.";
          }
          case bandwidth-160mhz {
            when "not (../frequency = '2G')";
            leaf bandwidth-160mhz {
              type empty;
              description
                "160mhz.";
            }
            description
              "160mhz.";
          }
          case bandwidth-320mhz {
            when "not (../frequency = '2G')";
            leaf bandwidth-320mhz {
              type empty;
              description
                "320mhz.";
            }
            description
              "320mhz.";
          }
        }
        leaf channel {
          type uint8;
          mandatory true;
          description
            "Channel configuration.";
        }
        description
          "Configure bandwidth and channel of ap individual configuration.";
      }
      leaf auto-channel-select {
        type enumeration {
          enum "enable" {
            value 0;
            description
              "Channel auto select enable.";
          }
          enum "disable" {
            value 1;
            description
              "Channel auto select disable.";
          }
          enum "nocfg" {
            value 2;
            description
              "Auto-channel-select not config.";
          }
        }
        default "nocfg";
        description
          "Channel auto select configuration.";
      }
      leaf auto-txpower-select {
        type enumeration {
          enum "enable" {
            value 0;
            description
              "Txpower auto select enable.";
          }
          enum "disable" {
            value 1;
            description
              "Txpower auto select disable.";
          }
          enum "nocfg" {
            value 2;
            description
              "Auto-txpower-select not config.";
          }
        }
        default "nocfg";
        description
          "Txpower auto select configuration.";
      }
      leaf frequency {
        type enumeration {
          enum "none" {
            value 0;
            description
              "Frequency is not set.";
          }
          enum "2G" {
            value 1;
            description
              "Frequency is 2.4G.";
          }
          enum "5G" {
            value 2;
            description
              "Frequency is 5G.";
          }
          enum "6G" {
            value 3;
            description
              "Frequency is 6G.";
          }
        }
        default "none";
        description
          "Configure frequency.";
      }
      leaf auto-bandwidth-select {
        type enumeration {
          enum "none" {
            value 0;
            description
              "Not set.";
          }
          enum "disable" {
            value 1;
            description
              "Disable.";
          }
          enum "enable" {
            value 2;
            description
              "Enable.";
          }
        }
        default "none";
        description
          "Calibrate auto-bandwidth-select.";
      }
      leaf flexible-radio {
        type enumeration {
          enum "disable" {
            value 0;
            description
              "Disable DFA of specified radios.";
          }
          enum "enable" {
            value 1;
            description
              "Enable DFA of specified radios.";
          }
        }
        description
          "Configure calibrate flexible-radio.";
      }
      leaf channel-monitor {
        type enumeration {
          enum "disable" {
            value 0;
            description
              "Disable the function of monitoring the status of all channels.";
          }
          enum "enable" {
            value 1;
            description
              "Disables the function of monitoring the status of all channels.";
          }
        }
        description
          "Disable or enable the function of monitoring the status of all channels.
           By default, the function of monitoring the status of all channels is following group Configuration.";
      }
      leaf antenna-gain {
        type int32 {
          range "-10..30";
        }
        units "dB";
        description
          "Config antenna-gain.";
      }
      leaf work-mode {
        type enumeration {
          enum "monitor" {
            value 0;
            description
              "Indicates the monitor mode.";
          }
          enum "normal" {
            value 1;
            description
              "Indicates the normal mode.";
          }
        }
        description
          "Configures the working mode for all AP radios in a specified AP radio.";
      }
      leaf spectrum-analysis-switch {
        type enumeration {
          enum "disable" {
            value 0;
            description
              "Disable spectrum-analysis.";
          }
          enum "enable" {
            value 1;
            description
              "Enable spectrum-analysis.";
          }
        }
        description
          "Configure spectrum-analysis-switch.";
      }
      leaf spectrum-report-switch {
        type boolean;
        default "false";
        description
          "Enable/disable the function of spectrum analysis data report.";
      }
      leaf data-3d-calibrate {
        type enumeration {
          enum "disable" {
            value 0;
            description
              "Disable 3d-data-calibrate.";
          }
          enum "enable" {
            value 1;
            description
              "Enable 3d-data-calibrate.";
          }
        }
        description
          "Configure 3d-data-calibrate.";
      }
      leaf interference-visualization-switch {
        type enumeration {
          enum "disable" {
            value 0;
            description
              "Disable interference-visualization.";
          }
          enum "enable" {
            value 1;
            description
              "Enable interference-visualization.";
          }
        }
        default "disable";
        description
          "Configure interference-visualization-switch.";
      }
      container coverage {
        description
          "Configure coverage parameters.";
        leaf distance {
          type uint16 {
            range 1..400;
          }
          units "100 m";
          description
            "Configure coverage distance.";
        }
      }
      leaf reference-data-analysis {
        type enumeration {
          enum "disable" {
            value 0;
            description
              "Disable reference-data-analysis.";
          }
          enum "enable" {
            value 1;
            description
              "Enable reference-data-analysis.";
          }
        }
        description
          "Configure reference-data-analysis.";
      }
      container radio-info {
        config false;
        description
          "Operational state of radio information.";
        leaf channel-utilization-rate {
          type uint8;
          units "%";
          description
            "Channel utilization rate.";
        }
        leaf channel-interference-rate {
          type uint8;
          units "%";
          description
            "Channel-interference-rate.";
        }
        leaf period-retry-frames {
          type uint64;
          description
            "Period-retry-frames.";
        }
        leaf period-drop-frames {
          type uint64;
          description
            "Period-drop-frames.";
        }
        leaf period-send-frames {
          type uint64;
          description
            "Period-send-frames.";
        }
        leaf radio-run-state {
          type enumeration {
            enum "disabled" {
              value 0;
              description
                "radio disabled.";
            }
            enum "enabled" {
              value 1;
              description
                "radio enabled.";
            }
            enum "invalid" {
              value 255;
              description
                "radio invalid.";
            }
          }
          description
            "Radio-run-state.";
        }
        leaf radio-frequency {
          type enumeration {
            enum "2.4G" {
              value 0;
              description
                "2.4G.";
            }
            enum "5G" {
              value 1;
              description
                "5G.";
            }
            enum "6G" {
              value 2;
              description
                "6G.";
            }
          }
          description
            "Frequency.";
        }
      }
      container asfn-roam {
        must "./high-level-margin > ./low-level-margin";
        description
          "Configure asfn roam.";
        leaf high-level-margin {
          type int32 {
            range 5..25;
          }
          units "dB";
          default 10;
          description
            "High level margin value.";
        }
        leaf low-level-margin {
          type int32 {
            range 3..15;
          }
          units "dB";
          default 5;
          description
            "Low level margin value.";
        }
      }
    }
  }

  grouping rfping-input {
    description
      "Rfping input information.";
    leaf station-mac-address {
        type pub-type:mac-address;
        mandatory true;
        description
		  "The wireless station mac-address, the rf-ping's destination.";
    }
    leaf interval {
        type uint32 {
          range "100..10000";
        }
        units "ms";
        default 100;
        description
          "Specifies the interval for sending data packets.";
    }
    leaf packet-count {
        type uint32 {
          range "1..1000";
        }
        default 10;
        description
          "Specifies the number of data packets sent by the AP.";
    }
    leaf priority {
        type enumeration {
          enum "be" {
            value 0;
            description
              "AC_BE.";
          }
          enum "bk" {
            value 1;
            description
              "AC_BK.";
          }
          enum "vi" {
            value 2;
            description
              "AC_VI.";
          }
          enum "vo" {
            value 3;
            description
              "AC_VO.";
          }
        }
        default "be";
        description
          "Specifies the priority of data packets sent by the AP, which can be AC_BE, AC_BK, AC_VI, or AC_VO.";
    }
  }

  grouping rfping-output {
    description
      "Rfping output information.";
    leaf station-mac-address {
      type pub-type:mac-address;
      mandatory true;
      description
		"The wireless station mac-address, the rf-ping's destination.";
    }
    leaf complete {
      type boolean;
      description
        "The rfping test is completed or not.";
    }
    list rfping-output-list {
      key sequence;
      description
        "The rfping replies information.";
      leaf sequence {
        type uint32 {
          range "1..max";
        }
        description
          "The sequence number of the rf-ping replies.";
      }
      leaf result {
        type string{
          length "1..256";
        }
        description
          "The response for each packet.";
      }
    }
  }

  rpc rfping {
    description
      "Run a rfping test.";

    input {
      leaf test-name {
        type string{
          length "1..32";
        }
        mandatory true;
        description
          "The test case name.";
      }
      leaf stop-enable {
        type boolean;
        description
          "It stops the running test case.";
      }
      container rfping {
        description
          "Rf-ping input.";
        uses rfping-input;
      }
    }
  }

  rpc get-rfping-result {
    description
      "Get rf-ping result.";

    input {
      leaf test-name {
        type string{
          length "1..32";
        }
        mandatory true;
        description
          "The test case name.";
      }
    }
    output {
      container rfping-output-lists {
        description
          "Rf-ping output.";
        uses rfping-output;
      }
    }
  }

  augment /hw-wlan-ap:wlan-ap/hw-wlan-ap:ap-instances/hw-wlan-ap:ap-instance {
    description
      "Configure ap instance radio instances.";
    container radio-instances {
      description
        "Configure ap instance radio instances.";
      uses hw-ap-radio:radio-instances;
    }
  }
  ext:task-name "wm";
}
