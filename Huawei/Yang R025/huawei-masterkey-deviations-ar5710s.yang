/*
Copyright (C) 2025 Huawei Technologies Co., Ltd. All rights reserved.
*/
module huawei-masterkey-deviations-ar5710s {
  namespace "urn:huawei:yang:huawei-masterkey-deviations-ar5710s";
  prefix masterkey-devs-ar5710s;

  import huawei-masterkey {
    prefix masterkey;
  }

  organization
    "Huawei Technologies Co., Ltd.";
  contact
    "Huawei Industrial Base
     Bantian, Longgang
     Shenzhen 518129
     People's Republic of China
     Website: http://www.huawei.com
     Email: support@huawei.com";
  description
    "This module defines deviation statements for huawei-masterkey module.";

  revision 2025-02-24 {
    description
      "Initial revision.";
    reference "Huawei private.";
  }

  deviation "/masterkey:masterkey" {
    deviate not-supported;
  }
  deviation "/masterkey:check-masterkey-sync-status" {
    deviate not-supported;
  }
}
