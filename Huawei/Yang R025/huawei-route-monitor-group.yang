/*
Copyright (C) 2019-2025 Huawei Technologies Co., Ltd. All rights reserved.
*/
module huawei-route-monitor-group {
  yang-version 1;
  namespace "urn:huawei:yang:huawei-route-monitor-group";
  prefix rmg;
  import ietf-inet-types {
    prefix inet;
  }
  import huawei-network-instance {
    prefix ni;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "A route monitoring group monitors the status of its member routes, each of which has a down-weight. The down-weight sum of the route monitoring group changes with the number of routes that are Down and indicates the link quality. If a route in the route monitoring group goes Down, its down-weight is added to the down-weight sum of the route monitoring group. If a route in the route monitoring group goes Up again, its down-weight is subtracted from the down-weight sum of the route monitoring group.";
  revision 2025-03-03 {
    description
      "Modify the elements num of monitor-group and monitor-group6.";
    reference
      "Huawei private.";
  }
  revision 2024-07-24 {
    description
      "Revert to old version, add the deprecated leaf nodes operator- and and trigger-down-delay.";
    reference
      "Huawei private.";
  }
  revision 2023-02-23 {
    description
      "Add container monitor-group6s.";
    reference
      "Huawei private.";
  }
  revision 2020-03-03 {
    description
      "Modify the description of the container.";
    reference
      "Huawei private.";
  }
  revision 2020-02-25 {
    description
      "Modify the description of the container.";
    reference
      "Huawei private.";
  }
  revision 2019-11-13 {
    description
      "Modify the max-elements of the container.";
    reference
      "Huawei private.";
  }
  revision 2019-10-22 {
    description
      "Add task name and import module.";
    reference
      "Huawei private.";
  }
  revision 2019-04-27 {
    description
      "Initial revision.";
    reference
      "Huawei private.";
  }
  ext:task-name "route-base";
  container route-monitor-group {
    description
      "A route monitoring group monitors the status of its member routes, each of which has a down-weight. The down-weight sum of the route monitoring group changes with the number of routes that are Down and indicates the link quality. If a route in the route monitoring group goes Down, its down-weight is added to the down-weight sum of the route monitoring group. If a route in the route monitoring group goes Up again, its down-weight is subtracted from the down-weight sum of the route monitoring group.";
    container monitor-groups {
      description
        "List of route monitoring groups.";
      list monitor-group {
        key "group-name";
        max-elements 255;
        description
          "Configure a route monitoring group.";
        leaf group-name {
          type string {
            length "1..31";
          }
          description
            "Name of a route monitoring group.";
        }
        leaf enable-status {
          type boolean;
          default "false";
          description
            "Enable/disable a route monitoring group.";
        }
        leaf operator-and {
          type boolean;
          default "false";
          description
            "Enable/disable the AND relationship for routes in a route monitoring group.";
        }
        leaf trigger-up-delay {
          type uint32 {
            range "0..1000";
          }
          units "s";
          default "5";
          description
            "Restoration delay.";
        }
        leaf trigger-down-delay {
          type uint32 {
            range "0..1000";
          }
          units "s";
          default "0";
          description
            "Notification delay.";
        }
        leaf weight-sum {
          type uint32;
          config false;
          description
            "Down-weight sum of the route monitoring group.";
        }
        leaf down-weight {
          type uint32;
          config false;
          description
            "Down-weight of the routes in the route monitoring group.";
        }
        container track-routes {
          description
            "List of routes added to a route monitoring group.";
          list track-route {
            key "destination-ni-name destination mask-length";
            max-elements 255;
            description
              "Configure routes to be added to a route monitoring group.";
            leaf destination-ni-name {
              type leafref {
                path "/ni:network-instance/ni:instances/ni:instance/ni:name";
              }
              description
                "Name of a VPN instance.";
            }
            leaf destination {
              type inet:ipv4-address-no-zone;
              description
                "Destination IP address.";
            }
            leaf mask-length {
              type uint8 {
                range "0..32";
              }
              description
                "Mask length.";
            }
            leaf down-weight {
              type uint32 {
                range "1..1000";
              }
              default "10";
              description
                "Down-weight of a route in a route monitoring group.";
            }
            leaf route-status {
              type enumeration {
                enum "active" {
                  value 0;
                  description
                    "The route is active.";
                }
                enum "inactive" {
                  value 1;
                  description
                    "The route is inactive.";
                }
                enum "invalid" {
                  value 2;
                  description
                    "The status is invalid.";
                }
              }
              config false;
              description
                "Displays the route status.";
            }
          }
        }
      }
    }
    container monitor-group6s {
      description
        "List of IPv6 route monitoring groups.";
      list monitor-group6 {
        key "group-name";
        max-elements 255;
        description
          "Configure a IPv6 route monitoring group.";
        leaf group-name {
          type string {
            length "1..31";
          }
          description
            "Name of a route monitoring group.";
        }
        leaf enable-status {
          type boolean;
          default "false";
          description
            "Enable/disable a route monitoring group.";
        }
        leaf operator-and {
          type boolean;
          default "false";
          description
            "Enable/disable the AND relationship for routes in a route monitoring group.";
        }
        leaf trigger-up-delay {
          type uint32 {
            range "0..1000";
          }
          units "s";
          default "5";
          description
            "Restoration delay.";
        }
        leaf trigger-down-delay {
          type uint32 {
            range "0..1000";
          }
          units "s";
          default "0";
          description
            "Notification delay.";
        }
        container track-routes {
          description
            "List of routes added to a route monitoring group.";
          list track-route {
            key "destination-ni-name destination mask-length";
            max-elements 255;
            description
              "Configure routes to be added to a route monitoring group.";
            leaf destination-ni-name {
              type leafref {
                path "/ni:network-instance/ni:instances/ni:instance/ni:name";
              }
              description
                "Name of a VPN instance.";
            }
            leaf destination {
              type inet:ipv6-address-no-zone;
              description
                "Destination IPv6 address.";
            }
            leaf mask-length {
              type uint8 {
                range "0..128";
              }
              description
                "Mask length.";
            }
            leaf down-weight {
              type uint32 {
                range "1..1000";
              }
              default "10";
              description
                "Down-weight of a route in a route monitoring group.";
            }
          }
        }
      }
    }
  }
}
