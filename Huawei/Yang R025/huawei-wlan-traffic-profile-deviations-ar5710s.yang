/*
Copyright (C) 2019 Huawei Technologies Co., Ltd. All rights reserved.
*/
module huawei-wlan-traffic-profile-deviations-ar5710s {
  yang-version 1;
  namespace "urn:huawei:yang:huawei-wlan-traffic-profile-deviations-ar5710s";
  prefix wlan-traffic-prof-devs-ar5710s;

  import huawei-wlan-traffic-profile {
    prefix wlan-traffic-prof;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-traffic-profile module.";

  revision 2019-11-06 {
    description
      "Initial revision.";
    reference "Huawei private.";
  }

  deviation "/wlan-traffic-prof:wlan-traffic-profile/wlan-traffic-prof:traffic-profiles/wlan-traffic-prof:traffic-profile/wlan-traffic-prof:traffic-optimize/wlan-traffic-prof:sta-bridge-forward" {
    deviate not-supported;
  }
  deviation "/wlan-traffic-prof:wlan-traffic-profile/wlan-traffic-prof:traffic-profiles/wlan-traffic-prof:traffic-profile/wlan-traffic-prof:traffic-optimize/wlan-traffic-prof:bcmc-unicast-mdns" {
    deviate not-supported;
  }
  deviation "/wlan-traffic-prof:wlan-traffic-profile/wlan-traffic-prof:traffic-profiles/wlan-traffic-prof:traffic-profile/wlan-traffic-prof:traffic-remarks/wlan-traffic-prof:traffic-remark/wlan-traffic-prof:priority" {
    deviate not-supported;
  }
  deviation "/wlan-traffic-prof:wlan-traffic-profile/wlan-traffic-prof:traffic-profiles/wlan-traffic-prof:traffic-profile/wlan-traffic-prof:igmp-mld-snooping/wlan-traffic-prof:mld-snooping" {
    deviate not-supported;
  }
  deviation "/wlan-traffic-prof:wlan-traffic-profile/wlan-traffic-prof:traffic-profiles/wlan-traffic-prof:traffic-profile/wlan-traffic-prof:traffic-filters/wlan-traffic-prof:traffic-filter/wlan-traffic-prof:priority" {
    deviate not-supported;
  }
  deviation "/wlan-traffic-prof:wlan-traffic-profile/wlan-traffic-prof:traffic-profiles/wlan-traffic-prof:traffic-profile/wlan-traffic-prof:traffic-filter-statistics-switch" {
    deviate not-supported;
  }
  deviation "/wlan-traffic-prof:wlan-traffic-profile/wlan-traffic-prof:traffic-profiles/wlan-traffic-prof:traffic-profile/wlan-traffic-prof:user-l2-lan-isolate" {
    deviate not-supported;
  }
  deviation "/wlan-traffic-prof:wlan-traffic-profile/wlan-traffic-prof:traffic-profiles/wlan-traffic-prof:traffic-profile/wlan-traffic-prof:traffic-remarks/wlan-traffic-prof:traffic-remark" {
    deviate delete {
      unique "direction priority";
    }
  }
  deviation "/wlan-traffic-prof:wlan-traffic-profile/wlan-traffic-prof:traffic-profiles/wlan-traffic-prof:traffic-profile/wlan-traffic-prof:traffic-remarks/wlan-traffic-prof:traffic-remark/wlan-traffic-prof:ipv4-acl-number" {
    deviate replace {
      type uint32 {
        range "0|3000..3031";
      }
    }
  }
  deviation "/wlan-traffic-prof:wlan-traffic-profile/wlan-traffic-prof:traffic-profiles/wlan-traffic-prof:traffic-profile/wlan-traffic-prof:traffic-filters/wlan-traffic-prof:traffic-filter" {
    deviate delete {
      unique "direction priority";
    }
  }
  deviation "/wlan-traffic-prof:wlan-traffic-profile/wlan-traffic-prof:traffic-profiles/wlan-traffic-prof:traffic-profile/wlan-traffic-prof:traffic-filters/wlan-traffic-prof:traffic-filter/wlan-traffic-prof:ipv4-acl-number" {
    deviate replace {
      type uint32 {
        range "0|3000..3031";
      }
    }
  }
}
