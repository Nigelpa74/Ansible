/*
Copyright (C) 2025 Huawei Technologies Co., Ltd. All rights reserved.
*/
module huawei-ifm-ip-statistics-deviations-ar5710s {
  yang-version 1;
  namespace "urn:huawei:yang:huawei-ifm-ip-statistics-deviations-ar5710s";
  prefix ifm-ip-statistics-devs-ar5710s;

  import huawei-ifm-ip-statistics {
    prefix ifm-ip-statistics;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-ifm-ip-statistics module.";

  revision 2025-02-24 {
    description
      "Initial revision.";
    reference "Huawei private.";
  }

  deviation "/ifm:ifm/ifm:interfaces/ifm:interface/ifm-ip-statistics:ip-statistics-enable/ifm-ip-statistics:ip-statistics-mode/ifm-ip-statistics:independent-mode" {
    deviate not-supported;
  }
  deviation "/ifm:ifm/ifm:interfaces/ifm:interface/ifm-ip-statistics:ip-statistics-enable/ifm-ip-statistics:ip-statistics-mode" {
    deviate add {
      default "unified-mode";
    }
  }
}
