/*
Copyright (C) 2019 Huawei Technologies Co., Ltd. All rights reserved.
*/
module huawei-xldp-deviations-ar5710s {
  namespace "urn:huawei:yang:huawei-xldp-deviations-ar5710s";
  prefix xldp-devs-ar5710s;

  import huawei-xldp {
    prefix xldp;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-xldp module.";

  revision 2019-11-06 {
    description
      "Initial revision.";
    reference "Huawei private.";
  }

  deviation "/xldp:xldp/xldp:enable" {
    deviate add {
      default "true";
    }
  }
  deviation "/ifm:ifm/ifm:interfaces/ifm:interface/xldp:xldp/xldp:enable" {
    deviate add {
      default "true";
    }
  }
}
