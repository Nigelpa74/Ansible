/*
Copyright (C) 2020-2025 Huawei Technologies Co., Ltd. All rights reserved.
*/
module huawei-driver {
  yang-version 1;
  namespace "urn:huawei:yang:huawei-driver";

  prefix driver;
  import huawei-pub-type {
    prefix pub-type;
  }
  import huawei-extension {
    prefix ext;
  }
  import huawei-devm {
    prefix devm; 
  }
  import huawei-hardware-type {
    prefix hardware-type;
  }
  import huawei-ifm {
    prefix ifm;
  }
  import huawei-license {
    prefix lcs;
  }
  include huawei-driver-type;
  
  organization
    "Huawei Technologies Co., Ltd.";
  contact
    "Huawei Industrial Base
     Bantian, Longgang
     Shenzhen 518129
     People's Republic of China
     Website: http://www.huawei.com
     Email: support@huawei.com";
  description
    "Configuration of the driver file.";
  revision 2025-09-05 {
    description
      "Modify range of system-mac-number.";
    reference
      "Huawei private.";
  }
  revision 2025-05-26 {
    description
      "Add container humiditys.
       Modify range of leaf minor-threshold-percent in container temperature2s.
       Modify range of leaf major-threshold-percent in container temperature2s.
       Modify range of leaf fatal-threshold-percent in container temperature2s.";
    reference
      "Huawei private.";
  }
  revision 2024-11-11 {
    description
      "Modify description of types about system-work-mode-type in huawei-driver-type.";
    reference
      "Huawei private.";
  }
  revision 2024-08-12 {
    description
      "Add leaf pnp-button-switch.
       Deprecated leaf factory-configuration-button-switch.";
    reference
      "Huawei private.";
  }
  revision 2024-07-16 {
    description
      "Add container temperature-attribute.
       Add leaf pm-auto-balance.";
    reference
      "Huawei private.";
  }
  revision 2024-07-08 {
    description
      "Delete leaf saved-power-consumption.";
    reference
      "Huawei private.";
  } 
  revision 2024-06-28 {
    description
      "Add leaf power-reserved.
       Add leaf temp-change-enable.";
    reference
      "Huawei private.";
  } 
  revision 2024-06-26 {
    description
      "Add leaf saved-power-consumption.";
    reference
      "Huawei private.";
  } 
  revision 2024-06-13 {
    description
      "Modify set-boot-password rpc node.";
    reference
      "Huawei private.";
  }
  revision 2024-05-29 {
    description
      "Add leaf energy-saving-fabric-fiber.
       Add types about driver-hightemp-switch-status in huawei-driver-type.
       Modify types about driver-sensor-state and driver-upgrade-mode-type in huawei-driver-type.
       Modify leaf voltage-value and electrical-value description in container power-environments.
       Add leaf alarm-pm-cable.";
    reference
      "Huawei private.";
  }
  revision 2024-04-28 {
    description
      "Add container fabric-fiber-elabels.";
    reference
      "Huawei private.";
  }
  revision 2024-04-20 {
    description
      "Modify types about driver-power-work-mode in huawei-driver-type.";
    reference
      "Huawei private.";
  }
  revision 2024-03-16 {
    description
      "Modify types about power-input-mode-type in huawei-driver-type.";
    reference
      "Huawei private.";
  }
  revision 2024-03-12 {
    description
      "Modify leaf warm-backup-mode.";
    reference
      "Huawei private.";
  }
  revision 2024-03-07 {
    description
      "Add container opt-electronic-labels.";
    reference
      "Huawei private.";
  }
  revision 2024-03-02 {
    description
      "Modify leaf cur-forward-mode.";
    reference
      "Huawei private.";
  }
  revision 2024-02-27 {
    description
      "Add types about set-led in huawei-driver-type.";
    reference
      "Huawei private.";
  }
  revision 2024-01-13 {
    description
      "Add container cpu-isolates.";
    reference
      "Huawei private.";
  }  
  revision 2023-12-12 {
    description
      "Add types about color-series-type in huawei-driver-type and add leaf color-series for leds.";
    reference
      "Huawei private.";
  }
  revision 2023-10-31 {
    description
      "Add types about driver-slot-infos-type in huawei-driver-type.";
    reference
      "Huawei private.";
  }
  revision 2023-09-11 {
    description
      "Add leaf disable-reason.";
    reference
      "Huawei private.";
  }
  revision 2023-06-02 {
    description
      "Modify leaf area-speed.";
    reference
      "Huawei private.";
  }
  revision 2023-05-19 {
    description
      "Modify container pm-input-attribute.";
    reference
      "Huawei private.";
  }
  revision 2023-05-18 {
    description
      "Add fan-status and fan-speeds.";
    reference
      "Huawei private.";
  }
  revision 2023-05-04 {
    description
      "Add container about battery.";
    reference
      "Huawei private.";
  }
  revision 2023-03-09 {
    description
      "Add leaf sfu-mode.";
    reference
      "Huawei private.";
  }
  revision 2023-03-01 {
    description
      "Modify container pm-input-attribute.";
    reference
      "Huawei private.";
  }
  revision 2023-02-21 {
    description
      "Modify leaf deep-sub-mode, energy-mode.";
    reference
      "Huawei private.";
  }
  revision 2022-12-28 {
    description
      "Modify container lcs-boards, list lcs-board, leaf position, capacity.";
    reference
      "Huawei private.";
  }
  revision 2022-12-07 {
    description
      "Modify the order of node pcb-name.";
    reference
      "Huawei private.";
  }
  revision 2022-12-06 {
    description
      "Add leaf support-mode-list, deep-sub-mode, type, expected-saved-power and container energy-saving-mode-states.";
    reference
      "Huawei private.";
  }
  revision 2022-12-05 {
    description
      "Modify leaf area-speed.";
    reference
      "Huawei private.";
  }
  revision 2022-11-21 {
    description
      "Add leaf power-input-mode.";
    reference
      "Huawei private.";
  }
  revision 2022-11-11 {
    description
      "Add leaf energy-saving-mode-status.";
    reference
      "Huawei private.";
  }
  revision 2022-10-09 {
    description
      "Add leaf power-supply-average and power-supply-others.";
    reference
      "Huawei private.";
  }
  revision 2022-08-09 {
    description
      "Add container boot-password and leaf boot-password.";
    reference
      "Huawei private.";
  }
  revision 2022-08-05 {
    description
      "Add leaf area-average-power, others-power, average-power and saved-power.";
    reference
      "Huawei private.";
  }
  revision 2022-07-22 {
    description
      "Add set-next-system-work-mode rpc node and change next-system-work-mode leaf.";
    reference
      "Huawei private.";
  }
  revision 2022-07-20 {
    description
      "Rollback area-speed range.";
    reference
      "Huawei private.";
  }
  revision 2022-07-18 {
    description
      "Modify old-password.";
    reference
      "Huawei private.";
  }
  revision 2022-07-13 {
    description
      "Modify area-fan-attribute.";
    reference
      "Huawei private.";
  }
  revision 2022-07-06 {
    description
      "Add low-threshold leaf for temperature2s and factory-configuration-button-switch leaf.";
    reference
      "Huawei private.";
  }
  revision 2022-07-04 {
    description
      "Modify range of system-mac-number.";
    reference
      "Huawei private.";
  }
  revision 2022-06-17 {
    description
      "Modify fan-attribute description.";
    reference
      "Huawei private.";
  }
  revision 2022-06-14 {
    description
      "Add choice sysmac-switch-time.";
    reference
      "Huawei private.";
  }
  revision 2022-06-01 {
    description
      "Add container fan-attributes.";
    reference
      "Huawei private.";
  }
  revision 2022-05-27 {
    description
      "Modify area-speed range.";
    reference
      "Huawei private.";
  }
  revision 2022-03-31 {
    description
      "Add container area-fan-attributes and add leaf area-id for fans.";
    reference
      "Huawei private.";
  }
  revision 2022-03-17 {
    description
      "Add must condition for system-mac-address and system-mac-number.";
    reference
      "Huawei private.";
  }
  revision 2022-02-28 {
    description
      "Add leaf area-real-power and area-power-mode.";
    reference
      "Huawei private.";
  }
  revision 2021-12-30 {
    description
      "Update huawei-driver file.";
    reference
      "Huawei private.";
  }
  revision 2021-12-10 {
    description
      "Update huawei-driver-type file.";
    reference
      "Huawei private.";
  }
  revision 2021-12-01 {
    description
      "Update huawei-driver-type file.";
    reference
      "Huawei private.";
  } 
  revision 2021-11-18 {
    description
      "Delete leaf default.";
    reference
      "Huawei private.";
  }
  revision 2021-11-08 {
    description
      "Add leaf power-redundant-mode.";
    reference
      "Huawei private.";
  }
  revision 2021-10-14 {
    description
      "Add container power-global-attribute.";
    reference
      "Huawei private.";
  }
  revision 2021-05-06 {
    description
      "Add rollback-feature-pkg-file.";
    reference
      "Huawei private.";
  }
  revision 2021-04-09 {
    description
      "Add cmu change.";
    reference
      "Huawei private.";
  }
  revision 2021-03-02 {
    description
      "Add container about LED indicators.";
    reference
      "Huawei private.";
  }
  revision 2020-09-07 {
    description
      "Add power consumption.";
    reference
      "Huawei private.";
  }
  revision 2020-08-04 {
    description
      "Add new attribute and change.";
    reference
      "Huawei private.";
  }
  revision 2020-07-13 {
    description
      "Add new attribute and change.";
    reference
      "Huawei private.";
  }
  revision 2020-04-02 {
    description
      "Init revision.";
    reference
      "Huawei private.";
  }
  ext:task-name "device-mgr";
  grouping led-flash-time {
    description
      "Indicator blinking periods.";
    leaf flash-time {
      type uint32 {
        range "1..5";
      }
      units "s";
      default "3";
      description
        "Set the duration in which an indicator blinks.";
    }
    leaf alarm-status-time {
      type uint32 {
        range "1..5";
      }
      units "s";
      default "3";
      description
        "Set the duration in which an indicator does not blink temporarily.";
    }
    leaf cancel-time {
      type uint32 {
        range "5..60";
      }
      units "min";
      default "10";
      description
        "Set the total duration after which an indicator stops blinking.";
    }
  }
  container driver {
    description
      "Configuration of the driver.";
    container global-attribute {
      description
        "Configure global attribute.";
      leaf board-power-on-delay {
        type uint32 {
          range "0..65535";
        }
        units "min";
        default "0";
        description
          "Board Power-on-delay (0 stands for cancel operation).";
      }
      leaf card-power-on-delay {
        type uint32 {
          range "0..65535";
        }
        units "min";
        default "0";
        description
          "Pic Power-on-delay (0 stands for cancel operation).";
      } 
      leaf dustproof-check {
        type driver-bool;
        default "yes";
        status deprecated;
        description
          "Dustproof Gate Check. New replacement node:/devm:devm/devm:chassiss/devm:chassis/driver:dustproof-attribute/driver:dustproofcheck.";
      }
      leaf support-mode-list {
        type string{
          length "1..255";
        }
        config false;
        description
          "Character string that describes the combinations of energy-saving modes supported by the device. Different combinations are separated by commas (,). modes and sub-modes are separated by double pound marks (#) in the same combination.";
      }
      leaf energy-mode {
        type energy-mode-type;
        default "basic";
        description
          "Energy saving mode.";
      }
      leaf deep-sub-mode {
        when "../energy-mode='deep'";
        type deep-sub-mode-type;
        description
          "Deep energy-saving sub-mode.";
      }
      leaf energy-saving-pm {
        ext:dynamic-default;
        type energy-saving-pm-type;
        must "not(../energy-mode='standard' and ../energy-saving-pm='enable')";
        description
          "PM Energy-saving Mode (which includes disable, enable. The default value is disable).";
      }        
      leaf energy-saving-fabric-fiber {
        ext:dynamic-default;
        type driver-entity-bool;
        description
          "Fabric Fiber Energy-saving Mode (which includes disable, enable).";
      }
      leaf entity-fault-board-isolate {
        type driver-entity-bool;
        default "enable";
        description
          "Enable Board Abnormal Reset Detection.";
      }
      leaf entity-fault-card-isolate {
        type driver-entity-bool;
        default "enable";
        description
          "Enable Card Abnormal Reset Detection.";
      }
      leaf fault-strategy {
        type global-card-fault-process-mode;
        default "reset";
        description
          "Global Card-Fault Process-Mode.";
      }
      leaf high-temp-switch {
        type driver-bool;
        default "yes";
        description
          "High Temperature Switch.";
      }
      leaf interface-match-check {
        type driver-interface-match-check-flag;
        default "disable";
        description
          "Used to configure interface matching check functionality.";
      }
      leaf least-sfu-number {
        type uint32 {
          range "1..8";
        }
        default "3";
        description
          "Least number of sfu (Dynamic parameter range, which may be smaller).";
      }
      leaf offline-function {
        type offline-function-type;
        default "enable";
        description
          "Offline function mask (which includes disable, enable. The default value is enable).";
      } 
      leaf optional-entity-fault-isolate {
        type entity-fault-isolate-type;
        default "enable";
        description
          "EntFaultIso mode.";
      } 
      leaf pic-reload-cycle {
        type reload-time;
        default "60min";
        description
          "Set the pic reload cycle after the pic failed to register 10 times.";
      }
      leaf sampling-period {
        type sampling-period-type;
        default "one-hour";
        description
          "Power sampling period.";
      }
      leaf sfu-switch-mode {
        type sfu-switch-mode-type;
        default "disable";
        description
          "SfuSwitchMode.";
      }
      leaf system-mac-address {
        type pub-type:mac-address{
          pattern '[0-9a-f][02468ace][0-9a-f]{2}(-[0-9a-f]{4}){2}';
        }
        must "../system-mac-number";
        description
          "The system MAC address, with the value being a unicast MAC address that is not composed of all 0s. It will take effect only after the system is rebooted.";
      }
      leaf system-mac-number {
        type uint32 {
           range "1..2048";
        }
        must "../system-mac-address";
        description
          "The number of system MAC address.";
      }
      leaf system-trap {
        type trap-type;
        default "base-trap";
        description
          "Switch trap type.";
      }
      leaf temp-query-mode {
        type mib-query-mode-type;
        default "default";
        description
          "MIB Temperatue Brief Query Mode.";
      }
      leaf vlt-query-mode {
        type mib-query-mode-type;
        default "default";
        description
          "MIB Voltage Brief Query Mode.";
      }
      leaf sfu-mode {
        type sfu-mode-type;
        description
          "Sfu Work Mode.";
      }
      leaf cur-forward-mode {
        type forwarding-mode;
        config false;
        description
          "Current forward mode, compatible or enhance.";
      }
      leaf next-forward-mode {
        type forwarding-mode;
        ext:dynamic-default;
        description
          "Next forward mode, compatible or enhance, which some boards can not support. The default value varies with the forward mode of a device. Generally, the default value is compatible. However, it changes to enhance if the device supports only enhance (warning:system will restart after success, and then take effect).";
      }
      leaf cur-work-mode {
        type driver-system-mode;
        config false;
        description
          "Cur work mode, 1+1 or 1:1.";
      }
      leaf next-work-mode {
        type driver-system-mode;
        config false;
        description
          "Next work mode,1+1 or 1:1. The work mode cannot be switched on specific device models or in specific scenarios (warning:system will restart after success, and then take effect).";
      }
      leaf warm-backup-states {
        type warm-backup-status;
        default "off";
        config false;
        description
          "Cur warm-backup status.";
      }
      leaf warm-backup-mode {
        type warm-backup-mode;
        default "disable";
        description
          "Cur warm-backup mode.";
      }
      leaf cur-device-work-mode {
        type driver-work-mode;
        config false;
        description
          "Cur device work mode, base or ptn-iot.";
      }
      leaf next-device-work-mode {
        type driver-work-mode;
        config false;
        description
          "Next device work mode, base or ptn-iot.";
      }
      leaf dcn-management-plane-lock-status {
        type driver-lock-state-type;
        config false;
        description
          "Dcn-management-plane locked status.";
      }
      leaf cur-dcn-plane-mode{
        type driver-dcn-plane-mode-type;
        config false;
        description
          "Current DCN plane mode.";
      }
      leaf next-dcn-plane-mode{
        type driver-dcn-plane-mode-type;
        config false;
        description
          "Next DCN plane mode.";
      }
      leaf cur-system-mode {
        type driver-system-mode-type;
        default "classic";
        config false;
        description
          "Cur System mode, classic or ls.";
      }
      leaf next-system-mode {
        type driver-system-mode-type;
        default "classic";
        config false;
        description
          "Next System mode, classic or ls (warning:system will restart after success, and then take effect).";
      }
      leaf auto-upgrade-model {
        type driver-upgrade-mode-type;
        default "open";
        config false;
        description
          "Auto Upgrade Model.";
      }
      leaf chassis-last-change-time {
        type pub-type:time-tick;
        config false;
        description
          "Time when a chassis or an entity is last added or removed, or time when chassis status (administration status, running status, or active/standby status) is last changed. The time is in UTC time.";
      }
      leaf cur-chassis-number {
        type uint32;
        config false;
        description
          "Current number of chassis.";
      }
      leaf max-chassis-number {
        type uint32 {
          range "1..255";
        }
        config false;
        description
          "Maximum number of chassis.";
      }
      leaf power-consumption {
        type string {
          length "1..255";
        }
        units "J";
        config false;
        description
            "Power Consumption.";
      }
      leaf split-resume {
        type driver-split-resume-mode-type;
        config false;
        description
          "Slave chassis reset mode.";
      }
      leaf switch-port-mode {
        type string {
          length "1..128";
        }
        config false;
        description
          "Switch-port Work-mode.";
      }
      leaf system-service-type {
        type string {
          length "1..128";
        }
        config false;
        description
          "System Service Type.";
      }
      leaf usb-uart-status {
        type usb-uart-status;
        config false;
        description
          "Usb uart status, open or closed.";
      }
      leaf cur-system-mac-address {
        type pub-type:mac-address;
        config false;
        description
          "Current system MAC address.";
      }
      leaf board-channel-check-status {
        type board-channel-check-type;
        config false;
        description
          "The board-channel-check status.";
      }
      leaf energy-saving-pm-status {
        type energy-saving-pm-type;
        config false;
        description
          "PM energy-saving mode status.";
      }
      leaf service-forward-ability {
        type service-forward-ability-type;
        config false;
        description
          "Current service-forward ability.";
      }
      leaf power-input-mode {
        type power-input-mode-type;
        default "single-mode";
        description
          "Device power input mode.";
      }
      leaf cur-system-work-mode {
        type system-work-mode-type;
        default "p-series";
        config false;
        description
          "This time the system starts working mode.";
      }
      leaf next-system-work-mode {
        type system-work-mode-type;
        default "p-series";
        config false;
        description
          "Next time the system starts working mode.";
      }
      leaf factory-configuration-button-switch {
        type driver-entity-bool;
        default "enable";
        status deprecated;
        description
          "Enable/disable the button for restoring factory settings. New replacement node:/driver:driver/driver:global-attribute/driver:pnp-button-switch leaf.";
      }
      leaf pnp-button-switch {
        type driver-entity-bool;
        default "enable";
        description
          "Enable/disable the pnp-button.";
      }
      choice sysmac-switch-time {
        default "switch-delay-time";
        description
          "Specify the delay in switching system-mac.";
        case switch-delay-time {
          description
            "Set the delay for switching system-mac.";
          leaf switch-delay-time {
            type uint32 {
              range "0..60";
            }
            units min;
            default "10";
            description
              "Set the delay for switching system-mac, 0 means to disable this function.";
          }
        }
        case switch-immediately {
          description
            "Set system-mac to be switched immediately.";
          leaf switch-immediately {
            type empty;
            description
              "Set system-mac to be switched immediately.";
          }
        }
      }
      leaf pm-auto-balance {
        type driver-entity-bool;
        default "disable";
        description
          "Pm auto balance.";
      }
      leaf temp-change-enable {
        type driver-bool;
        default "no";
        description
          "Temperature change monitoring enable.";
      }
    }

    container opt-electronic-labels {
        config false;
        description
        "List of optical module electronic labels.";
      list opt-electronic-label {
        key "entity-class position entity-serial-number";
        description
          "Statistics of electronic label.";
        leaf entity-class {
          type hardware-type:hardware-entityclass-type;
          description
            "Entity Class.";
        }
        leaf position {
          type string {
            length "1..32";
          }
          description
            "Position. The position is expressed in the format of slotID. For example, 1. Here 1 is an example. The value may vary with devices.";
        }
        leaf entity-serial-number {
          type uint32;
          description
            "Physical Number.";
        }
        leaf item {
          type string {
            length "1..128";
          }
          description
            "Optical module items.";
        }
        leaf vendor-sn {
          type string {
            length "1..128";
          }
          description
            "Vendor SN.";
        }
        leaf vendor-pn {
          type string {
            length "1..128";
          }
          description
            "Vendor PN.";
        }
        leaf opt-description {
          type string {
            length "1..256";
          }
          description
            "The description of optical module.";
        }
        leaf vendor-name {
          type string {
            length "1..128";
          }
          description
            "Vendor name.";
        }
        leaf manufacture-date {
          type string {
            length "1..128";
          }
          description
            "Manufacture date.";
        }
      }
    }

    container power-global-attribute {
      description
        "Configure power global attribute.";
      leaf full-supply-enable {
        type driver-entity-bool;
        default "disable";
        description
          "Power full supply.";
      }
      leaf alarm-pm-cable {
        type driver-entity-bool;
        default "enable";
        description
          "Power cable alarm detection.";
      }
      leaf power-reserved {
        type driver-entity-bool;
        default "enable";
        description
          "Enable power reserved.";
      }
    }

    container io-inspect-states {
      config false;
      description
        "List of IO inspect state.";
      list io-inspect-state {
        key "position index";
        description
          "IO inspect state.";
        leaf position {
          type string {
            length "1..32";
          }
          description
            "Position. The position is expressed in the format of slotID. For example, 1. Here 1 is an example. The value may vary with devices.";  
        }
        leaf index {
          type uint32;
          description
            "Index.";
        }
        leaf states {
          type driver-inspect-state;
          description
            "Input status.";
        }
        leaf default-states {
          type driver-inspect-state;
          description
            "Default status.";
        }
        leaf alarm-name {
          type string {
            length "1..16";
          }
          description
            "Alarm name.";
        }
        leaf alarm-status {
          type driver-inspect-alarm-state;
          description
            "Alarm status.";
        }
      }
    }

    container io-inspect-attributes {
      description
        "List of IO inspect attributes.";
      list io-inspect-attribute {
        key "position index";
        description
          "Configure IO inspect attribute.";
        leaf position {
          type string {
            length "1..32";
          }
          description
            "Position. The position is expressed in the format of slotID. For example, 1. Here 1 is an example. The value may vary with devices.";  
        }
        leaf index {
          type uint32;
          description
            "Index.";
        }
        leaf default-states {
          type driver-default-states;
          mandatory true;
          description
            "Default status.";
        }
        leaf alarm-name {
          ext:operation-exclude update|delete; 
          type string {
            length "1..16";
          }
          description
            "Alarm name.";
        }
      }
    }
    
    container temperatures {
      ext:operation-exclude create;
      description
        "List of temperature information about a board.";
      list temperature {
        ext:generated-by system;
        ext:operation-exclude create;
        key "position i2c address channel";
        description
          "Configure temperature information about a board.";
        leaf position {
          type string {
            length "1..50";
          }
          description
            "Location of a board. The position is expressed in the format of slotID. For example, 1. Here 1 is an example. The value may vary with devices.";
        }
        leaf i2c {
          type uint32;
          description
            "I2C bus number of a board.";
        }
        leaf address {
          type string {
            length "1..50";
          }
          description
            "Sensor address of a board. The address is expressed in the format of a number. For example, 0. Here 0 is an example. The value may vary with devices.";
        }
        leaf channel {
          type uint32;
          description
            "ID of the sensor channel of a board.";
        }
        leaf minor {
          type uint32 {
            range "80..120";
          }
          units "%";
          description
            "Minor high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
        }
        leaf major {
          type uint32 {
            range "80..120";
          }
          units "%";
          description
            "Major high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
        }
        leaf fatal {
          type uint32 {
            range "80..120";
          }
          units "%";
          description
            "Fatal high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
        }
        leaf fan-tmax {
          ext:dynamic-default;
          when "../minor and ../major and ../fatal";
          type int32 {
            range "-50..127";
          }
          units "°C";
          must "(../fan-tmax>=../fan-tmin)";
          description
            "Fan Speed Adjust High Threshold.[-50,127]for get operation,[-50,127]for edit operation. Each board has a different default fan-tmax value.";
        }
        leaf fan-tmin {
          ext:dynamic-default;
          when "../minor and ../major and ../fatal";
          type int32 {
            range "-50..127";
          }
          units "°C";
          must "(../fan-tmin<=../fan-tmax)";
          description
            "Fan Speed Adjust Low Threshold.[-50,127]for get operation,[-50,127]for edit operation. Each board has a different default fan-tmin value.";
        }
        leaf pcb-name {
          type string {
            length "1..50";
          }
          config false;
          description
            "Type of a board.";
        }
        leaf entity-index {
          type uint32;
          config false;
          description
            "Index of a board.";
        }
        leaf state {
          type driver-sensor-state;
          config false;
          description
            "Sensor status of a board.";
        }
        leaf current-temperature {
          type int32;
          units "°C";
          config false;
          description
            "Current temperature of a board.";
        }
        leaf minor-alarm-threshold {
          type int32;
          units "°C";
          config false;
          description
            "Lower temperature threshold of a board.";
        }
        leaf major-alarm-threshold {
          type int32;
          units "°C";
          config false;
          description
            "Upper temperature threshold of a board.";
        }
        leaf fatal-alarm-threshold {
          type int32;
          units "°C";
          config false;
          description
            "Upper limit of the temperature of a board.";
        }
        leaf fan-tmax-states {
          type int32 {
            range "-50..127";
          }
          units "°C";
          config false;
          description
            "Fan Speed Adjust High Threshold.";
        }
        leaf fan-tmin-states {
          type int32 {
            range "-50..127";
          }
          units "°C";
          config false;
          description
            "Fan Speed Adjust Low Threshold.";
        }
      }
    }
    
    container voltageinfos {
      ext:operation-exclude create;
      description
        "List of voltage information about a board.";
      list voltageinfo {
        ext:generated-by system;
        ext:operation-exclude create;
        key "position i2c address channel";
        description
          "Configure voltage information about a board.";
        leaf position {
          type string {
            length "1..50";
          }
          description
            "Location of a board. The position is expressed in the format of slotID. For example, 1. Here 1 is an example. The value may vary with devices.";
        }
        leaf i2c {
          type uint32;
          description
            "I2C bus number of a board.";
        }
        leaf address {
          type string {
            length "1..50";
          }
          description
            "Sensor address of a board. The address is expressed in the format of a number. For example, 0. Here 0 is an example. The value may vary with devices.";
        }
        leaf channel {
          type uint32;
          description
            "ID of the sensor channel of a board.";
        }
        leaf major-voltage-threshold-low {
          type uint32 {
            range "80..120";
          }
          units "%";
          description
            "The percentage of the major voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
        }
        leaf major-voltage-threshold-high {
          type uint32 {
            range "80..120";
          }
          units "%";
          description
            "The percentage of the major voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
        }
        leaf fatal-voltage-threshold-low {
          type uint32 {
            range "80..120";
          }
          units "%";
          description
            "The percentage of the fatal voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
        }
        leaf fatal-voltage-threshold-high {
          type uint32 {
            range "80..120";
          }
          units "%";
          description
            "The percentage of the fatal voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
        }
        leaf pcb-name {
          type string {
            length "1..50";
          }
          config false;
          description
            "Type of a board.";
        }
        leaf entity-index {
          type uint32;
          config false;
          description
            "Index of a board.";
        }
        leaf state {
          type driver-sensor-state;
          config false;
          description
            "Voltage sensor status of a board.";
        }
        leaf current-voltage {
          type string {
            length "1..50";
          }
          units "V";
          config false;
          description
            "Current voltage of a board.";
        }
        leaf required-voltage {
          type string {
            length "1..50";
          }
          units "V";
          config false;
          description
            "Basic voltage required by the board.";
        }
        leaf major-low-threshold {
          type string {
            length "1..50";
          }
          units "V";
          config false;
          description
            "Lower or lower threshold of the voltage of a board.";
        }
        leaf low-threshold {
          type string {
            length "1..50";
          }
          units "V";
          config false;
          description
            "Lower threshold of the board voltage.";
        }
        leaf major-high-threshold {
          type string {
            length "1..50";
          }
          units "V";
          config false;
          description
            "High upper threshold of the voltage of a board.";
        }
        leaf high-threshold {
          type string {
            length "1..50";
          }
          units "V";
          config false;
          description
            "Fatal upper threshold of the board voltage.";
        }
        leaf voltage-ratio {
          type string {
            length "1..50";
          }
          config false;
          description
            "Voltage division ratio of a board.";
        }
      }
    }

    container cpu-isolates {
      description
        "List of CPU isolates.";
      list cpu-isolate {
        key "slot-id cpu-id";
        description
            "Configure CPU isolate.";
        leaf slot-id {
          type string {
            length "1..32";
          }
          description
            "Board position.";
        }
        leaf cpu-id {
          type string {
            length "1..32";
          }
          description
            "CPU position.";
        }
      }
    }

    container electric-current-infos {
      config false;
      description
        "List of current information about a board.";
      list electric-current-info {
        key "position i2c address channel";
        description
          "Statistics of current information about a board.";
        leaf position {
          type string {
            length "1..32";
          }
          description
            "Board position. The position is expressed in the format of slot ID. For example, 1. Here 1 is an example. The value may vary with devices.";
        }        
        leaf i2c {
          type uint32;
          description
            "I2C bus number of a board.";
        }
        leaf address {
          type string {
            length "1..50";
          }
          description
            "Sensor address of a board. The address is expressed in the format of a number. For example, 0. Here 0 is an example. The value may vary with devices.";
        }
        leaf channel {
          type uint32;
          description
            "ID of the sensor channel of a board.";
        }
        leaf pcb-name {
          type string {
            length "1..50";
          }
          description
            "Type of a board.";
        }
        leaf state {
          type driver-sensor-state;
          description
            "Sensor status of a board.";
        }
        leaf current {
          type string {
            length "1..50";
          }
          units "A";
          description
            "Current value of the sensor.";
        }
        leaf required-current {
          type string {
            length "1..50";
          }
          units "A";
          description
            "Basic current required for the sensor.";
        }
        leaf fatal-low-threshold {
          type string {
            length "1..50";
          }
          units "A";
          description
            "Lower threshold of a critical current alarm.";
        }
        leaf fatal-high-threshold {
          type string {
            length "1..50";
          }
          units "A";
          description
            "Upper threshold of a critical current alarm.";
        }
        leaf major-low-threshold {
          type string {
            length "1..50";
          }
          units "A";
          description
            "Lower threshold of a major current alarm.";
        }
        leaf major-high-threshold {
          type string {
            length "1..50";
          }
          units "A";
          description
            "Upper threshold of a major current alarm.";
        }
      }
    }
    container temperature2s {
      description
        "List of temperature information about a sensor.";
      list temperature2 {
        key "position sensor-id";
        description
          "Configure temperature information about a sensor.";
        leaf position {
          type string {
            length "1..50";
          }
          description
            "Location of a board. The position is expressed in the format of slotID. For example, 1. Here 1 is an example. The value may vary with devices.";
        }
        leaf sensor-id {
          type uint32 {
            range "1..255";
          }
          description
            "Sensor ID of a sensor.";
        }
        leaf minor-threshold-percent {
          type uint32 {
            range "65..120";
          }
          units "%";
          mandatory true;
          description
            "Minor high temperature alarm threshold of a sensor.";
        }
        leaf major-threshold-percent {
          type uint32 {
            range "65..120";
          }
          units "%";
          mandatory true;
          description
            "Major high temperature alarm threshold of a sensor.";
        }
        leaf fatal-threshold-percent {
          type uint32 {
            range "65..120";
          }
          units "%";
          mandatory true;
          description
            "Fatal high temperature alarm threshold of a sensor.";
        }
        leaf fan-adjust-high-temperature {
           type int32 {
            range "-50..127";
          }
          units "°C";
          must "(../fan-adjust-high-temperature>../fan-adjust-low-temperature)";
          mandatory true;
          description
            "Upper threshold for fan speed adjustment.";
        }
        leaf fan-adjust-low-temperature {
          type int32 {
            range "-50..127";
          }
          units °C;
          must "(../fan-adjust-low-temperature<../fan-adjust-high-temperature)";
          mandatory true;
          description
            "Lower threshold for fan speed adjustment.";
        }
        leaf pcb-name {
          type string {
            length "1..50";
          }
          config false;
          description
            "Component name.";
        }
        leaf sensor-name {
          type string {
            length "1..50";
          }
          config false;
          ext:support-filter true;
          description
            "Name of a sensor.";
        }
        leaf state {
          type driver-sensor-state;
          config false;
          description
            "Status of a sensor.";
        }
        leaf current-temperature {
          type int32;
          units "°C";
          config false;
          description
            "Current temperature of a sensor.";
        }
        leaf minor-threshold {
          type int32;
          units "°C";
          config false;
          description
            "Upper minor temperature threshold of a sensor.";
        }
        leaf major-threshold {
          type int32;
          units "°C";
          config false;
          description
            "Upper major temperature threshold of a sensor.";
        }
        leaf fatal-threshold {
          type int32;
          units "°C";
          config false;
          description
            "Upper fatal temperature threshold of a sensor.";
        }
        leaf low-threshold {
          type int32;
          units "°C";
          config false;
          description
            "Lower temperature threshold of a sensor.";
        }
      }
    }
        
    container voltages {
      description
        "List of voltage information about a sensor.";
      list voltage {
        key "position sensor-id";
        description
          "Configure voltage information about a sensor.";
        leaf position {
          type string {
            length "1..50";
          }
          description
            "Location of a board. The position is expressed in the format of slotID. For example, 1. Here 1 is an example. The value may vary with devices.";
        }
        leaf sensor-id {
          type uint32 {
            range "1..255";
          }
          description
            "ID of a sensor.";
        }
        leaf major-low-threshold-percent {
          type uint32 {
            range "80..120";
          }
          units "%";
          mandatory true;
          description
            "Percentage of the major undervoltage threshold over the default undervoltage.";
        }
        leaf fatal-low-threshold-percent {
          type uint32 {
            range "80..120";
          }
          units "%";
          mandatory true;
          description
            "Percentage of the fatal undervoltage threshold over the default undervoltage.";
        }        
        leaf major-high-threshold-percent {
          type uint32 {
            range "80..120";
          }
          units "%";
          mandatory true;
          description
            "Percentage of the major overvoltage threshold over the default overvoltage.";
        }
        leaf fatal-high-threshold-percent {
          type uint32 {
            range "80..120";
          }
          units "%";
          mandatory true;
          description
            "Percentage of the fatal overvoltage threshold over the default overvoltage.";
        }
        leaf pcb-name {
          type string {
            length "1..50";
          }
          config false;
          description
            "Component name.";
        }
        leaf sensor-name {
          type string {
            length "1..50";
          }
          config false;
          ext:support-filter true;
          description
            "Name of a sensor.";
        }
        leaf state {
          type driver-sensor-state;
          config false;
          description
            "Status of a sensor.";
        }
        leaf current-voltage {
          type string {
            length "1..50";
          }
          units "V";
          config false;
          description
            "Current voltage of a sensor.";
        }
        leaf required-voltage {
          type string {
            length "1..50";
          }
          units "V";
          config false;
          description
            "Basic voltage required by the sensor.";
        }
        leaf major-low-threshold {
          type string {
            length "1..50";
          }
          units "V";
          config false;
          description
            "Major lower threshold of the voltage of a sensor.";
        }
        leaf fatal-low-threshold {
          type string {
            length "1..50";
          }
          units "V";
          config false;
          description
            "Fatal lower threshold of the voltage of a sensor.";
        }
        leaf major-high-threshold {
          type string {
            length "1..50";
          }
          units "V";
          config false;
          description
            "High upper threshold of the voltage of a sensor.";
        }
        leaf fatal-high-threshold {
          type string {
            length "1..50";
          }
          units "V";
          config false;
          description
            "Fatal upper threshold of the voltage of a sensor.";
        }
        leaf ratio {
          type string {
            length "1..50";
          }
          config false;
          description
            "Voltage division ratio of a sensor.";
        }
      }
    }
    container humiditys {
      config false;
      description
        "List of humidity information about a sensor.";
      list humidity {
        key "position sensor-id";
        config false;
        description
          "Statistics of humidity information about a sensor.";
        leaf position {
          type string {
            length "1..50";
          }
          config false;
          description
            "Location of a board. The position is expressed in the format of slotID. For example, 1. Here 1 is an example. The value may vary with devices.";
        }
        leaf sensor-id {
          type uint32 {
            range "1..255";
          }
          config false;
          description
            "Sensor ID of a sensor.";
        }
        leaf pcb-name {
          type string {
            length "1..50";
          }
          config false;
          description
            "Component name.";
        }
        leaf sensor-name {
          type string {
            length "1..50";
          }
          config false;
          description
            "Name of a sensor.";
        }
        leaf state {
          type driver-sensor-state;
          config false;
          description
            "Status of a sensor.";
        }
        leaf current-humidity {
          type string {
            length "1..50";
          }
          units "%";
          config false;
          description
            "Current humidity of a sensor.";
        }
      }
    }
    container interface-match-check-states {
      config false;
      description
        "List of matching detection information about interfaces.";
      list interface-match-check-state {
        key "position";
        description
          "Statistics of matching detection information about an interface.";
        leaf position {
          type string {
            length "1..30";
          }
          description
            "Enabling position of interface match detection. The position is expressed in the format of slotID. For example, 1. Here 1 is an example. The value may vary with devices.";
        }
        leaf object {
          type driver-interface-match-check-object;
          description
            "Enabling object of interface match detection.";
        }
      }
    }

    container fan-attributes {
      description
        "List of configurations of the working mode and speed of the fan.";
      list fan-attribute {
        key "position";
        description
          "Configure the working mode and speed of the fan of the specific device.";
        leaf position {
          type string {
            length "1..32";
          }
          description
            "Board position. The position is expressed in the format of slotID. For example, 1. Here 1 is an example. The value may vary with devices.";
        }
        leaf workmode {
          type fan-workmode;
          default "auto";
          description
              "Fan working mode.";
        }
        leaf speed {
          ext:dynamic-default;
          when "../workmode='manual' or ../workmode='minimum-percent'";
          type uint32 {
              range "0..100";
          }
          units "%";
          description
            "Fan speed which is a percentage of the highest speed and the range of value changes with the workmode and the hardtype of fan. The current range is determined by combining the minimum and maximum values of all cases.";
        }
      }
    }

    container area-energyinfos {
      config false;
      description
        "List of Area Energy.";
      list area-energyinfo {
        key "chassis-position area-id";
        config false;
        description
          "Statistics of Area Energy.";
        leaf chassis-position {
          type string {
            length "1..32";
          }
          config false;
          description
            "Chassis position. The chassis-position is expressed in the format of chassisID. For example, 1. Here 1 is an example. The value may vary with devices.";
        }
        leaf area-id {
          type uint32;
          config false;
          description
            "Area ID.";
        }
        leaf area-rated-power {
          type string {
            length "1..255";
          }
          units "W";
          config false;
          description
            "Area Rated Power.";
        }
        leaf area-assigned-power {
          type string {
            length "1..255";
          }
          units "W";
          config false;
          description
            "Area assigned Power.";
        }
        leaf area-used-power {
          type string {
            length "1..255";
          }
          units "W";
          config false;
          description
            "Area Used Power.";
        }
        leaf area-left-power {
          type string {
            length "1..255";
          }
          units "W";
          config false;
          description
            "Area Left Power.";
        }
        leaf area-real-power {
          type string {
            length "1..255";
          }
          units "W";
          description
            "Area Real-time Power.";
        }
        leaf area-power-mode {
          type string {
            length "1..255";
          }
          description
            "Area Power Mode.";
        }
        leaf area-average-power {
          type string {
            length "1..255";
          }
          units "W";
          config false;
          description
            "Average instantaneous power consumption in a period of time.";
        }
        leaf others-power {
          type string {
            length "1..255";
          }
          units "W";
          config false;
          description
            "Accumulated rated power consumption of devices with low power consumption, such as the CMU, PMU, LCD, fan, and power board.";
        }
        container board-energys {
          config false;
          description
            "List of energy information about a board.";
          list board-energy {
            key "position";
            config false;
            description
              "Statistics of energy information about a board.";
            leaf position {
              type string {
                length "1..32";
              }
              config false;
              description
                "Board position. The position is expressed in the format of slotID. For example, 1. Here 1 is an example. The value may vary with devices.";
            }
            leaf entity-index {
              type uint32;
              config false;
              description
                "Board index.";
            }
            leaf type {
              type string {
                length "1..32";
              }
              config false;
              description
                "Board type.";
            }
            leaf pcb-name {
              type string {
                length "1..32";
              }
              config false;
              description
                "Board pcb name.";
            }
            leaf energy-saving-mode-status {
              type driver-entity-bool;
              config false;
              description
                "Board energy-saving mode status.";
            }
            leaf voltage-value {
              type string {
                length "1..255";
              }
              units "V";
              config false;
              description
                "Current voltage value.";
            }
            leaf electrical-value {
              type string {
                length "1..255";
              }
              units "A";
              config false;
              description
                "Current electrical value.";
            }
            leaf current-power {
              type string {
                length "1..255";
              }
              units "W";
              config false;
              description
                "Current power value.";
            }
            leaf rated-power {
              type string {
                length "1..255";
              }
              units "W";
              config false;
              description
                "Rated power value.";
            }
            leaf power-threshold {
              type string {
                length "1..255";
              }
              units "W";
              config false;
              description
                "Power threshold value.";
            }
            leaf efficiency {
              type string {
                length "1..255";
              }
              units "%";
              config false;
              description
                "Efficiency value.";
            }
            leaf average-power {
              type string {
                length "1..255";
              }
              units "W";
              config false;
              description
                "Average instantaneous power value consumption of the board in a period of time.";
            }
            leaf saved-power {
              type string {
                length "1..255";
              }
              units "W";
              config false;
              description
                "Indicates the actual reduced power consumption of the board.";
            }
            leaf expected-saved-power {
              type string {
                length "1..255";
              }
              units "W";
              config false;
              description
                "The power consumption expected to be reduced by the board after energy saving measures are taken.";
            }
            container energy-saving-mode-states {
              config false;
              description
                "List of energy-saveing mode information about a board.";
              list energy-saving-mode-state {
                key "board-energy-mode";
                config false;
                description
                    "Operational state of the board in energy-saving mode.";
                leaf board-energy-mode {
                  type standard-deep-mode-type;
                  description
                    "The energy-saving mode of a board.";
                }
                leaf support {
                  type driver-bool;
                  description
                    "'yes' indicates the board supports energy-saving mode; while 'no' indicates the board cannot support energy-saving mode.";
                }
                leaf status {
                  type driver-entity-bool;
                  description
                    "Whether the energy-saving mode is enabled on the board.";
                }
                leaf disable-reason {
                  type string {
                    length "1..255";
                  }
                  description
                    "Disable reason.";
                }
              }
            }
          }
        }
      }
    }
    
    container board-powers {
      config false;
      description
        "List of power information about a board.";
      list board-power {
        key "position";
        description
          "Statistics of power information about a board.";
        leaf position {
          type string {
            length "1..32";
          }
          description
            "Board position. The position is expressed in the format of slotID. For example, 1. Here 1 is an example. The value may vary with devices.";
        }
        leaf entity-index {
          type uint32;
          description
            "Board index.";
        }
        leaf pcb-name {
          type string {
            length "1..32";
          }
          description
            "Board type.";
        }
        leaf voltage-value {
          type string {
            length "1..255";
          }
          units "V";
          description
            "Current voltage value.";
        }
        leaf electrical-value {
          type string {
            length "1..255";
          }
          units "A";
          description
            "Current electrical value.";
        }
        leaf current-power {
          type string {
            length "1..255";
          }
          units "W";
          description
            "Current power value.";
        }
        leaf rated-power {
          type string {
            length "1..255";
          }
          units "W";
          description
            "Rated power value.";
        }
        leaf power-threshold {
          type string {
            length "1..255";
          }
          units "W";
          description
            "Power threshold value.";
        }
        leaf efficiency {
          type string {
            length "1..255";
          }
          units "%";
          description
            "Efficiency value.";
        }
      }
    }

    container electronic-labels {
      config false;
      description
        "List of electronic labels.";
      list electronic-label {
        key "entity-class position entity-serial-number";
        config false;
        description
          "Statistics of electronic label.";
        leaf entity-class {
          type hardware-type:hardware-entityclass-type;
          config false;
          description
            "Entity Class.";
        }
        leaf position {
          type string {
            length "1..32";
          }
          config false;
          description
            "Position. The position is expressed in the format of slotID. For example, 1. Here 1 is an example. The value may vary with devices.";
        }
        leaf entity-serial-number {
          type uint32;
          config false;
          description
            "Physical Number.";
        }
        leaf entity-index {
          type uint32;
          config false;
          description
            "Entity Index.";
        }
        leaf entity-bomid {
          type string {
            length "1..128";
          }
          config false;
          description
            "BOM ID.";
        }
        leaf barcode {
          type string {
            length "1..128";
          }
          config false;
          description
            "Barcode.";
        }
        leaf bom-english-desc {
          type string {
            length "1..256";
          }
          config false;
          description
            "English description of a BOM.";
        }
        leaf bom-local-desc {
          type string {
            length "1..256";
          }
          config false;
          description
            "Local description of a BOM.";
        }
        leaf manufacturer-name {
          type string {
            length "1..128";
          }
          config false;
          description
            "Manufacturer name.";
        }
        leaf manufacturer-date {
          type string {
            length "1..128";
          }
          config false;
          description
            "Manufacture date.";
        }
        leaf manufacturer-code {
          type string {
            length "1..128";
          }
          config false;
          description
            "Manufacture code.";
        }
        leaf board-type {
          type string {
            length "1..128";
          }
          config false;
          description
            "Board type.";
        }
        leaf entity-asset-id {
          type string {
            length "1..128";
          }
          config false;
          description
            "Asset ID.";
        }
        leaf entity-clei-code {
          type string {
            length "1..128";
          }
          config false;
          description
            "CLEI code.";
        }
        leaf entity-update-log {
          type string {
            length "1..128";
          }
          config false;
          description
            "Update log.";
        }
        leaf archives-info-version {
          type string {
            length "1..128";
          }
          config false;
          description
            "Archives information version.";
        }
        leaf entity-open-bomid {
          type string {
            length "1..128";
          }
          config false;
          description
            "The BomId for distribution.";
        }
        leaf entity-issue-number {
          type string {
            length "1..128";
          }
          config false;
          description
            "Issue number.";
        }
        leaf entity-model {
          type string {
            length "1..128";
          }
          config false;
          description
            "External model of an entity.";
        }
        leaf entity-elabel-version {
          type string {
            length "1..128";
          }
          config false;
          description
            "Elabel version.";
        }
        leaf entity-elabel-extend {
          type string {
            length "1..270";
          }
          config false;
          description
            "Extend information.";
        }
        leaf silk-screen {
          type string {
            length "1..256";
          }
          config false;
          description
            "Silk screen information.";
        }
      }
    }

    container mbusnodes {
      config false;
      description
        "List of information about all monitoring nodes of the host.";
      list mbusnode {
        key "slot-id";
        config false;
        description
          "Statistics of information about a monitoring node.";
        leaf slot-id {
          type string {
            length "1..30";
          }
          config false;
          description
            "Position. The slot-id is expressed in the format of slotID. For example, 1. Here 1 is an example. The value may vary with devices.";  
        }
        leaf register {
          type string {
            length "1..63";
          }
          config false;
          description
            "Registration status of the board.";
        }
        leaf board-type {
          type string {
            length "1..63";
          }
          config false;
          description
            "Type of the board.";
        }
        leaf eeprom-number {
          type uint32 {
            range "0..24";
          }
          config false;
          description
            "Number of EEPROMS on the board.";
        }
        leaf temperature-monitor-number {
          type uint32 {
            range "0..128";
          }
          config false;
          description
            "Number of temperature sensors on the board.";
        }
        leaf voltage-monitor-number {
          type uint32 {
            range "0..128";
          }
          config false;
          description
            "Number of voltage sensors on the board.";
        }
      }
    }
    container check-running-software-safes {
      config false;
      description
        "List of checking running software safety.";
       list check-running-software-safe {
        key "position item";
        config false;
        description
          "Statistics of checking running software safety.";
        leaf position {
          type string {
            length "1..32";
          }
          config false;
          description
            "Board position. The position is expressed in the format of slotID. For example, 1. Here 1 is an example. The value may vary with devices.";
        }
		leaf item {
          type driver-item-type;
          config false;
          description
            "System Item.";
        }
        leaf board-type {
          type string {
            length "1..32";
          }
          config false;
          description
            "Board type.";
        }
        leaf pkgsha256hash {
          type string {
            length "1..255";
          }
          config false;
          description
            "The HASH value in the system.";
        }
        leaf runsha256hash {
          type string {
            length "1..255";
          }
          config false;
          description
            "The HASH value in the board.";
        }
		leaf result {
          type driver-result-type;
          config false;
          description
            "Check Result.";
        }
      }
    } 
	
	  container bootinfos {
      config false;
      description
        "List of boot information.";
       list  bootinfo{
        key "position";
        config false;
        description
          "Statistics of boot status information.";
        leaf position {
          type string {
            length "1..32";
          }
          config false;
          description
            "Board position. The position is expressed in the format of slotID. For example, 1. Here 1 is an example. The value may vary with devices.";
        }
        leaf board-type {
          type string {
            length "1..32";
          }
          config false;
          description
            "Board type.";
        }
        leaf rot {
           type string {
            length "1..64";
          }
          config false;
          description
            "Boot Status.";
        }
      }
    }
    
    container multi-chassis-attributes {
      config false;
      description
        "List of multiple chassis attributes.";
      list multi-chassis-attribute {
        key "current-chassis-id";
        description
          "Statistics of multiple chassis attribute.";
        leaf current-chassis-id {
          type uint32 {
            range "1..2";
          }
          description
            "Current chassis id.";
        }
        leaf next-chassis-id {
          type uint32 {
            range "1..2";
          }
          description
            "Next chassis id.";
        }
        leaf chassis-type {
          type driver-multi-chassis-type;
          description
            "Multi chassis type.";
        }
      }
    }
    
    container chassis-run-modes {
      config false;
      description
        "List of chassis running modes.";
      list chassis-run-mode {
        key "chassis-id";
        description
          "Statistics of chassis running mode.";
        leaf chassis-id {
          type string {
            length "1..31";
          }
          description
            "Chassis id. The chassis-id is expressed in the format of chassisID. For example, 1. Here 1 is an example. The value may vary with devices.";
        }
        leaf current-run-mode {
          type driver-run-mode-type;
          description
            "Current run mode.";
        }
        leaf next-run-mode {
          type driver-run-mode-type;
          description
            "Next run mode.";
        }
        leaf current-run-cluster {
          type string {
            length "1..4";
          }
          description
            "Current cluster id.";
        }
        leaf next-run-cluster {
          type string {
            length "1..3";
          }
          description
            "Next cluster id.";
        }
      }
    }
    
    container stratum-3-clocks {
      config false;
      description
        "List of status information about the stratum-3 clocks of the system.";
      list stratum-3-clock {
        key "slot-id";
        description
          "Statistics of status information about the stratum-3 clock of the system.";
        leaf slot-id {
          type string {
            length "1..32";
          }
          description
            "ID of the slot where the board resides. The slot-id is expressed in the format of slotID. For example, 1. Here 1 is an example. The value may vary with devices.";
        }
        leaf board-device-type {
          type string {
            length "1..32";
          }
          description
            "Type of the board.";
        }
        leaf clock-type {
          type driver-clock-type;
          description
            "Type of the clock associated with the board.";
        }
        leaf clock-slot-id {
          type string {
            length "1..32";
          }
          description
            "ID of the clock associated with the board.";
        }
        leaf switch-mode {
          type driver-switch-mode-type;
          description
            "Mode of the clock associated with the board.";
        }
      }
    }

    container system-sync-clocks {
      config false;
      description
        "List of status information about the synchronization clocks of the system.";
      list system-sync-clock {
        key "slot-id";
        description
          "Statistics of status information about the synchronization clock of the system.";
        leaf slot-id {
          type string {
            length "1..32";
          }
          description
            "ID of the slot where the board resides. The slot-id is expressed in the format of slotID. For example, 1. Here 1 is an example. The value may vary with devices.";
        }
        leaf board-device-type {
          type string {
            length "1..32";
          }
          description
            "Type of the board.";
        }
        leaf clock-type {
          type driver-clock-type;
          description
            "Type of the clock associated with the board.";
        }
        leaf clock-slot-id {
          type string {
            length "1..32";
          }
          description
            "ID of the clock associated with the board.";
        }
        leaf switch-mode {
          type driver-switch-mode-type;
          description
            "Mode of the clock associated with the board.";
        }
        leaf lock-state {
          type driver-lock-state-type;
          description
            "Locking status of the clock.";
        }
      }
    }
    
    container rollback-attribute {
      config false;
      description
        "Statistics of rollback information.";
        leaf rollback-soft-pack {
          type string {
            length "1..255";
          }
          description
            "Rollback software package info.";
        }
        leaf rollback-patch-file {
          type string {
            length "1..255";
          }
          description
            "Rollback patch file info.";
        }
        leaf rollback-config-file {
          type string {
            length "1..255";
          }
          description
            "Rollback config file info.";
        }
        leaf rollback-paf-file {
          type string {
            length "1..255";
          }
          description
            "Rollback paf file info.";
        }
        leaf rollback-result {
          type string {
            length "1..255";
          }
          description
            "Rollback result info.";
        }
        leaf rollback-remain-time {
          type string {
            length "1..255";
          }
          description
            "Rollback remain time info.";
        }
        leaf-list rollback-feature-pkg-file {
        type string {
          length "1..255";
        }
        description "Operational data of rollback feature package file.";
      }
    }
    
	 container slave-defaults {
      config false;
      description
        "List of slave default.";
        list slave-default {
        key "chassis-id slot-id";
        description
          "Statistics of slave default.";
        leaf chassis-id {
          type string {
            length "1..32";
          }
          description
            "Chassis ID. The chassis-id is expressed in the format of chassisID. For example, 1. Here 1 is an example. The value may vary with devices.";
        }
        leaf slot-id {
          type string {
            length "1..32";
          }
          description
            "Slot ID. The slot-id is expressed in the format of slotID. For example, 1. Here 1 is an example. The value may vary with devices.";
        }
        leaf slave-default {
          type string {
            length "1..64";
          }
          description
            "Slave Default.";
        }
      }
    }

    container inner-links {
       config false;
       description
         "List of inner links.";
       list inner-link {
         key "link-type left-chassis-position right-chassis-position";
         config false;
         description
           "Statistics of inner link.";
         leaf link-type {
           type driver-inner-link-type;
           config false;
           description
             "Link type.";
         }  
         leaf left-chassis-position {
           type string {
             length "1..32";
           }
           config false;
           description
             "Position of the left chassis.";
         }
         leaf right-chassis-position {
           type string {
             length "1..32";
           }
           config false;
           description
             "Position of the right chassis.";
         }
         leaf link-name {
           type string {
             length "1..64";
           }
           config false;
           description
             "Inner link name.";
         }
         leaf link-index {
           type string {
             length "1..64";
           }
           config false;
           description
             "Inner link index.";
         }
         leaf left-chassis-type {
           type driver-link-chassis-type;
           config false;
           description
             "Type of the left chassis.";
         }
         leaf right-chassis-type {
           type driver-link-chassis-type;
           config false;
           description
             "Type of the right chassis.";
         }
         leaf operation-state {
           type driver-link-state-type;
           config false;
           description
             "Operation state.";
         }
         leaf alarm-state {
           type driver-link-state-type;
           config false;
           description
             "Alarm states whose values inherit HUAWEI-INNER-LINK-MIB.";
         }
         container physical-inner-links {
           config false;
           description
             "List of physical inner links.";
           list physical-inner-link {
             key "physical-link-name";
             config false;
             description
               "Statistics of physical inner link.";
             leaf physical-link-name {
               type string {
                 length "1..128";
               }
               config false;
               description
                 "Physical link name. The physical-link-name is expressed in the format of slotID/cardID/portID. For example, 1/0/1. Here 1/0/1 is an example. The value may vary with devices.";
             }
             leaf left-port-name {
               type string {
                 length "1..128";
               }
               config false;
               description
                 "Left port name.";
             }
             leaf right-port-name {
               type string {
                 length "1..128";
               }
               config false;
               description
                 "Right port name.";
             }
             leaf operation-status {
               type driver-link-state-type;
               config false;
               description
                 "Operation status.";
             }
             leaf repair-id {
               type uint32;
               config false;
               description
                 "Repair ID.";
             }
             leaf repair-description {
               type string {
                 length "1..255";
               }
               config false;
               description
                 "Repair description.";
             }
             container check-points {
               config false;
               description
                 "List of checking points.";
               list check-point {
                 key "index";
                 config false;
                 description
                   "Statistics of checking point.";
                 leaf index {
                   type uint32;
                   config false;
                   description
                     "Check point index.";
                 }
                 leaf entity-name {
                   type string {
                     length "1..255";
                   }
                   config false;
                   description
                     "Check point name.";
                 }
                 leaf entity-class {
                   type hardware-type:hardware-entityclass-type;
                   config false;
                   description
                     "Check point type.";
                 }
                 leaf status {
                   type driver-link-state-type;
                   config false;
                   description
                     "Check point status.";
                 }
                 leaf reason-id {
                   type uint32;
                   config false;
                   description
                     "Reason ID.";
                 }
                 leaf reason-description {
                   type string {
                     length "1..255";
                   }
                   config false;
                   description
                     "Reason description.";
                 }
                 leaf repair-id {
                   type uint32;
                   config false;
                   description
                     "Repair ID.";
                 }
                 leaf repair-description {
                   type string {
                     length "1..255";
                   }
                   config false;
                   description
                     "Repair description.";
                 }
               }
             }
           }
         }
      }
    }
    
    container slot-statistics {
      config false;
      description
        "List of slot statistics.";
      list slot-statistic {
        key "chassis-id slot-type";
        description
          "Statistics of slot.";
        leaf chassis-id {
          type string {
            length "1..32";
          }
          description
            "ChassisId. The chassis-id is expressed in the format of chassisID. For example, 1. Here 1 is an example. The value may vary with devices.";
        }
        leaf slot-type {
          type driver-slot-infos-type;
          description
            "SlotType.";
        }
        leaf total-slot-number {
          type uint32 {
            range "1..65535";
          }
          description
            "TotalSlotnum.";
        }
        leaf online-slot-number {
          type uint32 {
            range "0..65535";
          }
          description
            "OnlineSlotnum.";
        }
      }
    }
     
    container device-health-checks {
      config false;
      description
        "List of check device health.";
      list device-health-check {
        key "item";
        description
          "Operational data of device health check.";
        leaf item {
          type string {
            length "1..255";
          }
          description
            "Check items.";
        }
        leaf status {
          type string {
            length "1..255";
          }
          description
            "Check status.";
        }
        leaf reason {
          type string {
            length "1..255";
          }
          description
            "Abnormal reason.";
        }
        leaf advice {
          type string {
            length "1..255";
          }
          description
            "Check advice.";
        }
      }
    }   
    container leds {
      config false;
      description
        "List of all LED indicators.";
      list led {
        key "class position led-type";
        description
          "Operational data of LED indicators.";
        leaf class {
          type devm:entity-class-type;
          description
            "Entity class of the device where the LED indicator is located.";
        }
        leaf position {
          type string {
            length "1..32";
          }
          description
            "Entity position of the device where the LED indicator is located.";
        }
        leaf led-type {
          type driver:led-class-type;
          description
            "Type of the LED indicator.";
        }
        leaf led-color {
          type driver:led-color-type;
          description
            "Luminous Color of the LED indicator.";
        }
        leaf color-series {
          type driver:color-series-type;
          description
            "Color Series of LED indicators.";
        }
        leaf blink-frequency {
          type string {
            length "1..64";
          }
          units "Hz";
          description
            "Blinking frequency of the LED indicator.";
        }
        leaf duration {
          type uint32 {
            range "1..3600";
          }
          units "s";
          description
            "Blinking duration of the LED indicator.";
        }
      }
    }
    container cluster-fiber {
      description
          "Configure cluster fiber.";
      container chassis-fibers {
        description
          "List of chassis fibers statistics.";
        list chassis-fiber {
          key "chassis-id";
          description
            "Configure chassis fiber length.";
          leaf chassis-id {
            type string {
              length "1..32";
            }
            description
              "Chassis id. For example, it is expressed by 1. And the value may vary with devices.";
          }
          leaf fiber-length {
            type uint32 {
              range "10|15|20|30|60|90|100";
            }
            units "m";
            mandatory true;
            description
              "Fiber length between clc and ccc or master and slave.";
          }
        }
      }
      container actual-fibers {
        config false;
        description
          "List of actual fibers statistics.";
        list actual-fiber {
          key "chassis-id";
          description
            "Statistics of actual fiber length.";
          leaf chassis-id {
            type string {
              length "1..32";
            }
            description
              "Chassis id. For example, it is expressed by 1. And the value may vary with devices.";
          }
          leaf fiber-length {
            type uint32 {
              range "10|15|20|30|60|90|100";
            }
            units "m";
            description
              "Fiber length between clc and ccc or master and slave.";
          }
        }
      }
      container chassis-fiber-connected-mode {
        config false;
        description
          "Statistics of chassis fiber connected modes.";
        leaf current-fiber-connect-mode {
          type driver-fiber-connect-mode;
          description
            "Current fiber connect mode.";
        }
        leaf next-fiber-connect-mode {
          type driver-fiber-connect-mode;
          description
            "Next fiber connect mode.";
        } 
      }

      container fabric-fiber-status-errors {
        config false;
        description
          "List of fabric fiber status errors.";
        list fabric-fiber-status-error {
          key "local-physical-port";
          description
            "Statistics of fabric fiber status errors between physical innerlinks.";
          leaf local-physical-port {
            type string {
              length "1..32";
            }
            description
              "Local physical port name. It is expressed in the format of chassisID/slotID/cardID/portID."; 
          }
          leaf local-physical-port-status {
            type fiber-status;
            description
              "Local physical port status.";
          }
          leaf remote-physical-port {
            type string {
              length "1..32";
            }
            description
              "Remote physical port name. It is expressed in the format of chassisID/slotID/cardID/portID.";
          }
          leaf remote-physical-port-status {
            type fiber-status;
            description
              "Remote physical port status.";
          } 
          leaf fiber-actual-length {
            type uint32;
            units "m";
            description
              "Actual length of the fiber.";
          }
          leaf fiber-config-length {
            type uint32;
            units "m";
            description
              "Config length of the fiber.";
          }
          leaf fiber-sequence-number {
            type string {
              length "1..32";
            }
            description
              "Sequence number of the fiber.";
          }
          leaf bomid {
            type string {
              length "1..32";
            }
            description
              "Bill of materials code.";
          }
          leaf chassis-id {
            type string {
              length "1..32";
            }
            description
              "Chassis id. The value may vary with devices.";
            ext:support-filter "true";
          }
        }
      }

      container fabric-fiber-elabels {
        config false;
        description
          "List of fabric fiber elabel.";
        list fabric-fiber-elabel {
          key "local-physical-port";
          description
            "Statistics of fabric fiber elabel.";
          leaf local-physical-port {
            type string {
              length "1..32";
            }
            description
              "Local physical port name. It is expressed in the format of chassisID/slotID/cardID/portID."; 
          }
          leaf vendor-pn {
            type string {
              length "1..32";
            }
            description
              "Vendor part number.";
          }
          leaf vendor-sn {
            type string {
              length "1..32";
            }
            description
              "Vendor serial number.";
          }
          leaf vendor-name {
            type string {
              length "1..32";
            }
            description
              "Vendor name.";
          }
          leaf item-number {
            type string {
              length "1..32";
            }
            description
              "Item number.";
          } 
          leaf fiber-description {
            type string {
              length "1..32";
            }
            description
              "Fiber description.";
          }
          leaf remote-physical-port {
            type string {
              length "1..32";
            }
            description
              "Remote physical port name. It is expressed in the format of chassisID/slotID/cardID/portID.";
          }
        }
      }
    }

    container battery {
      config false;
      description
        "Operational state of Battery.";
      leaf soc {
        type uint8 {
          range "0..100";
        }
        units "%";
        description
          "Battery state of charge (SOC).";
      }
      leaf soh {
        type uint8 {
          range "0..100";
        }
        units "%";
        description
          "Battery state of health (SOH).";
      }
    }
  }
    rpc set-usb-uart-stat {
    description
      "Set usb uart status.";
    input {
      leaf usb-uart-status {
        type driver-usb-uart;
        description
          "Usb uart status, open or close.";
         }
        }
      }
    rpc set-next-system-work-mode {
       description "Set next system work mode.";
       input {
         leaf next-system-work-mode {
           type system-work-mode-type;
           mandatory true;
           description
             "Next time the system starts working mode.";
         }
       }
    }
    rpc power-on-board {
       description "Power on board.";
       input {
         leaf board-position {
           type string {
             length "1..32";
           }
           mandatory true;
           description
             "Board position.";
         }
       }
    }
    rpc power-off-board {
       description
         "Power off board.";
        input {
          leaf board-position {
            type string {
              length "1..32";
           }
           mandatory true;
           description
             "Board position.";
           }
           leaf auto-power-on {
             type empty;
             description
               "Auto power on.";
            }
        }
    }
    rpc power-on-mpu {
    ext:node-ref "/devm:devm/devm:mpu-boards/devm:mpu-board";
    description
      "Power on MPU.";
    input {
      leaf board-position {
        type leafref {
          path "/devm:devm/devm:mpu-boards/devm:mpu-board/devm:position";
        }
        mandatory true;
        description
          "Board Position. The board-position is expressed in the format of slotID. For example, 1. Here 1 is an example. The value may vary with devices.";
      }
    }
   }
    rpc power-off-mpu {
    ext:node-ref "/devm:devm/devm:mpu-boards/devm:mpu-board";
    description
      "Power off MPU.";
    input {
      leaf board-position {
        type leafref {
          path "/devm:devm/devm:mpu-boards/devm:mpu-board/devm:position";
        }
        mandatory true;
        description
          "Board Position. The board-position is expressed in the format of slotID. For example, 1. Here 1 is an example. The value may vary with devices.";
      }
      leaf auto-power-on {
        type empty;
        description
          "Auto power on.";
      }
    }
   }
    rpc power-on-lpu {
    ext:node-ref "/devm:devm/devm:lpu-boards/devm:lpu-board";
    description
      "Power on LPU.";
    input {
      leaf board-position {
        type leafref {
          path "/devm:devm/devm:lpu-boards/devm:lpu-board/devm:position";
        }
        mandatory true;
        description
          "Board Position. The board-position is expressed in the format of slotID. For example, 1. Here 1 is an example. The value may vary with devices.";
      }
    }
   }
    rpc power-off-lpu {
    ext:node-ref "/devm:devm/devm:lpu-boards/devm:lpu-board";
    description
      "Power off LPU.";
    input {
      leaf board-position {
        type leafref {
          path "/devm:devm/devm:lpu-boards/devm:lpu-board/devm:position";
        }
        mandatory true;
        description
          "Board Position. The board-position is expressed in the format of slotID. For example, 1. Here 1 is an example. The value may vary with devices.";
      }
      leaf auto-power-on {
        type empty;
        description
          "Auto power on.";
      }
    }
   }
    rpc power-on-sfu {
    ext:node-ref "/devm:devm/devm:sfu-boards/devm:sfu-board";
    description
      "Power on SFU.";
    input {
      leaf board-position {
        type leafref {
          path "/devm:devm/devm:sfu-boards/devm:sfu-board/devm:position";
        }
        mandatory true;
        description
          "Board Position. The board-position is expressed in the format of slotID. For example, 1. Here 1 is an example. The value may vary with devices.";
      }
    }
  }
    rpc power-off-sfu {
    ext:node-ref "/devm:devm/devm:sfu-boards/devm:sfu-board";
    description
      "Power off SFU.";
    input {
      leaf board-position {
        type leafref {
          path "/devm:devm/devm:sfu-boards/devm:sfu-board/devm:position";
        }
        mandatory true;
        description
          "Board Position. The board-position is expressed in the format of slotID. For example, 1. Here 1 is an example. The value may vary with devices.";
      }
      leaf auto-power-on {
        type empty;
        description
          "Auto power on.";
      }
    }
  }
    rpc power-on-ecu {
    description
      "Power on ECU.";
    input {
      leaf board-position {
        type string {
          length "1..32";
        }
        mandatory true;
        description
          "Board Position. The board-position is expressed in the format of slotID. For example, 1. Here 1 is an example. The value may vary with devices.";
      }
    }
  }
    rpc power-off-ecu {
    description
      "Power off ECU.";
    input {
      leaf board-position {
        type string {
          length "1..32";
        }
        mandatory true;
        description
          "Board Position. The board-position is expressed in the format of slotID. For example, 1. Here 1 is an example. The value may vary with devices.";
      }
      leaf auto-power-on {
        type empty;
        description
          "Auto power on.";
      }
    }
  } 
    rpc power-on-icu {
    description
      "Power on ICU.";
    input {
      leaf board-position {
        type leafref {
          path "/devm:devm/driver:driver/driver:icus/driver:icu/driver:position";
        }
        mandatory true;
        description
          "Board Position. The board-position is expressed in the format of slotID. For example, 1. Here 1 is an example. The value may vary with devices.";
      }
    }
  }
    rpc power-off-icu {
    description
      "Power off ICU.";
    input {
      leaf board-position {
        type leafref {
          path "/devm:devm/driver:driver/driver:icus/driver:icu/driver:position";
        }
        mandatory true;
        description
          "Board Position. The board-position is expressed in the format of slotID. For example, 1. Here 1 is an example. The value may vary with devices.";
      }
      leaf auto-power-on {
        type empty;
        description
          "Auto power on.";
      }
    }
  }
    rpc reset-lcd {
    description
      "Reset LCD.";
    input {
      leaf board-position {
        type string {
          length "1..32";
        }
        description
          "Board Position. The board-position is expressed in the format of slotID. For example, 1. Here 1 is an example. The value may vary with devices.";
      }
    }
  }
    rpc reset-ecu-board {
    description
      "Reset ECU board.";
    input {
      leaf board-position {
        type string {
          length "1..32";
        }
        description
          "Board Position. The board-position is expressed in the format of slotID. For example, 1. Here 1 is an example. The value may vary with devices.";
      }
    }
  }
    rpc reset-icu-board {
    description
      "Reset ICU board.";
    input {
      leaf board-position {
        type leafref {
          path "/devm:devm/driver:driver/driver:icus/driver:icu/driver:position";
        }
        description
          "Board Position. The board-position is expressed in the format of slotID. For example, 1. Here 1 is an example. The value may vary with devices.";
      }
    }
  }
    rpc reset-cmu-board {
      ext:node-ref "/devm:devm/driver:driver/driver:cmus/driver:cmu";
    description
      "Reset CMU board.";
    input {
      leaf board-position {
        type leafref {
          path "/devm:devm/driver:driver/driver:cmus/driver:cmu/driver:position";
        }
        description
          "Board Position. The board-position is expressed in the format of slotID. For example, 1. Here 1 is an example. The value may vary with devices.";
      }
    }
  }
    rpc reset-fan-board {
      ext:node-ref "/devm:devm/driver:driver/driver:fans/driver:fan";
    description
      "Reset fan.";
    input {
      leaf board-position {
        type leafref {
          path "/devm:devm/driver:driver/driver:fans/driver:fan/driver:position";
        }
        description
          "Board Position. The board-position is expressed in the format of slotID. For example, 1. Here 1 is an example. The value may vary with devices.";
      }
    }
  }
    rpc reset-dustproof-net {
      ext:node-ref "/devm:devm/devm:chassiss/devm:chassis";
      description
        "Clear the running time of the air filter in a specified chassis.";
      input {
        leaf chassis-position {
          type leafref {
          path "/devm:devm/devm:chassiss/devm:chassis/devm:position";
        }
          description
            "Chassis position. The chassis-position is expressed in the format of chassisID. For example, 1. Here 1 is an example. The value may vary with devices.";
        }
      }
    }
    rpc reset-mbus-node {
      ext:node-ref "/driver:driver/driver:mbusnodes/driver:mbusnode";
      description
        "Reset mbus node.";
      input {
        leaf board-position {
          type leafref {
          path "/driver:driver/driver:mbusnodes/driver:mbusnode/driver:slot-id";
        }
          description
            "Board Position. The board-position is expressed in the format of slotID. For example, 1. Here 1 is an example. The value may vary with devices.";
        }
      }
    }
    rpc reset-chassis {
      ext:node-ref "/devm:devm/devm:chassiss/devm:chassis";
      description
        "Reset chassis.";
      input {
        leaf chassis-position {
          type leafref {
            path "/devm:devm/devm:chassiss/devm:chassis/devm:position";
          }
          description
            "Chassis position. The chassis-position is expressed in the format of chassisID. For example, 1. Here 1 is an example. The value may vary with devices.";
        }
      }
    }
    rpc set-slave-default {
    ext:node-ref "/devm:devm/devm:chassiss/devm:chassis";
    description
      "Set slave default.";
    input {
      leaf chassis-id {
          type string {
            length "1..32";
          }
        description
          "Chassis ID. The chassis-id is expressed in the format of chassisID. For example, 1. Here 1 is an example. The value may vary with devices.";
      }
      choice set-slave-board {
        mandatory true;
          description
            "Set the default slave board.";
        case slave-default {
          description
            "Set the default slave board.";
          leaf slave-default {
            type string {
              length "1..64";
            }
            description
              "Slave Default. The slave-default is expressed in the format of slotID. For example, 1. Here 1 is an example. The value may vary with devices.";
          }
        }
        case clear-slave-default {
          description
            "Clear the configuration of the default slave board.";
          leaf clear-slave-board {
            type empty;
            description
              "Clear the configuration of the default slave board.";
          }
        }
      }
    }
  }

    rpc set-flash-lock {
      description
        "Set-flash-lock.";
      input {
        leaf flash-lock {
          type driver-flash-lock;
          default "immediately";
          description
            "Flash lock.";
        }
        leaf days {
          when "../flash-lock = 'delay' ";
          type uint32 {
          range "1..90";
          }
          description
            "Days.";
        }
      }
    }
	
    rpc power-on-card {
    ext:node-ref "/devm:devm/devm:cards/devm:card";
    description
      "Power-on-card.";
    input {
      leaf card-position {
        type leafref {
          path "/devm:devm/devm:cards/devm:card/devm:position";
        }
        mandatory true;
        description
          "Card Position. The card-position is expressed in the format of slotID/cardID. For example, 1/0. Here 1/0 is an example. The value may vary with devices.";
      }
    }
  }	

    rpc power-off-card {
    ext:node-ref "/devm:devm/devm:cards/devm:card";
    description
      "Power-off-card.";
    input {
      leaf card-position {
        type leafref {
          path "/devm:devm/devm:cards/devm:card/devm:position";
        }
        mandatory true;
        description
          "Card Position. The card-position is expressed in the format of slotID/cardID. For example, 1/0. Here 1/0 is an example. The value may vary with devices.";
      }
      leaf auto-power-on {
        type empty;
        description
          "Auto power on.";
      }
    }
  }
  rpc reset-cpu {
    description
      "Reset CPU.";
    input {
      leaf slot-id {
        type string {
          length "1..32";
        }
        mandatory true;
        description
          "Board position.";
      }
      leaf cpu-id {
        type string {
          length "1..32";
        }
        mandatory true;
        description
          "CPU position.";
      }
    }
  }
    rpc set-boot-password {
    description
      "Set-boot-password.";
    input {
      choice position {
          description
          "Choose to set all slot or one slot.";
          case all {
            description
              "Set boot password to all.";
              leaf all {
                type empty;
                mandatory true;
                description
                  "Set boot password to all.";
              }
          }
          case slot-id {
            description
              "Set boot password to specific slot.";
              leaf slot-id {
                type string {
                  length "1..31";
                }
                mandatory true;
                description
                  "Slot ID. The slot-id is expressed in the format of slotID. For example, 1. Here 1 is an example. The value may vary with devices.";
              }
          }
      }
      leaf old-password {
        type pub-type:password-extend {
          length "1..255";
        }
        description
          "OldPassword.";
      }
      leaf new-password {
        type pub-type:password-extend {
          length "1..255";
        }
        mandatory true;
        description
          "NewPassword.";
      }	
    }
  }
  
  rpc auto-upgrade-models {
    ext:node-ref "/driver:driver/driver:global-attribute";
    description
      "Set auto upgrade model.";
    input {
      leaf auto-upgrade-model {
        type driver-auto-upgrade-mode;
        description
          "Auto upgrade model.";
      }
    }
  }
  
  rpc interface-match-check-recovery {
    description
      "Used to enable the configuration restoration function.";
    input {
      leaf position {
        type string {
          length "1..30";
        }
        description
          "Enabling position of configuration restoration function. The position is expressed in the format of slotID. For example, 1. Here 1 is an example. The value may vary with devices.";
      }
    }
  }
  
  rpc rollback {
    description
      "The system will rollback to the previous version, the current configuration will be lost.";
    input {
      leaf rollback-choice {
        type rollback-choice-type;
        description
          "Used to rollback to the previous version.";
      }
    }
  }
  
  rpc set-multi-chassis-id {
    ext:node-ref "/devm:devm/devm:chassiss/devm:chassis";
    description
      "Set multi chassis id.";
    input {
      leaf current-chassis-id {
        type uint32 {
          range "1..2";
        }
        description
          "Current chassis id.";
      }
      leaf next-chassis-id {
        type uint32 {
          range "1..2";
        }
        description
          "Next chassis id.";
      }
    }
  }
  
  rpc set-chassis-run-mode {
    ext:node-ref "/devm:devm/devm:chassiss/devm:chassis";
    description
      "Set chassis run mode.";
    input {
      leaf chassis-id {
        type string {
          length "1..31";
        }
        description
          "Chassis id. The chassis-id is expressed in the format of chassisID. For example, 1. Here 1 is an example. The value may vary with devices.";
      }
      leaf next-run-mode {
        type driver-next-run-mode;
        mandatory true;
        description
          "Next run mode.";
      }
      leaf next-run-cluster {
        when "../next-run-mode='virtual-cluster-chassis'";
        type string {
          length "1..3";
        }
        description
          "Next cluster id.";
      }
    }
  }
  
  rpc set-next-work-mode {
    description
      "Set next work mode, 1+1 or 1:1. The work mode cannot be switched on specific device models or in specific scenarios (warning:system will restart after success, and then take effect).";
    input {
      leaf next-work-mode {
        type driver-system-mode;
        mandatory true;
        description
          "Next work mode, 1+1 or 1:1.";
      }
    }
  }
  
  rpc set-split-resume {
    description
      "Slave chassis reset mode. It will take effect only both the inter-chassis control link and data link fail in virtual cluster scenarios.";
    input {
      leaf split-resume {
        type driver-split-resume-mode-type;
        mandatory true;
        description
          "Slave chassis reset mode.";
      }
    }
  }

  rpc set-led-flash {
    description
      "Set the indicator blinking periods.";
    input {
      uses led-flash-time;
    }
  }

  rpc set-slot-led-flash {
    ext:node-ref "/devm:devm/devm:mpu-boards/devm:mpu-board";
    ext:node-ref "/devm:devm/devm:lpu-boards/devm:lpu-board";
    ext:node-ref "/devm:devm/devm:cards/devm:card";
    description
      "Set the board or card indicator blinking periods.";
    input {
      leaf position {
        type string {
          length "1..32";
        }
        mandatory true;
        description
          "Device position. The position is expressed in the format of slotID.";
      }
      leaf flash-time {
        type uint32 {
          range "1..5";
        }
        units "s";
        default "3";
        description
          "Set the duration in which an indicator blinks.";
      }
      leaf alarm-status-time {
        type uint32 {
          range "1..5";
        }
        units "s";
        default "3";
        description
          "Set the duration in which an indicator does not blink temporarily.";
      }
      leaf cancel-time {
        type uint32 {
          range "1..60";
        }
        units "min";
        default "10";
        description
          "Set the total duration after which an indicator stops blinking.";
      }
    }
  }

  rpc set-run-led-flash-off {
    description
      "Set board or card indicator stop blinking periods.";
    input  {
      choice set-type {
        mandatory true;
        description
          "Set type.";
        case turn-off-all {
          description
            "Set all the board or card indicator blinking periods.";
          leaf turn-off-all {
            type empty;
            description
              "Set all the board or card indicator blinking periods.";
          }
        }
        case turn-off-specific {
          description
            "Set the board or card indicator blinking periods.";
          leaf turn-off-specific {
            type string {
              length "1..32";
            }
            description
              "Set the board or card indicator blinking periods.";
          }
        }
      }
    }
  }

  rpc board-channel-check {
    description
      "Board channel check.";
    input {
      leaf enable {
        type board-channel-check-type;
        mandatory true;
        description
          "Enable or disable board channel check.";
      }
    }
  }

  rpc set-vsu-service-type {
    description
      "Set VSU service type.";
    input {
      leaf position {
        type string {
          length "1..32";
        }
        mandatory true;
        description
          "VSU position. The position is expressed in the format of slotID. For example, 1. Here 1 is an example. The value may vary with devices.";
      }
      leaf service-type {
        type driver-vsu-service-type;
        mandatory true;
        description
          "VSU service type.";
      }
    }
  }

  rpc check-hardware-compatibility {
    description
      "Check hardware compatibility.";
    input {
      choice check-type {
        mandatory true;
        description
          "Check type.";
        case startup {
          description
            "Startup.";
          leaf startup {
            type empty;
            description
              "The startup file.";
          }
        }
        case file {
          description
            "File.";
          leaf file-name {
            type string {
              length "4..127";
            }
            mandatory true;
            description
              "Packet file name in master MPU cfcard, for example:cfcard:/B02D.CC.";
          }
        }
      }
    }
    output {
      container hardware-compatibility-infos {
        description
          "List of hardware compatibility information.";
        list hardware-compatibility-info {
          key "slot";
          description
            "Information of hardware compatibility.";
          leaf slot {
            type string {
              length "1..32";
            }
            description
              "Slot.";
          }
          leaf board-type {
            type string {
              length "1..32";
            }
            description
              "Board type.";
          }
          leaf result {
            type string {
              length "1..32";
            }
            description
              "Result.";
          }
          leaf detail {
            type string {
              length "1..64";
            }
            description
              "Detail.";
          }
        }
      }
    }
  }

  rpc check-system-software {
    description
      "Check system software.";
    input {
      choice startup-file {
        mandatory true;
        description
          "Choose startup or file.";
        case startup {
          description
            "Startup file.";
          leaf startup {
            type empty;
            description
              "The startup file.";
          }
        }
        case file {
          description
            "Packet file.";
          leaf file-name {
            type string {
              length "4..127";
            }
            description
              "Packet file name in master MPU cfcard, for example:cfcard:/B02D.cc.";
          }
        }
      }
    }
    output {
      leaf sha256-hash-value {
        type string {
          length "1..255";
        }
        description
          "SHA256 hash value of the system software.";
      }
      leaf signature-result {
        type driver-check-result-type;
        description
          "Result of system software signature check.";
      }
      leaf crc-result {
        type driver-check-result-type;
        description
          "Result of system software CRC check.";
      }
      leaf match-result {
        type driver-check-result-type;
        description
          "Result of system software match check.";
      }
    }
  }

  rpc check-hardware-version {
    description
      "Check whether the system software package version matches the software versions, such as the EPLD and CANBUS version, running on the hardware.";
    input {
      leaf chassis-id {
        type string {
          length "1..32";
        }
        description
          "Chassis ID of device.";
      }
      choice check-type {
        mandatory true;
        description
          "Choose startup or file.";
        case startup-package {
          description
            "Startup.";
          leaf startup {
            type empty;
            description
              "The startup file.";
          }
        }
        case package-file {
          description
            "Packet file name.";
          leaf file-name {
            type string {
              length "4..127";
            }
            description
              "Packet file name in master MPU.";
          }
        }
      }
    }
    output {
      leaf signature-result {
        type driver-check-result-type;
          description
            "Result of system software signature check.";
      }
      leaf match-result {
        type driver-check-result-type;
          description
            "Result of system software version check.";
      }
      container version-infos {
        description
          "List of version information.";
        list version-info {
          key "slot";
          description
            "Information of version.";
          leaf slot {
            type string {
              length "1..32";
            }
            description
              "Slot ID of device.";
          }
          leaf hardware-type {
            type driver-slot-infos-type;
            description
              "Hardware type.";
          }
          leaf content {
            type driver-hardware-version-type;
            description
              "Content of system software.";
          }
          leaf current-version {
            type string {
              length "1..15";
            }
            description
              "Current version.";
          }
          leaf package-version {
            type string {
              length "1..15";
            }
            description
              "Package version.";
          }
          leaf compatibility-state {
            type driver-compatibility-state-type;
            description
              "Compatibility state of system software.";
          }
          leaf upgrade-suggestion {
            type driver-upgrade-suggestion-type;
            description
              "Upgrade suggestion.";
          }
        }
      }
    }
  }

  rpc clear-nv-port-bip8-err-alarm {
    ext:node-ref "/devm:devm/devm:ports/devm:port";
    description
      "Clear nv bip error alarm.";
    input  {
      leaf if-name {
        type leafref {
          path "/ifm:ifm/ifm:interfaces/ifm:interface/ifm:name";
        }
        description
          "Remote port index.";
      }
    }
  }
  rpc clear-nv-port-crc-err-alarm {
    ext:node-ref "/devm:devm/devm:ports/devm:port";
    description
      "Clear nv crc error alarm.";
    input  {
      leaf if-name {
        type leafref {
          path "/ifm:ifm/ifm:interfaces/ifm:interface/ifm:name";
        }
        description
          "Remote port index.";
      }
    }
  }
  rpc clear-nv-port-input-err-alarm {
    ext:node-ref "/devm:devm/devm:ports/devm:port";
    description
      "Clear nv input error alarm.";
    input  {
      leaf if-name {
        type leafref {
          path "/ifm:ifm/ifm:interfaces/ifm:interface/ifm:name";
        }
        description
          "Remote port index.";
      }
    }
  }
  rpc clear-nv-port-output-err-alarm {
    ext:node-ref "/devm:devm/devm:ports/devm:port";
    description
      "Clear nv output error alarm.";
    input  {
      leaf if-name {
        type leafref {
          path "/ifm:ifm/ifm:interfaces/ifm:interface/ifm:name";
        }
        description
          "Remote port index.";
      }
    }
  }
  rpc clear-nv-port-sdh-err-alarm {
    ext:node-ref "/devm:devm/devm:ports/devm:port";
    description
      "Clear nv sdh error alarm.";
    input  {
      leaf if-name {
        type leafref {
          path "/ifm:ifm/ifm:interfaces/ifm:interface/ifm:name";
        }
        description
          "Remote port index.";
      }
    }
  }
  rpc clear-nv-port-symbol-err-alarm {
    ext:node-ref "/devm:devm/devm:ports/devm:port";
    description
      "Clear nv symbol error alarm.";
    input  {
      leaf if-name {
        type leafref {
          path "/ifm:ifm/ifm:interfaces/ifm:interface/ifm:name";
        }
        description
          "Remote port index.";
      }
    }
  }
  rpc clear-nv-port-trans-alarm {
    ext:node-ref "/devm:devm/devm:ports/devm:port";
    description
      "Clear remote port tad alarm information.";
    input  {
      leaf if-name {
        type leafref {
          path "/ifm:ifm/ifm:interfaces/ifm:interface/ifm:name";
        }
        description
          "Remote port index.";
      }
    }
  }
  rpc clear-nv-port-tx-pause-err-alarm {
    ext:node-ref "/devm:devm/devm:ports/devm:port";
    description
      "Clear nv txpause error alarm.";
    input  {
      leaf if-name {
        type leafref {
          path "/ifm:ifm/ifm:interfaces/ifm:interface/ifm:name";
        }
        description
          "Remote port index.";
      }
    }
  }
  rpc clear-port-bip8-err-alarm {
    ext:node-ref "/devm:devm/devm:ports/devm:port";
    description
      "Clear bip error alarm.";
    input  {
      leaf port-position {
        type leafref {
          path "/devm:devm/devm:ports/devm:port/devm:position";
        }
        description
          "Port position.";
      }
    }
  }
  rpc clear-port-tx-pause-err-alarm {
    ext:node-ref "/devm:devm/devm:ports/devm:port";
    description
      "Clear txPause error alarm.";
    input  {
      leaf port-position {
        type leafref {
          path "/devm:devm/devm:ports/devm:port/devm:position";
        }
        description
          "Port position.";
      }
    }
  }
  rpc set-nv-laser-turn {
    ext:node-ref "/devm:devm/devm:ports/devm:port";
    description
      "Set port nv laser.";
    input  {
      leaf if-name {
        type leafref {
          path "/ifm:ifm/ifm:interfaces/ifm:interface/ifm:name";
        }
        description
          "Remote port index.";
      }
      leaf laser-shutdown {
        type enumeration {
          enum "on" {
            value 0;
            description
              "Laser open.";
          }
          enum "off" {
            value 1;
            description
              "Laser close.";
          }
        }
        default "on";
        description
          "Laser open or shut.";
      }
      leaf laser-test-time {
        type uint32 {
          range "200..30000";
        }
        description
          "Laser open time(10ms).";
      }
    }
  }
  
  rpc check-lcm-channel {
    description
      "Check lcm channel.";
    output {
      container check-lcm-channel-slots {
        description
          "List of checking results of channels on slots.";
        list check-lcm-channel-slot {
          key "channel-type slot interface-name link-slot link-interface-name";
          description
            "The checking result of channels on slot.";
          leaf channel-type {
            type enumeration {
              enum "channels-in-single" {
                value 0;
                description
                  "Channels in single.";
              }
              enum "channels-in-clc" {
                value 1;
                description
                  "Channels in CLC.";
              }
              enum "channels-in-ccc" {
                value 2;
                description
                  "Channels in CCC.";
              }
              enum "channels-between-chassises" {
                value 3;
                description
                  "Channels between Chassises.";
              }
              enum "escape-channels" {
                value 4;
                description
                  "Escape channels.";
              }
              enum "fast-switchover-channels" {
                value 5;
                description
                  "Fast switchover channels.";
              }
            }
            description
              "Channel type.";
          }
          leaf slot {
            type string {
              length "1..31";
            }
            description
              "Slot.";
          }
          leaf interface-name {
            type string {
              length "1..31";
            }
            description
              "Interface name.";
          }
          leaf link-slot {
            type string {
              length "1..31";
            }
            description
              "Link slot.";
          }
          leaf link-interface-name {
            type string {
              length "1..31";
            }
            description
              "Link interface name.";
          }
          leaf product-type {
            type string {
              length "1..31";
            }
            description
              "Product type.";
          }
          leaf channel-status {
            type string {
              length "1..31";
            }
            description
              "Channel status.";
          }
        }
      }
    }
  }
   rpc check-virtual-cables {
    description
      "Checks the cable connection of the Ethernet port and displays the test result.";
    input  {
      leaf port-position {
        type leafref {
          path "/devm:devm/devm:ports/devm:port/devm:position";
        }
        description
          "Port position.";
      }
    }
    output {
      container cable-results {
        description
          "List of checking results of cables on the interface.";
        list cable-result {
          key "name";
          description
            "Operational state of cable.";
          leaf name {
            type string {
              length "1..32";
            }
            description
              "Cable name.";
          }
          leaf state {
            type enumeration {
              enum "ok" {
                value 0;
                description
                  "Cable state ok.";
              }
              enum "open" {
                value 1;
                description
                  "Cable state open.";
              }
              enum "short" {
                value 2;
                description
                  "Cable state short.";
              }
              enum "crosstalk" {
                value 3;
                description
                  "Cable state crosstalk.";
              }
              enum "unknown" {
                value 4;
                description
                  "Cable state unknown.";
              }
            }
            description
              "Cable state.";
          }
          leaf length {
            type string {
              length "1..32";
            }
            units "m";
            description
              "Cable length.";
          }
        }
      }
    }
  }
  rpc multi-level-alarm-boolean {
    description
      "Multi level alarm boolean output.";
    input {
      leaf operation-flag {
        type driver-operation-flag;
        mandatory true;
        description
          "Operation flag (which includes disable, enable).";
      }
      leaf slot {
        type string {
          length "1..31";
        }
        mandatory true;
        description
          "The available slot. The slot is expressed in the format of slotID. For example, 1. Here 1 is an example. The value may vary with devices.";
      }
      leaf index {
        type string {
          length "1..31";
        }
        mandatory true;
        description
          "Index id. The index is expressed in the format of a number. For example, 1. Here 1 is an example. The value may vary with devices.";
      }
      leaf relation {
        type driver-relation-type;
        must "(../operation-flag='enable' and ../relation) or (../operation-flag='disable' and not(../relation))";
        description
          "Relation.";
      }
      leaf alarm-level {
        type driver-alarm-level-type;
        must "(../operation-flag='enable' and ../alarm-level) or (../operation-flag='disable' and not(../alarm-level))";
        description
          "Alarm level.";
      }
    }
  }
  
  rpc sysmac-load {
    description
      "Loads MAC addresses assigned to multiple VSs.";
    input {
      leaf sysmac-file {
        type string {
          length "1..32";
        }
        mandatory true;
        description
          "The MAC address file for loading. For example, sysmac.txt.";
      }
      leaf slot-id {
        type string {
          length "1..32";
        }
        mandatory true;
        description
          "Slot ID. The slot ID is expressed in the format of slot ID. For example, 1. Here 1 is an example. The value may vary with devices.";
      }
      leaf chassis-id {
        type uint32 {
          range "1..2";
        }
        description
          "Chassis ID. The chassis ID is expressed in the format of chassis ID. For example, 1. Here 1 is an example. The value may vary with devices.";
      }
    }
  }
  
  rpc set-next-system-mode {
    description
      "Set next system mode.";
    input {
      leaf next-system-mode {
        type driver-system-mode-type;
        description
          "Set next system mode.";
        }
    }
  }
  
  rpc set-next-run-mode {
    ext:node-ref "/devm:devm/devm:chassiss/devm:chassis";
    description
      "Set chassis run mode, set a chassis operating mode to be used at the next startup (warning:system will restart after success, and then take effect).";
    input {
      leaf chassis-id {
        type string {
          length "1..31";
        }
        description
          "Chassis ID.";
      }
      leaf next-run-mode {
        type driver-run-mode-type;
        description
          "Next run mode.";
      }
    }
  }
  
    rpc set-next-chassis-id {
    ext:node-ref "/devm:devm/devm:chassiss/devm:chassis";
    description
      "Set next chassis ID, set a chassis ID to be used at the next startup (warning:system will restart after success, and then take effect).";
    input {
      leaf chassis-id {
        type string {
          length "1..31";
        }
        description
          "Chassis ID.";
      }
      leaf next-chassis-id {
        type uint32 {
          range "1..8";
        }
        description
          "Next chassis ID.";
      }
    }
   }
   rpc reboot-with-factory-configuration {
   description
      "Configure the device to restore factory settings after restart.";
   }
   rpc offline-disk {
     description
       "Offline disk.";
     input {
       leaf position {
         type string {
           length "1..32";
         }
         mandatory true;
         description
           "Disk Position. The board-position is expressed in the format of slotID. For example, 1. Here 1 is an example. The value may vary with devices.";
       }
     }
   }
   rpc online-disk {
     description
       "Online disk.";
     input {
       leaf position {
         type string {
           length "1..32";
         }
         mandatory true;
         description
           "Disk Position. The board-position is expressed in the format of slotID. For example, 1. Here 1 is an example. The value may vary with devices.";
       }
     }
   }

  rpc set-dcn-management-plane-lock {
    description
      "Set dcn-management-plane locked status.";
    input {
      leaf lock-status {
        type driver-lock-state-type;
        mandatory true;
        description
          "Locked status.";
      }
    }
  }

  rpc set-power-pm-input-mode {
    description
      "Set pm input mode.";
    input {
      leaf chassis-id {
        type string {
          length "1..31";
        }
        description
          "Chassis ID.";
      }
      leaf pm-input-mode {
        type set-pm-input-mode-type;
        mandatory true;
        description
          "Pm input mode.";
      }
    }
  }

  rpc refresh-power-pm-input {
    description
      "Refresh pm input.";
    input {
      leaf chassis-id {
        type string {
          length "1..31";
        }
        description
          "Chassis ID.";
      }
    }
  }

  rpc set-led {
    description
      "Set device LED status.";
    input {
      leaf position {
        type string {
          length "1..32";
        }
        description
          "Device position.";
      }
      leaf type {
        type device-type;
        description
          "Device type.";
      }
      leaf status {
        type led-status-type;
        default "dim";
        description
          "Device LED status.";
      }
    }
  }

  rpc set-next-fiber-connect-mode {
    description
      "Set next fiber connect mode.";
    input {
      leaf next-fiber-connect-mode {
        type driver-fiber-connect-mode;
        description
          "Next fiber connect mode.";
      }
    }
  }
  rpc set-service-forward-ability {
    description
      "Set service forward ability (warning:system may restart after success, and then take effect).";
    input {
      leaf service-forward-ability {
        type service-forward-ability-type;
        mandatory true;
        description
          "Service-forward ability.";
      }
    }
  }
  rpc reset-cmu-switch-fog {
    description
    "Reset the fog sensor.";
    input {
      leaf cmu-switch-fog {
        type empty;
        description
          "Cmu switch fog sensor.";
      }
    }
  }
    augment "/devm:devm/devm:chassiss/devm:chassis" {
      description
        "Adds driver configuration to devm model.";
      container fan-attribute {
        must "((./workmode='manual' or ./workmode='minimum-percent') and ./speed) or ((./workmode!='manual' and ./workmode!='minimum-percent') and not(./speed))";
        description
          "Configure the working mode and speed of the fan. You can set the fan speed adjustment mode based on the number of working boards that a device requires.";
        leaf workmode {
          type fan-workmode;
          default "auto";
          description
              "Fan working mode.";
        }
        leaf speed {
          ext:dynamic-default;
          type uint32 {
              range "0..100";
          }
          units "%";
          description
            "Fan speed which is a percentage of the highest speed and the range of value changes with the workmode and the hardtype of fan. The current range is determined by combining the minimum and maximum values of all cases.";
        }
        container area-fan-attributes {
          description
            "List of fan speed information about an area.";
          list area-fan-attribute {
            ext:generated-by system;
            ext:operation-exclude create;
            key "area-id";
            description
              "Configure fan speed information about an area.";
            leaf area-id {
              type uint32 {
                range "1..3";
              }
              description
                "Fan area ID.";
            }
            leaf area-speed {
              ext:dynamic-default;
              type uint32 {
                range "30..100";
              }
              units "%";
              must "(../../../workmode='manual' or ../../../workmode='full')";
              description
                "Fan speed in the area.";
            }
          }
        }
      }
      
      container power-supply-attribute {
        description
          "Configure power supply information.";
        leaf pm-output-limit {
          type uint32 {
            range "0..4294967295";
          }
          units "W";
          default "0";
          description
            "PM output limited value. The value range of this parameter is dynamically determined by the rated power, used power, and number of PMs.";
        }
        leaf pm-input-voltage-110 {
          type driver-bool;
          ext:dynamic-default;
          description
            "Set pm input voltage 110V. The input voltage 110V mode of the PM can be set only when the power supply type is PHD-3000W or PAC-2700W or PAH-3000W.";
        }
        leaf power-supply-mode {
          type pwr-supply-mode-type;
          default "standard";
          description
            "Power supply mode.";
        }
        leaf power-supply-input {
          when "../power-supply-mode='assign'";
          type uint32 {
            range "0..11200";
          }
          units "W";
          description
            "Power supply input power. The value range of this parameter is dynamically determined by the rated power, used power, and number of power supply partitions.";
        }
        leaf power-supply-temp {
          when "../power-supply-mode='standard'";
          type pwr-supply-temp-type;
          default "temphigh";
          description
            "Chassis Working Temperature. Some temperature modes are not supported on specific device models or in specific scenarios.";
        }
        leaf power-redundant-mode {
          type pwr-redundant-mode-type;
          default "module";
          description
            "Power supply redundancy mode.";
        }
        leaf power-supply-limit {
          type uint32;
          units "W";
          config false;
          description
            "Limit Power.";
        }
        leaf power-supply-alarm-limit {
          type uint32;
          units "W";
          config false;
          description
            "Alarm Limit Power.";
        }
        leaf power-supply-assigned {
          type uint32;
          units "W";
          default "0";
          config false;
          description
            "Assigned Power.";
        }
        leaf power-supply-assigned-utility {
          type string {
            length "1..255";
          }
          default "0";
          config false;
          description
            "Assigned Power Utility.";
        }
        leaf power-supply-left {
          type int32;
          units "W";
          default "0";
          config false;
          description
            "Left Power.";
        }
        leaf power-supply-real {
          type uint32;
          units "W";
          config false;
          description
            "Real Power.";
        }
        leaf power-supply-real-utility {
          type string {
            length "1..255";
          }
          default "0";
          config false;
          description
            "Real Power Utility.";
        }
        leaf current-power-consumption {
          type string {
            length "1..255";
          }
          units "W";
          config false;
          description
            "Current power consumption.";
        }
        leaf average-power-consumption {
          type string {
            length "1..255";
          }
          units "W";
          config false;
          description
            "Average power consumption.";
        }
        leaf power-supply-average {
          type uint32;
          units "W";
          config false;
          description
            "Average instantaneous power consumption in a period of time.";
        }
        leaf power-supply-others {
          type uint32;
          units "W";
          config false;
          description
            "Accumulated rated power consumption of devices with low power consumption, such as the CMU, PMU, LCD, fan, and power board.";
        }
      }
      container dustproof-attribute {
        description
          "Configure the state of checking dustproof gate.";
        leaf dustproofcheck {
          type dustproof-gate-state;
          default "enable";
          description
              "The state of checking dustproof gate.";
        }
        leaf dustproof-delay-time {
          type uint32{
            range "0..480";
          }
          units "min";
          default "30";
          description
              "The alarm delay time of checking dustproof gate.";
        }
      }
        container chassis-id {
        config false;
        description
          "Statistics of chassis ID.";
        leaf current-id {
          type uint32 {
            range "1..8";
          }	  
          description
            "Current chassis ID.";
        }
        leaf next-id {
          type uint32 {
            range "1..8";
          }
          description
            "Chassis ID to be used at the next startup.";
        }
      }  
      container chassis-run-mode {
        config false;
        description
          "Statistics of chassis run mode.";
        leaf current-run-mode {
          type driver-run-mode-type;
          description
            "Current chassis operating mode.";
        }
        leaf next-run-mode {
          type driver-run-mode-type;
          description
            "Chassis operating mode to be used at the next startup.";
        }
      }

      container chassis-sfu-mode {
        description
          "Configure SFU mode.";
        leaf current-sfu-mode {
          type sfu-mode-type;
          config false;
          description
            "Current SFU mode.";
        }
        leaf next-sfu-mode {
          type sfu-mode-type;
          default "four-sfu";
          description
            "Next SFU mode.";
        }
      }
      container pm-input-attribute {
        description
          "Configure pm input information.";
        leaf pm-input-mode {
          type get-pm-input-mode-type;
          config false;
          description
            "Pm input mode.";
        }
        leaf pm-auto-balance {
          type driver-entity-bool;
          default "disable";
          description
            "Pm auto balance.";
        }
        leaf pm-auto-balance-status {
          type driver-entity-bool;
          config false;
          description
            "Pm auto balance effective status.";
        }        
      }
      container temperature-attribute {
        description
          "Configure temperature change monitoring.";
        leaf temp-change-enable {
          type driver-bool;
          default "no";
          description
            "Temperature change monitoring enable.";
        }
      }
    }

    augment "/devm:devm/devm:mpu-boards/devm:mpu-board" {
      description
        "Adds driver configuration to devm model.";
      container boot-status {
        config false;
        description
          "Statistics of boot password status of MPUs.";
        leaf boot-password-status {
          type enumeration {
            enum "unset" {
              value 0;
              description
                "Boot password unset.";
            }
            enum "set" {
              value 1;
              description
                "Boot password set.";
            }
          }
          config false;
          description
            "Boot password status.";
        }
      }
    }

    augment "/devm:devm/devm:lpu-boards/devm:lpu-board" {
      description
        "Adds driver configuration to devm model.";
      container driver {
        config false;
        description
          "Statistics of driver apply."; 
          container l3-clocks {
            config false;
            description
              "List of l3 clocks.";
            list l3-clock {
              key "clock-id";
              config false;
              description
                "Statistics of l3 clock.";
              leaf clock-id {
                type string {
                  length "1..255";
                }
                config false;
                description
                  "L3 clock ID. The clock-id is expressed in the format of slotID. For example, 1. Here 1 is an example. The value may vary with devices.";
              }
              leaf l3-clock-state {
                type driver-clock-status;
                config false;
                description
                  "L3 clock state.";
              }
            }
          }
       }
    }
  
  augment "/devm:devm" {
   description
     "Adds driver configuration to devm model.";
   container driver {
     description
       "Configure driver apply."; 
    container cmus {
      description
        "List of CMUs.";
      list cmu {
        ext:generated-by system;
        key "position";
        description
          "Configure CMU.";
        leaf position {
          type string {
            length "1..32";
          }
          description
            "CMU position. The position is expressed in the format of slotID. For example, 1. Here 1 is an example. The value may vary with devices.";
        }
        leaf entity-index {
          type uint32;
          config false;
          description
            "CMU supply index.";
        }
        leaf board-type {
          type string {
            length "1..32";
          }
          config false;
          description
            "Type of a CMU board.";
        }
        leaf sdram-size {
          type uint32;
          units "MB";
          config false;
          description
            "SDRAM size.";
        }
        leaf flash-size {
          type uint32;
          units "MB";
          config false;
          description
            "Flash size.";
        }
        leaf up-time {
          type pub-type:time-tick;
          config false;
          description
            "Up time of an CMU, the unit is timetick.";
        }
        leaf role {
          type driver-cmu-role;
          config false;
          description
            "CMU role.";
         }
        container switchs {
          description
            "List of CMU Switch.";
          list switch {
            key "switch-id";
            description
              "Configure the ID, name and alarm type for the switch parameter monitored by the environment monitoring unit.";
            leaf switch-id {
              type uint32 {
                range "0..6";
              }
              description
                "Cmu Switch ID.";
            }
            leaf switch-name {
              type string {
                length "1..24";
              }
              mandatory true;
              description
                "Specify cmu switch name.";
            }
            leaf alarm-triggering-mode {
              type driver-switch-alarm-triggering-mode;
              mandatory true;
              description
                "Specify cmu alarm-triggering-mode.";
            }
            leaf sensor-name {
              when "../switch-id='0'";
              type driver-sensor-name;
              description
                "Specify cmu sensor.";
            }
          }
        }
        container relays {
          description
            "List of CMU Relays.";
          list relay {
            key "relay-id";
            description
              "Configure the ID and name for the external relay of a CMU. The external relay is used to control an external device.";
            leaf relay-id {
              type uint32 {
                range "0..1";
              }
              description
                "Specify the ID of the external relay of a CMU.";
            }
            leaf relay-name {
              type string {
                length "1..24";
              }
              mandatory true;
              description
                "Specify the name of the external relay of a CMU.";
            }
            leaf relay-mode {
              type driver-relay-mode;
              mandatory true;
              description
                "Specify the relay-mode of the external relay of a CMU.";
            }
          }
        }
        container analogs {
          description
            "List of CMU Analogs.";
          list analog {
            must "((lower-alarm-threshold<lower-limit) and (lower-limit<nominal-value) and (nominal-value<upper-limit) and (upper-limit<high-alarm-threshold))";
            key "analog-id";
            description
              "Configure CMU Analog.";
            leaf analog-id {
              type uint32 {
                range "0..1";
              }
              description
                "Specifies the ID of the input analog of a CMU.";
            }
            leaf analog-name {
              type string {
                length "1..24";
              }
              mandatory true;
              description
                "Specifies the name of the input analog of a CMU.";
            }
            leaf analog-object {
              type driver-analog-object-type;
              mandatory true;
              description
                "Specify object monitored by this cmu analog sensor.";
            }
            leaf analog-sensor-type {
              type driver-analog-type;
              mandatory true;
              description
                "Specify cmu analog sensor type.";
            }
            leaf lower-limit {
              type int32 {
                range "0..10";
              }
              mandatory true;
              description
                "Specify cmu analog work lower limit.";
            }
            leaf upper-limit {
              type int32 {
                range "0..10";
              }
              mandatory true;
              description
                "Specify cmu analog work upper limit.";
            }
            leaf nominal-value {
              type int32 {
                range "0..10";
              }
              mandatory true;
              description
                "Specify cmu analog input nominal value.";
            }
            leaf lower-alarm-threshold {
              type int32 {
                range "0..10";
              }
              mandatory true;
              description
                "Specify cmu analog lower alarm threshold.";
            }
            leaf high-alarm-threshold {
              type int32 {
                range "0..10";
              }
              mandatory true;
              description
                "Specify cmu analog high alarm threshold.";
            }
          }
        }
        container alarm-output {
          description
            "Configure CMU alarm output.";
          leaf major-relay-output-enable {
            type empty;
            description
              "Major relay output enable.";
          }
          leaf minor-relay-output-enable {
            type empty;
            description
              "Minor relay output enable.";
          }
        }
      }
    }
    
    container pms {
      description
        "List of PM.";
      list pm {
        ext:generated-by system;
        ext:operation-exclude create;
        key "position serial-number";
        description
          "Configure PM.";
        leaf position {
          type string {
            length "1..32";
          }
          description
            "PM position. The position is expressed in the format of slotID/pmID. For example, 1/1. Here 1/1 is an example. The value may vary with devices.";
        }
        leaf serial-number {
          type uint32;
          description
            "Serial Number.";
        }
        leaf single-input {
          type driver-single-input-type;
          default "NA";
          description
            "Set Single Input. The power supply management mode can be switched only when DC power supply is used.";
        }
        leaf board-type {
          type string {
            length "1..32";
          }
          config false;
          description
            "Type of a PM board.";
        }
        leaf entity-index {
          type uint32;
          config false;
          description
            "PM index.";
        }
        leaf monitor-cable-state {
          type driver-cable-state;
          config false;
          description
            "State of a PM monitor cable.";
        }
        leaf input-voltage-value {
          type string {
            length "1..255";
          }
          units "V";
          config false;
          description
            "Input voltage value.";
        }
        leaf input-electrical-value {
          type string {
            length "1..255";
          }
          units "A";
          config false;
          description
            "Input electrical value.";
        }
        leaf input-power-value {
          type string {
            length "1..255";
          }
          units "W";
          config false;
          description
            "Input power.";
        }
        leaf output-voltage-value {
          type string {
            length "1..255";
          }
          units "V";
          config false;
          description
            "Output voltage value.";
        }
        leaf output-electrical-value {
          type string {
            length "1..255";
          }
          units "A";
          config false;
          description
            "Output electrical value.";
        }
        leaf output-power-value {
          type string {
            length "1..255";
          }
          units "W";
          config false;
          description
            "Output power.";
        }
        leaf pm-area {
          type string {
            length "1..16";
          }
          config false;
          description
            "PM area.";
        }
        leaf pm-status {
          type driver-pm-status;
          config false;
          description
            "PM Status Information.";
        }
      }
    }
    
    container ccus {
      config false;
      description
        "Statistics of CCU information.";
      container ccu {
      presence "ccu";
        config false;
        description
          "Statistics of CCU information.";
        leaf software-version {
          type string {
            length "1..32";
          }
          config false;
          description
            "CCU version.";
        }
      }
    }
    
    container dacss {
      config false;
      description
        "List of DACS.";
      list dacs {
        key "position serial-number";
        config false;
        description
          "Statistics of DACS.";
        leaf position {
          type string {
            length "1..32";
          }
          config false;
          description
            "DACS position. The position is expressed in the format of slotID. For example, PDU1. Here PDU1 is an example. The value may vary with devices.";
        }
        leaf serial-number {
          type uint32;
          config false;
          description
            "Serial Number.";
        }
        leaf board-type {
          type string {
            length "1..32";
          }
          config false;
          description
            "Type of a DACS board.";
        }
        leaf dacs-area {
          type string {
            length "1..16";
          }
          config false;
          description
            "DACS area.";
        }
        leaf entity-index {
          type uint32;
          config false;
          description
            "DACS index.";
        }
        leaf status {
          type driver-dacs-status;
          config false;
          description
            "State of a DACS monitor.";
        }
        leaf insource-plane {
          type string {
            length "1..255";
          }
          config false;
          description
            "InSource plane.";
        }
        leaf insource-plane-a {
          type string {
            length "1..255";
          }
          config false;
          description
            "InSource A plane value (A).";
        }
        leaf insource-plane-b {
          type string {
            length "1..255";
          }
          config false;
          description
            "InSource B plane value (B).";
        }
        leaf output-voltage-value {
          type string {
            length "1..255";
          }
          config false;
          description
            "Output voltage value (V).";
        }
        leaf output-electrical-value {
          type string {
            length "1..255";
          }
          config false;
          description
            "Output electrical value (A).";
        }
        leaf output-status {
          type string {
            length "1..255";
          }
          config false;
          description
            "Output Status.";
        }
      }
    }
    
    container ecus {
      config false;
      description
        "List of ECU boards.";
      list ecu {
        key "position";
        config false;
        description
          "Statistics of ECU board.";
        leaf position {
          type string {
            length "1..32";
          }
          config false;
          description
            "The position is expressed in the format of slotID. For example, 1. Here 1 is an example. The value may vary with devices.";
        }
        leaf entity-index {
          type uint32;
          config false;
          description
            "ECU index.";
        }
        leaf board-type {
          type string {
            length "1..32";
          }
          config false;
          mandatory true;
          description
            "ECU type.";
        }
        leaf sdram-size {
          type uint32;
          units "MB";
          config false;
          description
            "SDRAM size.";
        }
        leaf flash-size {
          type uint32;
          units "MB";
          config false;
          description
            "Flash size.";
        }
        leaf up-time {
          type pub-type:time-tick;
          config false;
          description
            "Up time of an ECU, the unit is timetick.";
        }
        leaf ofc-card-number {
          type uint32;
          config false;
          description
            "Number of OFC cards.";
        }
        leaf subcard-slot-number {
          type uint32;
          config false;
          description
            "Number of slots on a subcard.";
        }
      }
    }
    
    container fans {
      config false;
      description
        "List of information about all fans on a device.";
      list fan {
        key "position";
        config false;
        description
          "Statistics of fan information on a device.";
        leaf position {
          type string {
            length "1..50";
          }
          config false;
          description
            "Position of the fan board. The position is expressed in the format of slotID. For example, 1. Here 1 is an example. The value may vary with devices.";
        }
        leaf area-id {
          type uint32 {
            range "1..3";
          }
          config false;
          description
            "Fan area ID.";
        }
        leaf entity-index {
          type uint32;
          config false;
          description
            "Index of the fan board.";
        }
        leaf board-type {
          type string {
            length "1..32";
          }
          config false;
          description
            "Type of a fan board.";
        }
        leaf work-mode {
          type fan-workmode;
          default "auto";
          config false;
          description
            "Working mode of a fan.";
        }
        leaf speed {
          type uint32 {
            range "0..100";
          }
          units "%";
          config false;
          description
            "Fan speed, which is the highest percentage of the fan speed.";
        }
        leaf fan-rate {
          type uint32;
          units "r/min";
          config false;
          description
            "Rated rotational speed of the fan.";
        }
        leaf monitor-cable-state {
          type driver-cable-state;
          config false;
          description
            "Monitors the fan status.";
        }
        leaf register {
          type driver-bool;
          config false;
          description
            "Whether the fan is registered.";
        }
        leaf present {
          type driver-bool;
          config false;
          description
            "Check whether the fan is in position.";
        }
        leaf fan-number {
          type uint32;
          config false;
          description
            "Number of fans.";
        }
        leaf global-speed {
          type string {
            length "1..128";
          }
          units "%";
          default "NA";
          config false;
          description
            "Fan speed percentage, which is the percentage of the maximum rate.";
        }
        leaf running-status {
          type driver-fan-status;
          config false;
          description
            "Fan running status.";
        }
        container sub-fans {
          config false;
          description
            "List of sub fan speed information.";
          list sub-fan {
            key "index";
            description
              "Statistics of fan speed information.";
            leaf index {
              type uint32;
              description
                "Index of sub fan.";
            }
            leaf real-speed {
              type string {
                length "1..128";
              }
              units "r/min";
              description
                "Actual sub fan speed.";
            }
          }
        }
      }
    }
    
    container icus {
      config false;
      description
        "List of ICUs.";
      list icu {
        key "position";
        config false;
        description
          "Statistics of ICU board.";
        leaf position {
          type string {
            length "1..32";
          }
          config false;
          description
            "ICU position. The position is expressed in the format of slotID. For example, 1. Here 1 is an example. The value may vary with devices.";
        }
        leaf entity-index {
          type uint32;
          config false;
          description
            "ICU index.";
        }
        leaf board-type {
          type string {
            length "1..32";
          }
          config false;
          mandatory true;
          description
            "ICU type.";
        }
        leaf sdram-size {
          type uint32;
          units "MB";
          config false;
          description
            "SDRAM size.";
        }
        leaf flash-size {
          type uint32;
          units "MB";
          config false;
          description
            "Flash size.";
        }
        leaf up-time {
          type pub-type:time-tick;
          config false;
          description
            "Up time of an ICU, the unit is timetick.";
        }
      }
    } 

    container lcds {
      config false;
      description
        "List of LCDs.";
      list lcd {
        key "position";
        config false;
        description
          "Statistics of LCD.";
        leaf position {
          type string {
            length "1..32";
          }
          config false;
          description
            "Lcd position. The position is expressed in the format of slotID. For example, 1. Here 1 is an example. The value may vary with devices.";
        }
        leaf entity-index {
          type uint32;
          config false;
          description
            "Lcd supply index.";
        }
        leaf board-type {
          type string {
            length "1..32";
          }
          config false;
          description
            "Type of a LCD board.";
        }
      }
    }
    
    container pmus {
      config false;
      description
        "List of PMU.";
      list pmu {
        key "position";
        config false;
        description
          "Statistics of PMU.";
        leaf position {
          type string {
            length "1..32";
          }
          config false;
          description
            "PMU position. The position is expressed in the format of slotID. For example, 1. Here 1 is an example. The value may vary with devices.";
        }
        leaf entity-index {
          type uint32;
          config false;
          description
            "PMU index.";
        }
        leaf board-type {
          type string {
            length "1..32";
          }
          config false;
          description
            "Type of a PMU board.";
        }
        leaf present {
          type string {
            length "1..16";
          }
          config false;
          description
            "Present.";
        }
        leaf ha-status {
          type string {
            length "1..16";
          }
          config false;
          description
            "HaStatus.";
        }
        leaf register {
          type string {
            length "1..16";
          }
          config false;
          description
            "Register.";
        }
        leaf work {
          type string {
            length "1..16";
          }
          config false;
          description
            "Work.";
        }
      }
    }    
    
    container power-supplys {
      config false;
      description
        "List of information about all power supplies on a device.";
      list power-supply {
        key "position";
        config false;
        description
          "Statistics of power supply information on a device.";
        leaf position {
          type string {
            length "1..50";
          }
          config false;
          description
            "Position of the power supply. The position is expressed in the format of slotID. For example, 1. Here 1 is an example. The value may vary with devices.";
        }
        leaf entity-index {
          type uint32;
          config false;
          description
            "Index of the power supply.";
        }
        leaf board-type {
          type string {
            length "1..32";
          }
          config false;
          description
            "Hardware type of the power supply.";
        }
        leaf work-mode {
          type driver-power-work-mode;
          config false;
          description
            "Working mode of a power supply board.";
        }
        leaf monitor-cable-state {
          type driver-cable-state;
          config false;
          description
            "Status of the power monitoring point.";
        }
        leaf power-state {
          type string {
            length "1..255";
          }
          config false;
          description
            "Working mode of the power supply.";
        }
        leaf abnormal-number {
          type uint32;
          config false;
          description
            "Number of faulty power modules on a device.";
        }
        leaf normal-number {
          type uint32;
          config false;
          description
            "Number of normal power modules on a device.";
        }
        container power-environments {
          config false;
          description
            "List of environment information about the power supply on a device.";
          list power-environment {
            key "pem-index";
            config false;
            description
              "Statistics of environment information about the power supply on a device.";
            leaf pem-index {
              type uint32;
              config false;
              description
                "Index of the power supply.";
            }
            leaf voltage-value {
              type string {
                length "1..255";
              }
              units "V";
              config false;
              description
                "Current input voltage value of an existing device.";
            }
            leaf electrical-value {
              type string {
                length "1..255";
              }
              units "A";
              config false;
              description
                "Current input electrical value of an existing device.";
            }
            leaf temperature-value {
              type string {
                length "1..255";
              }
              config false;
              description
                "Temperature of an existing device.";
            }
            leaf power-value {
              type string {
                length "1..255";
              }
              units "W";
              config false;
              description
                "Query the current power.";
            }
            leaf out-voltage-value {
              type string {
                length "1..255";
              }
              units "V";
              config false;
              description
                "Current output voltage value of an existing device.";
            }
            leaf out-electrical-value {
              type string {
                length "1..255";
              }
              units "A";
              config false;
              description
                "Current output electrical value of an existing device.";
            }
            leaf out-power-value {
              type string {
                length "1..255";
              }
              units "W";
              config false;
              description
                "Current output power value of an existing device.";
            }
          }
        }
      }
    }

    container dmus {
      config false;
      description
        "List of DMU.";
      list dmu {
        key "position";
        config false;
        description
          "Statistics of DMU.";
        leaf position {
          type string {
            length "1..32";
          }
          description
            "DMU position. The position is expressed in the format of slotID. For example, PDU1. Here PDU1 is an example. The value may vary with devices.";
        }
        leaf entity-index {
          type uint32;
          description
            "DMU index.";
        }
        leaf board-type {
          type string {
            length "1..32";
          }
          description
            "Type of a DMU board.";
        }
        leaf present {
          type string {
            length "1..16";
          }
          description
            "Present.";
        }
        leaf register {
          type string {
            length "1..16";
          }
          description
            "Register.";
        }
        leaf work {
          type string {
            length "1..16";
          }
          description
            "Work.";
        }
      }
    }

    container pdus {
      config false;
      description
        "List of PDU.";
      list pdu {
        key "position";
        config false;
        description
          "Statistics of PDU.";
        leaf position {
          type string {
            length "1..32";
          }
          description
            "PDU position. The position is expressed in the format of slotID. For example, PDU1. Here PDU1 is an example. The value may vary with devices.";
        }
        leaf entity-index {
          type uint32;
          description
            "Index.";
        }
        leaf board-type {
          type string {
            length "1..32";
          }
          description
            "Type of a pdu board.";
        }
        leaf work-mode {
          type driver-power-work-mode;
          description
            "Working mode of a pdu board.";
        }
        leaf power-state {
          type string {
            length "1..255";
          }
          description
            "Power Running State.";
        }
        leaf abnormal-number {
          type string {
            length "1..255";
          }
          description
            "Abnormal PowerModule Number.";
        }
        leaf normal-number {
          type string {
            length "1..255";
          }
          description
            "Normal PowerModule Number.";
        }
      }
    }	

    container vsus {
      config false;
      description
        "List of VSU.";
      list vsu {
        key "position";
        description
          "Statistics of VSU.";
        leaf position {
          type string {
            length "1..32";
          }
          description
            "VSU position. The position is expressed in the format of slotID. For example, 1. Here 1 is an example. The value may vary with devices.";
        }
        leaf service-type {
          type driver-vsu-service-type;
          description
            "Service type of a VSU board.";
        }
      }
    }
    container disks {
      config false;
      description
        "List of information about disks on a device.";
      list disk {
        key "position";
        description
          "Statistics of disk information on a device.";
        leaf position {
          type string {
            length "1..32";
          }
          description
            "Position. The position is expressed in the format of slotID. For example, 1. Here 1 is an example. The value may vary with devices.";
        }
        leaf type {
          ext:support-filter "true";
          type driver:disk-type;
          description
            "Disk type.";
        }
        leaf present {
          type string {
            length "1..32";
          }
          description
            "Present status of a disk.";
        }
        leaf power {
          type string {
            length "1..32";
          }
          description
            "Working mode of the power supply.";
        }
        leaf register {
          type string {
            length "1..32";
          }
          description
            "Registered status of a disk.";
        }
        leaf vendor {
          type string {
            length "1..32";
          }
          description
            "Type of a hardware entity.";
        }
        leaf serial-number {
          type string {
            length "1..32";
          }
          description
            "Disk number.";
        }
        leaf firmware-version {
          type string {
            length "1..32";
          }
          description
            "Firmware version.";
        }
      }
    }
   }
  }

  augment "/lcs:license" {
  description
     "Adds driver configuration to lcs model.";
    container lcs-boards {
      status deprecated;
      description
        "List of license information about all boards capacity improvement.";
      list lcs-board {
        key "position capacity";
        status deprecated;
        description
          "Configure license information about a board capacity improvement.";
        leaf position {
          type string {
            length "1..32";
          }
          status deprecated;
          description
            "Position which the license for the capacity improvement feature is activated. The position is expressed in the format of slotID. For example, 1. Here 1 is an example. The value may vary with devices.";
        }
        leaf capacity {
          type lcs-improve-capacity-type;
          units "bit/s";
          status deprecated;
          description
            "Capacity. The capacity is related to a specific board.";
        }
      }
    }
    container lcs-usage-board-capacitys {
      config false;
      description
        "List of capacity improvement license usage information.";
      list lcs-usage-board-capacity {
        key "feature-name";
        description
          "Statistics of capacity improvement license usage information.";
        leaf feature-name {
          type string {
            length "1..31";
          }
          description
            "Name of the control item corresponding to the board license.";
        }
        leaf feature-description {
          type string {
            length "1..255";
          }
          description
            "Description of the control item corresponding to the board license.";
        }
        leaf offline {
          type uint32;
          description
            "Number of offline resources to be activated.";
        }
        leaf allocated {
          type uint32;
          description
            "Number of allocated resources to be activated.";
        }
        leaf activated {
          type uint32;
          description
            "Number of activated resources.";
        }
        leaf available {
          type uint32;
          description
            "Number of remaining available resources.";
        }
        leaf total {
          type uint32;
          description
            "Total number of resources.";
        }
        container boards {
          description
            "List of capacity improvement license usage information on all boards.";
          list board {
            key "position";
            description
              "Statistics of capacity improvement license usage information on a board.";
            leaf position {
              type string {
                length "1..32";
              }
              description
                "Position which the license for the capacity improvement feature is activated. The position is expressed in the format of slotID. For example, 1. Here 1 is an example. The value may vary with devices.";
            }
            leaf needed {
              type uint32;
              description
                "Number of needed resources.";
            }
            leaf used {
              type uint32;
              description
                "Number of used resources.";
            }
            leaf active-status {
              type lcs-active-status-type;
              description
                "License status.";
            }
          }
        }
      }
    }
  }
}
