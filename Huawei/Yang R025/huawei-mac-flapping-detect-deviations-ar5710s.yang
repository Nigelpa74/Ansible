/*
Copyright (C) 2024 Huawei Technologies Co., Ltd. All rights reserved.
*/
module huawei-mac-flapping-detect-deviations-ar5710s {
  namespace "urn:huawei:yang:huawei-mac-flapping-detect-deviations-ar5710s";
  prefix mac-flapping-detect-devs-ar5710s;

  import huawei-mac-flapping-detect {
    prefix mac-flapping-detect;
  }
  import huawei-ifm {
    prefix ifm;
  }
  import huawei-ethernet {
    prefix ethernet;
  }

  organization
    "Huawei Technologies Co., Ltd.";
  contact
    "Huawei Industrial Base
     Bantian, Longgang
     Shenzhen 518129
     People's Republic of China
     Website: http://www.huawei.com
     Email: support@huawei.com";
  description
    "This module defines deviation statements for huawei-mac-flapping-detect module.";

  revision 2024-10-27 {
    description
      "Initial revision.";
    reference "Huawei private.";
  }

  deviation "/mac-flapping-detect:mac-flapping-detect/mac-flapping-detect:global-attribute/mac-flapping-detect:detect-type" {
    deviate not-supported;
  }
  deviation "/mac-flapping-detect:mac-flapping-detect/mac-flapping-detect:global-attribute/mac-flapping-detect:aging-time" {
    deviate not-supported;
  }
  deviation "/mac-flapping-detect:mac-flapping-detect/mac-flapping-detect:global-attribute/mac-flapping-detect:trap-interval" {
    deviate not-supported;
  }
  deviation "/mac-flapping-detect:mac-flapping-detect/mac-flapping-detect:exclude-mac-addresses" {
    deviate not-supported;
  }
  deviation "/mac-flapping-detect:mac-flapping-detect/mac-flapping-detect:exclude-bds" {
    deviate not-supported;
  }
  deviation "/ifm:ifm/ifm:interfaces/ifm:interface/ethernet:ethernet/ethernet:main-interface/ethernet:l2-attribute/mac-flapping-detect:mac-address-flapping" {
    deviate not-supported;
  }
  deviation "/ifm:ifm/ifm:interfaces/ifm:interface/ethernet:ethernet/ethernet:l2-sub-interface/mac-flapping-detect:mac-address-flapping" {
    deviate not-supported;
  }
}
