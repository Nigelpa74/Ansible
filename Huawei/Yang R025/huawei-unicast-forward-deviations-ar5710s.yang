/*
Copyright (C) 2025 Huawei Technologies Co., Ltd. All rights reserved.
*/
module huawei-unicast-forward-deviations-ar5710s {
  yang-version 1;
  namespace "urn:huawei:yang:huawei-unicast-forward-deviations-ar5710s";
  prefix unicast-forward-devs-ar5710s;

  import huawei-unicast-forward {
    prefix unicast-forward;
  }
  import huawei-ifm {
    prefix ifm;
  }
  import huawei-devm {
    prefix devm;
  }
  import huawei-license {
    prefix lcs;
  }

  organization
    "Huawei Technologies Co., Ltd.";
  contact
    "Huawei Industrial Base
     Bantian, Longgang
     Shenzhen 518129
     People's Republic of China
     Website: http://www.huawei.com
     Email: support@huawei.com";
  description
    "This module defines deviation statements for huawei-unicast-forward module.";

  revision 2025-02-24 {
    description
      "Initial revision.";
    reference "Huawei private.";
  }

  deviation "/unicast-forward:unicast-forward/unicast-forward:global-uc-attribute/unicast-forward:fib-miss" {
    deviate not-supported;
  }
  deviation "/unicast-forward:unicast-forward/unicast-forward:global-uc-attribute/unicast-forward:nexthop-spt" {
    deviate not-supported;
  }
  deviation "/unicast-forward:unicast-forward/unicast-forward:global-uc-attribute/unicast-forward:mtu-force-frag" {
    deviate not-supported;
  }
  deviation "/unicast-forward:unicast-forward/unicast-forward:global-uc-attribute/unicast-forward:indirect-nexthop" {
    deviate not-supported;
  }
  deviation "/unicast-forward:unicast-forward/unicast-forward:global-uc-attribute/unicast-forward:ignore-mac" {
    deviate not-supported;
  }
  deviation "/unicast-forward:unicast-forward/unicast-forward:global-uc-attribute/unicast-forward:ttl-decrement" {
    deviate not-supported;
  }
  deviation "/unicast-forward:unicast-forward/unicast-forward:global-uc-attribute/unicast-forward:trunk-nd-mode" {
    deviate not-supported;
  }
  deviation "/unicast-forward:unicast-forward/unicast-forward:global-uc-attribute/unicast-forward:trunk-arp-mode" {
    deviate not-supported;
  }
  deviation "/unicast-forward:unicast-forward/unicast-forward:high-re-modes" {
    deviate not-supported;
  }
  deviation "/unicast-forward:unicast-forward/unicast-forward:global-nexthop-spt" {
    deviate not-supported;
  }
  deviation "/unicast-forward:unicast-forward/unicast-forward:na-anti-attack-statistics" {
    deviate not-supported;
  }
  deviation "/unicast-forward:unicast-forward/unicast-forward:vxlan-central-reassemble" {
    deviate not-supported;
  }
  deviation "/unicast-forward:unicast-forward/unicast-forward:global-gre" {
    deviate not-supported;
  }
  deviation "/unicast-forward:unicast-forward/unicast-forward:ip-urpf" {
    deviate not-supported;
  }
  deviation "/unicast-forward:unicast-forward/unicast-forward:ip-urpf-check-mode" {
    deviate not-supported;
  }
  deviation "/unicast-forward:unicast-forward/unicast-forward:ipv4-ttl-expired-forwards" {
    deviate not-supported;
  }
  deviation "/unicast-forward:unicast-forward/unicast-forward:ipv6-ttl-expired-forwards" {
    deviate not-supported;
  }
  deviation "/unicast-forward:unicast-forward/unicast-forward:vxlan-forward-ospf" {
    deviate not-supported;
  }
  deviation "/unicast-forward:unicast-forward/unicast-forward:vxlan-forward-ospfv3" {
    deviate not-supported;
  }
  deviation "/unicast-forward:unicast-forward/unicast-forward:backup-groups" {
    deviate not-supported;
  }
  deviation "/unicast-forward:unicast-forward/unicast-forward:vxlan-anycast-gateway-extend" {
    deviate not-supported;
  }
  deviation "/unicast-forward:unicast-forward/unicast-forward:ip-special-address/unicast-forward:link-local-address" {
    deviate not-supported;
  }
  deviation "/unicast-forward:reset-na-anti-attack-statistic" {
    deviate not-supported;
  }
  deviation "/ifm:ifm/ifm:interfaces/ifm:interface/unicast-forward:unicast-forward" {
    deviate not-supported;
  }
  deviation "/devm:devm/devm:lpu-boards/devm:lpu-board/unicast-forward:unicast-forward" {
    deviate not-supported;
  }
  deviation "/devm:devm/devm:mpu-boards/devm:mpu-board/unicast-forward:unicast-forward" {
    deviate not-supported;
  }
  deviation "/lcs:license/lcs:license-items/lcs:license-item/unicast-forward:port-l3vpns" {
    deviate not-supported;
  }
  deviation "/lcs:license/lcs:license-items/lcs:license-item/unicast-forward:port-l3vpn-evpns" {
    deviate not-supported;
  }
  deviation "/lcs:license/lcs:license-items/lcs:license-item/unicast-forward:port-service-enhances" {
    deviate not-supported;
  }
  deviation "/lcs:license/lcs:license-items/lcs:license-item/unicast-forward:port-aggregations" {
    deviate not-supported;
  }
  deviation "/lcs:license/lcs:license-items/lcs:license-item/unicast-forward:port-core-aggregations" {
    deviate not-supported;
  }
  deviation "/lcs:license/lcs:license-items/lcs:license-item/unicast-forward:port-peerings" {
    deviate not-supported;
  }
  deviation "/lcs:license/lcs:license-items/lcs:license-item/unicast-forward:port-srv6s" {
    deviate not-supported;
  }
  deviation "/lcs:license/lcs:resource-usages/lcs:resource-usage/unicast-forward:port-l3vpns" {
    deviate not-supported;
  }
  deviation "/lcs:license/lcs:resource-usages/lcs:resource-usage/unicast-forward:port-l3vpn-evpns" {
    deviate not-supported;
  }
  deviation "/lcs:license/lcs:resource-usages/lcs:resource-usage/unicast-forward:port-service-enhances" {
    deviate not-supported;
  }
  deviation "/lcs:license/lcs:resource-usages/lcs:resource-usage/unicast-forward:port-aggregations" {
    deviate not-supported;
  }
  deviation "/lcs:license/lcs:resource-usages/lcs:resource-usage/unicast-forward:port-core-aggregations" {
    deviate not-supported;
  }
  deviation "/lcs:license/lcs:resource-usages/lcs:resource-usage/unicast-forward:port-peerings" {
    deviate not-supported;
  }
  deviation "/lcs:license/lcs:resource-usages/lcs:resource-usage/unicast-forward:port-srv6s" {
    deviate not-supported;
  }
}
