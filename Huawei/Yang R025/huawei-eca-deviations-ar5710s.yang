/*
Copyright (C) 2025 Huawei Technologies Co., Ltd. All rights reserved.
*/
module huawei-eca-deviations-ar5710s {
  namespace "urn:huawei:yang:huawei-eca-deviations-ar5710s";
  prefix eca-devs-ar5710s;

  import huawei-eca {
    prefix eca;
  }

  organization
    "Huawei Technologies Co., Ltd.";
  contact
    "Huawei Industrial Base
     Bantian, Longgang
     Shenzhen 518129
     People's Republic of China
     Website: http://www.huawei.com
     Email: support@huawei.com";
  description
    "This module defines deviation statements for huawei-eca module.";

  revision 2025-02-24 {
    description
      "Initial revision.";
    reference "Huawei private.";
  }

  deviation "/eca:eca/eca:history-service-infos" {
    deviate not-supported;
  }
}
