/*
Copyright (C) 2025 Huawei Technologies Co., Ltd. All rights reserved.
*/
module huawei-arp-fwd-deviations-ar5710s {
  namespace "urn:huawei:yang:huawei-arp-fwd-deviations-ar5710s";
  prefix arp-fwd-devs-ar5710s;

  import huawei-arp-fwd {
    prefix arp-fwd;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-arp-fwd module.";

  revision 2025-02-24 {
    description
      "Initial revision.";
    reference "Huawei private.";
  }

  deviation "/arp-fwd:arp-fwd" {
    deviate not-supported;
  }
  deviation "/ifm:ifm/ifm:interfaces/ifm:interface/arp-fwd:arp-miss-enable" {
    deviate not-supported;
  }
}
