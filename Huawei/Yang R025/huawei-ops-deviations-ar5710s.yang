/*
Copyright (C) 2025 Huawei Technologies Co., Ltd. All rights reserved.
*/
module huawei-ops-deviations-ar5710s {
  namespace "urn:huawei:yang:huawei-ops-deviations-ar5710s";
  prefix ops-devs-ar5710s;

  import huawei-ops {
    prefix ops;
  }

  organization
    "Huawei Technologies Co., Ltd.";
  contact
    "Huawei Industrial Base
     Bantian, Longgang
     Shenzhen 518129
     People's Republic of China
     Website: http://www.huawei.com
     Email: support@huawei.com";
  description
    "This module defines deviation statements for huawei-ops module.";

  revision 2025-02-24 {
    description
      "Initial revision.";
    reference "Huawei private.";
  }

  deviation "/ops:ops/ops:global-switch" {
    deviate not-supported;
  }
  deviation "/ops:ops/ops:assistant/ops:mtp-status-switch" {
    deviate not-supported;
  }
}
