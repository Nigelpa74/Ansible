/*
Copyright (C) 2025 Huawei Technologies Co., Ltd. All rights reserved.
*/
module huawei-syslog-deviations-ar5710s {
  namespace "urn:huawei:yang:huawei-syslog-deviations-ar5710s";
  prefix syslog-devs-ar5710s;

  import huawei-syslog {
    prefix syslog;
  }

  organization
    "Huawei Technologies Co., Ltd.";
  contact
    "Huawei Industrial Base
     Bantian, Longgang
     Shenzhen 518129
     People's Republic of China
     Website: http://www.huawei.com
     Email: support@huawei.com";
  description
    "This module defines deviation statements for huawei-syslog module.";

  revision 2025-02-24 {
    description
      "Initial revision.";
    reference "Huawei private.";
  }

  typedef logfile-type-deviations {
    type enumeration {
      enum log {
        value 1;
        description
          "Log logfile.";
      }
      enum security {
        value 3;
        description
          "Security logfile.";
      }
    }
    description
      "The type of log.";
  }

  deviation "/syslog:syslog/syslog:servers/syslog:server/syslog:host-name" {
    deviate not-supported;
  }
  deviation "/syslog:syslog/syslog:servers/syslog:server/syslog:is-activated" {
    deviate not-supported;
  }
  deviation "/syslog:syslog/syslog:servers/syslog:server/syslog:facility-mask" {
    deviate not-supported;
  }
  deviation "/syslog:syslog/syslog:servers/syslog:server/syslog:severity-mask" {
    deviate not-supported;
  }
  deviation "/syslog:syslog/syslog:global-parameter/syslog:delay-suppress-enable" {
    deviate not-supported;
  }
  deviation "/syslog:syslog/syslog:global-parameter/syslog:character-set" {
    deviate not-supported;
  }
  deviation "/syslog:syslog/syslog:log-switch-list/syslog:log-switch/syslog:suppress" {
    deviate not-supported;
  }
  deviation "/syslog:syslog/syslog:logfiles/syslog:logfile/syslog:latest-logs" {
    deviate not-supported;
  }
  deviation "/syslog:syslog/syslog:logfile-prefixs" {
    deviate not-supported;
  }
  deviation "/syslog:syslog/syslog:logfile-servers" {
    deviate not-supported;
  }
  deviation "/syslog:syslog/syslog:servers/syslog:server/syslog:ipaddress" {
    deviate replace {
      type string {
        length "1..255";
      }
    }
  }
  deviation "/syslog:syslog/syslog:global-parameter/syslog:buffer-size" {
    deviate replace {
      type int32 {
        range "0..10240";
      }
    }
  }
  deviation "/syslog:syslog/syslog:logfiles/syslog:logfile/syslog:logfile-type" {
    deviate replace {
      type syslog-devs-ar5710s:logfile-type-deviations;
    }
  }
  deviation "/syslog:syslog/syslog:logfiles/syslog:logfile/syslog:max-file-num" {
    deviate replace {
      type uint32 {
        range "3..500";
      }
    }
  }
  deviation "/syslog:syslog/syslog:logfiles/syslog:logfile/syslog:max-file-size" {
    deviate delete {
      must "(../logfile-type='debug' and ../max-file-size=8) or ((../logfile-type='security' or ../logfile-type='operation') and (../max-file-size>=1 and ../max-file-size<=4))or (../logfile-type='log' and (../max-file-size=4 or ../max-file-size=8 or ../max-file-size=16 or ../max-file-size=32))";
    }
    deviate add {
      must "((../logfile-type='security') and (../max-file-size>=1 and ../max-file-size<=4))or (../logfile-type='log' and (../max-file-size=4 or ../max-file-size=8 or ../max-file-size=16 or ../max-file-size=32))";
    }
  }
}
