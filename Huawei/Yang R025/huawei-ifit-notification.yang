/*
Copyright (C) 2021-2024 Huawei Technologies Co., Ltd. All rights reserved.
*/
module huawei-ifit-notification {
  yang-version 1;
  namespace "urn:huawei:yang:huawei-ifit-notification";
  prefix ifit-notification;
  import huawei-extension {
    prefix ext;
  } 
  organization
    "Huawei Technologies Co., Ltd.";
  contact
    "Huawei Industrial Base
    Bantian, Longgang
    Shenzhen 518129
    People's Republic of China
    Website: http://www.huawei.com
    Email: support@huawei.com";
  description
    "Notification of ifit.";
  revision 2024-12-19 {
    description
      "Change the type length of measurement-flow-threshold-exceed.";
    reference
      "Huawei private.";
  }
  revision 2024-10-24 {
    description
      "Add IFIT ALARM.";
    reference
      "Huawei private.";
  }
  revision 2022-08-29 {
    description
      "Modify ALARM description.";
    reference
      "Huawei private.";
  }
  revision 2022-08-08 {
    description
      "Add IFIT ALARM.";
    reference
      "Huawei private.";
  }
  revision 2021-02-01 {
    description
      "Initial revision.";
    reference
      "Huawei private.";
  }

  ext:task-name  "ifit";

  notification dynflow-ingress-exceed {
    description
      "The number of IFIT dynamic ingress flow reaches the upper limit.";
    leaf upper-limit {
      type uint32;
      description
        "Total dynamic ingress flow number upper limit of IFIT.";
    }
  }
  notification dynflow-ingress-resume {
    description
      "The number of IFIT dynamic ingress flow is below the upper limit.";
    leaf upper-limit {
      type uint32;
      description
        "Total dynamic ingress flow number upper limit of IFIT.";
    }
  }
  notification dynflow-midegress-exceed {
    description
      "The number of IFIT dynamic midegress flow reaches the upper limit.";
    leaf upper-limit {
      type uint32;
      description
        "Total dynamic midegress flow number upper limit of IFIT.";
    }
  }
  notification dynflow-midegress-resume {
    description
      "The number of IFIT dynamic midegress flow is below the upper limit.";
    leaf upper-limit {
      type uint32;
      description
        "Total dynamic midegress flow number upper limit of IFIT.";
    }
  }
  notification ingress-exceed {
    description
      "The number of IFIT ingress flow reaches the upper limit.";
    leaf upper-limit {
      type uint32;
      description
        "Total ingress flow number upper limit of IFIT.";
    }
  }
  notification ingress-resume {
    description
      "The number of IFIT ingress flow is below the upper limit.";
    leaf upper-limit {
      type uint32;
      description
        "Total ingress flow number upper limit of IFIT.";
    }
  }
  notification measurement-flow-exceed {
    description
      "The number of IFIT measurement flow reaches the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
  notification measurement-flow-resume {
    description
      "The number of IFIT measurement flow is below the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
  notification dynflow-ingress-almost-exceed {
    description
      "The number of IFIT dynamic ingress flows almost reaches the upper limit.";
    leaf upper-limit {
      type uint32;
      description
        "Total dynamic ingress flow number upper limit of IFIT.";
    }
  }
  notification dynflow-ingress-almost-exceed-resume {
    description
      "The number of IFIT dynamic ingress flows is below 80% of the upper limit.";
    leaf upper-limit {
      type uint32;
      description
        "Total dynamic ingress flow number upper limit of IFIT.";
    }
  }
  notification dynflow-midegress-almost-exceed {
    description
      "The number of IFIT dynamic midegress flows almost reaches the upper limit.";
    leaf upper-limit {
      type uint32;
      description
        "Total dynamic midegress flow number upper limit of IFIT.";
    }
  }
  notification dynflow-midegress-almost-exceed-resume {
    description
      "The number of IFIT dynamic midegress flows is below 80% of the upper limit.";
    leaf upper-limit {
      type uint32;
      description
        "Total dynamic midegress flow number upper limit of IFIT.";
    }
  }
  notification ingress-almost-exceed {
    description
      "The number of IFIT ingress flows almost reaches the upper limit.";
    leaf upper-limit {
      type uint32;
      description
        "Total ingress flow number upper limit of IFIT.";
    }
  }
  notification ingress-almost-exceed-resume {
    description
      "The number of IFIT ingress flows is below 80% of the upper limit.";
    leaf upper-limit {
      type uint32;
      description
        "Total ingress flow number upper limit of IFIT.";
    }
  }
  notification measurement-flow-almost-exceed {
    description
      "The number of IFIT measurement flows almost reaches the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
  notification measurement-flow-almost-exceed-resume {
    description
      "The number of IFIT measurement flows is below 80% of the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
  notification mcp-no-sla-data {
    description
      "IFITMCP has not been generating SLA data for a noticeable period of time.";
  }
  notification mcp-sla-data-resume {
    description
      "IFITMCP is generating SLA data now.";
  }
  notification measurement-flow-threshold-exceed {
    description
      "The number of IFIT measurement flows almost reaches the upper threshold.";
    leaf node-type {
      type string {
        length "1..64";
      }
      description
        "The measurement flow node type of IFIT.";
    }
    leaf flow-type {
      type string {
        length "1..64";
      }
      description
        "The measurement flow type of IFIT.";
    }
    leaf upper-threshold {
      type string {
        length "1..8";
      }
      description
        "Total measurement flow number upper threshold of IFIT.";
    }
    leaf lower-threshold {
      type string {
        length "1..8";
      }
      description
        "Total measurement flow number lower threshold of IFIT.";
    }
    leaf spec-value {
      type uint32;
      description
        "Total measurement flow number specification of IFIT.";
    }
  }
  notification measurement-flow-threshold-exceed-resume {
    description
      "The number of IFIT measurement flows is below the lower threshold.";
    leaf node-type {
      type string {
        length "1..64";
      }
      description
        "The measurement flow node type of IFIT.";
    }
    leaf flow-type {
      type string {
        length "1..64";
      }
      description
        "The measurement flow type of IFIT.";
    }
    leaf upper-threshold {
      type string {
        length "1..8";
      }
      description
        "Total measurement flow number upper threshold of IFIT.";
    }
    leaf lower-threshold {
      type string {
        length "1..8";
      }
      description
        "Total measurement flow number lower threshold of IFIT.";
    }
    leaf spec-value {
      type uint32;
      description
        "Total measurement flow number specification of IFIT.";
    }
  }
}
