/*
Copyright (C) 2019-2025 Huawei Technologies Co., Ltd. All rights reserved.
*/
module huawei-qos-notification {
  yang-version 1;
  namespace "urn:huawei:yang:huawei-qos-notification";
  prefix qos-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of qos.";
  revision 2025-03-04 {
    description
      "Correct spelling errors.";
    reference
      "Huawei private.";
  }
  revision 2025-01-20 {
    description
      "Add new nodes.";
    reference
      "Huawei private.";
  }
  revision 2024-11-10 {
    description
      "Modify description.";
    reference
      "Huawei private.";
  }
  revision 2024-06-05 {
    description
      "Add enum for feature-type.";
    reference
      "Huawei private.";
  }
  revision 2024-06-04 {
    description
      "Modify spelling error.";
    reference
      "Huawei private.";
  }
  revision 2024-05-16 {
    description
      "Add xqos-traffic-policy-rule-resource-pre-alarm, xqos-traffic-policy-rule-resource-pre-alarm-resume.";
    reference
      "Huawei private.";
  }
  revision 2024-03-20 {
    description
      "Add xqos-IPv6-acl-mask-imprecise-alarm, xqos-IPv6-acl-mask-imprecise-resume.";
    reference
      "Huawei private.";
  }
  revision 2023-03-29 {
    description
      "Add xqos-slot-traffic-congestion, xqos-slot-traffic-congestion-resume.";
    reference
      "Huawei private.";
  }
  revision 2023-02-21 {
    description
      "Add xqos-board-service-mismatch-trap.";
    reference
      "Huawei private.";
  }
  revision 2023-02-01 {
    description
      "Add xqos-forward-resource-over-load, xqos-forward-resource-over-load-resume.";
    reference
      "Huawei private.";
  }
  revision 2022-11-30 {
    description
      "Add xqos-received-multi-pause-frame-interface-down, xqos-trunk-traffic-congestion.";
    reference
      "Huawei private.";
  }
  revision 2022-09-14 {
    description
      "Add xqos-board-hqos-fail-alarm, xqos-interface-hqos-fail-alarm.";
    reference
      "Huawei private.";
  }
  revision 2022-01-29 {
    description
      "Add leaf is-percent for xqos-car-bindwidth-exceed-chip-limit-alarm.";
    reference
      "Huawei private.";
  }
  revision 2022-01-25 {
    description
      "Add xqos-car-bindwidth-exceed-chip-limit-alarm.";
    reference
      "Huawei private.";
  }
  revision 2022-01-13 {
    description
      "Add xqos-mode-flexe-over-portshap-alarm, xqos-mode-flexe-over-portshap-alarm-resume.";
    reference
      "Huawei private.";
  }
  revision 2020-09-01 {
    description
      "Add new nodes.";
    reference
      "Huawei private.";
  }
  revision 2020-06-08 {
    description
      "Add new nodes.";
    reference
      "Huawei private.";
  }
  revision 2019-09-07 {
    description
      "Init revision.";
    reference
      "Huawei private.";
  }
  ext:task-name "qos";
  typedef qos-service-class {
    type enumeration {
      enum "be" {
        value 1; 
        description
          "BE service-class.";
      }
      enum "af1" {
        value 2; 
        description
          "AF1 service-class.";
      }
      enum "af2" {
        value 3; 
        description
          "AF2 service-class.";
      }
      enum "af3" {
        value 4; 
        description
          "AF3 service-class.";
      }
      enum "af4" {
        value 5; 
        description
          "AF4 service-class.";
      }
      enum "ef" {
        value 6; 
        description
          "EF service-class.";
      }
      enum "cs6" {
        value 7; 
        description
          "CS6 service-class.";
      }
      enum "cs7" {
        value 8; 
        description
          "CS7 service-class.";
      }
    }
    description
      "Queue type.";
  }
  typedef drop-type {
    type enumeration {
      enum "discard-packet" {
        value 1; 
        description
          "Discard by packet.";
      }
      enum "discard-byte" {
        value 2; 
        description
          "Discard by byte.";
      }
      enum "discard-packet-ratio" {
        value 3; 
        description
          "Discard by packet ratio.";
      }
    }
    description
      "Discard type.";
  }
  typedef qos-direction-type {
    type enumeration {
      enum "inbound" {
        value 1; 
        description
          "Inbound.";
      }
      enum "outbound" {
        value 2; 
        description
          "Outbound.";
      }
    }
    description
      "Direction type.";
  }
  typedef pool-type {
    type enumeration {
      enum "pool-0" {
        value 1;
        description
          "Pool 0.";
      }
      enum "pool-1" {
        value 2;
        description
          "Pool 1.";
      }
    }
    description
      "Pool ID.";
  }
  typedef feature-type {
    type enumeration {
      enum "bgpflow" {
        value 1; 
        description
          "BGP Flow.";
      }
      enum "qppb" {
        value 2; 
        description
          "QPPB.";
      }
      enum "behavior-of-netstream" {
        value 3; 
        description
          "Sampling at a fixed interval and sampling for fixed and random packets with a sampling ratio less than 10000 in the behavior.";
      }
      enum "behavior-of-strict-ip-urpf" {
        value 4; 
        description
          "Strict IP URPF in the behavior.";
      }
      enum "bgpflow-vxlan-pop" {
        value 5; 
        description
          "BGP Flow Vxlan Pop.";
      }
    }
    description
      "Feature type.";
  }
  typedef qos-all-direction-type {
    type enumeration {
      enum "in-outbound" {
        value 0; 
        description
          "Inbound and outbound.";
      }
      enum "inbound" {
        value 1; 
        description
          "Inbound.";
      }
      enum "outbound" {
        value 2; 
        description
          "Outbound.";
      }
    }
    description
      "The direction of traffic policy apply.";
  }
  notification hqos-buffer-alarm {
    description
      "The buffersize on slot [SLOTID] chip [CHIPID] has reached [BufferSize]%%.";
    leaf slot-id {
      type string {
        length "0..15";
      }
      description
        "Slot ID.";
    }
    leaf chip-id {
      type string {
        length "0..7";
      }
      description
        "Chip ID.";
    }
    leaf buffer-size {
      type string {
        length "0..63";
      }
      units "kB";
      description
        "Queue buffer size.";
    }
  }
  notification hqos-buffer-alarm-resume {
    description
      "Queue buffer alarm on slot [SLOTID] chip [CHIPID] cleared.";
    leaf slot-id {
      type string {
        length "0..15";
      }
      description
        "Slot ID.";
    }
    leaf chip-id {
      type string {
        length "0..7";
      }
      description
        "Chip ID.";
    }
    leaf buffer-size {
      type string {
        length "0..63";
      }
      units "kB";
      description
        "Queue buffer size.";
    }
  }
  notification hqos-port-queue-statistics-discard-alarm {
    description
      "On interface [InterfaceName],[Queue] in queue [DiscardType] is [DiscardValue],it reached alarm-threshold.";
    leaf interface-name {
      type string {
        length "1..511";
      }
      description
        "Interface name.";
    }
    leaf queue {
      type qos-service-class;
      description
        "Queue index.";
    }
    leaf discard-type {
      type drop-type;
      description
        "Discard type.";
    }
    leaf discard-value {
      type string {
        length "1..32";
      }
      description
        "Discard value.";
    }
  }
  notification hqos-port-queue-statistics-discard-alarm-resume {
    description
      "On interface [InterfaceName],[Queue] in queue [DiscardType] is [DiscardValue],it is Less than alarm-threshold.";
    leaf interface-name {
      type string {
        length "1..511";
      }
      description
        "Interface name.";
    }
    leaf queue {
      type qos-service-class;
      description
        "Queue index.";
    }
    leaf discard-type {
      type drop-type;
      description
        "Discard type.";
    }
    leaf discard-value {
      type string {
        length "1..32";
      }
      description
        "Discard value.";
    }
  }
  notification hqos-user-queue-apply-pir-fail-alarm {
    description
      "The sum of the pirs requested by all users exceeded the maximum configuration specification of the TM chip.";
    leaf ent-physical-index {
      type uint32;
      description
        "Indicates the index of the physical entity.";
    }
    leaf ent-physical-name {
      type string {
        length "0..255";
      }
      description
        "Indicates the name of the physical entity.";
    }
    leaf direction {
      type qos-direction-type;
      description
        "Direction. - 1: inbound - 2: outbound.";
    }
  }
  notification hqos-user-queue-apply-pir-success-alarm {
    description
      "All users successfully requested pirs.";
    leaf ent-physical-index {
      type uint32;
      description
        "Indicates the index of the physical entity.";
    }
    leaf ent-physical-name {
      type string {
        length "0..255";
      }
      description
        "Indicates the name of the physical entity.";
    }
    leaf direction {
      type qos-direction-type;
      description
        "Direction. - 1: inbound - 2: outbound.";
    }
  }
  notification hqos-user-queue-apply-pir-from-pool-fail-alarm {
    description
      "The sum of the PIRs requested from resource pool by all users exceeded the maximum configuration specification of the TM chip.";
    leaf ent-physical-index {
      type uint32;
      description
        "Indicates the index of the physical entity.";
    }
    leaf ent-physical-name {
      type string {
        length "0..255";
      }
      description
        "Indicates the name of a physical entity.";
    }
    leaf pool {
      type pool-type;
      description
        "Resource pool. - 1: pool-0 - 2: pool-1.";
    }
  }
  notification hqos-user-queue-apply-pir-from-pool-success-alarm {
    description
      "All users successfully requested pirs.";
    leaf ent-physical-index {
      type uint32;
      description
        "Indicates the index of the physical entity.";
    }
    leaf ent-physical-name {
      type string {
        length "0..255";
      }
      description
        "Indicates the name of a physical entity.";
    }
    leaf pool {
      type pool-type;
      description
        "Resource pool. - 1: pool-0 - 2: pool-1.";
    }
  }
  notification xqos-4queue-resource-over-alarm {
    description
      "The number of outbound 4queue user-queue exceeded the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-4queue-resource-over-alarm-resume {
    description
      "The number of Outbound 4queue user-queue under the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-4queue-resource-pre-alarm {
    description
      "The number of outbound 4queue user-queue exceeded 90 percent of the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-4queue-resource-pre-alarm-resume {
    description
      "The number of Outbound 4queue user-queue under 90 percent of the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-8queue-resource-over-alarm {
    description
      "The number of outbound 8queue user-queue exceeded the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-8queue-resource-over-alarm-resume {
    description
      "The number of Outbound 8queue user-queue under the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-8queue-resource-pre-alarm {
    description
      "The number of outbound 8queue user-queue exceeded 90 percent of the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-8queue-resource-pre-alarm-resume {
    description
      "The number of outbound 8queue user-queue under 90 percent of the specification of the forwarding engine resources.";
    leaf ent-physical-index {
      type uint32;
      description
        "Indicates the index of the physical entity.";
    }
    leaf ent-physical-name {
      type string {
        length "0..255";
      }
      description
        "Name of a physical entity.";
    }
    leaf chip-id {
      type uint32;
      description
        "Chip ID.";
    }
  }
  notification xqos-hard-pipe-ac-band-over-alarm {
    description
      "The hard pipe configured on the interface [InterfaceName] over port bandwidth or port shaping.";
    leaf interface-name {
      type string {
        length "1..511";
      }
      description
        "Hardpipe interface name.";
    }
  }
  notification xqos-hard-pipe-ac-band-over-alarm-resume {
    description
      "The hard pipe configured on the interface [InterfaceName] over port bandwidth or port shaping has cleared.";
    leaf interface-name {
      type string {
        length "1..511";
      }
      description
        "Hardpipe interface name.";
    }
  }
  notification xqos-hard-pipe-alarm {
    description
      "The hard-pipe service on interface [InterfaceName] has reached [BandwidthUsage]%% of interface's hard-pipe capability.";
    leaf interface-name {
      type string {
        length "1..511";
      }
      description
        "Hardpipe interface name.";
    }
    leaf bandwidth-usage {
      type uint32;
      units "%";
      description
        "Hardpipe bandwidth usage.";
    }
  }
  notification xqos-hard-pipe-alarm-resume {
    description
      "The hard-pipe service alarm on interface [InterfaceName] has cleared.";
    leaf interface-name {
      type string {
        length "1..511";
      }
      description
        "Hardpipe interface name.";
    }
  }
  notification xqos-hard-pipe-apply-fail-alarm {
    description
      "The hard pipe configured on the interface [InterfaceName] does not take effect.";
    leaf interface-name {
      type string {
        length "1..511";
      }
      description
        "Hardpipe interface name.";
    }
  }
  notification xqos-hard-pipe-apply-fail-alarm-resume {
    description
      "The hard pipe not taking effect alarm on the interface [InterfaceName] has cleared.";
    leaf interface-name {
      type string {
        length "1..511";
      }
      description
        "Hardpipe interface name.";
    }
  }
  notification xqos-hard-pipe-apply-user-queue-fail-alarm {
    description
      "The hard pipe of the interface specified by [InterfaceName] fails to apply for forwarding resources.";
    leaf interface-name {
      type string {
        length "1..511";
      }
      description
        "Interface name.";
    }
  }
  notification xqos-hard-pipe-apply-user-queue-fail-alarm-resume {
    description
      "The alarm indicating that the hard pipe of the interface specified by [InterfaceName] fails to apply for forwarding resources is cleared.";
    leaf interface-name {
      type string {
        length "1..511";
      }
      description
        "Interface name.";
    }
  }
  notification xqos-hard-pipe-bandwidth-alarm {
    description
      "The hard-pipe bandwidth configuration on interface [InterfaceName] exceeded the max available bandwidth [MaxCfgBandwidth]Kbps.";
    leaf interface-name {
      type string {
        length "1..511";
      }
      description
        "Interface name of the hard pipe.";
    }
    leaf max-cfg-bandwidth {
      type uint32;
      units "kbit/s";
      description
        "Maximum configurable bandwidth of the hard pipe.";
    }
  }
  notification xqos-hard-pipe-bandwidth-alarm-resume {
    description
      "The hard-pipe config alarm on interface [InterfaceName] has cleared.";
    leaf interface-name {
      type string {
        length "1..511";
      }
      description
        "Interface name of the hard pipe.";
    }
  }
  notification xqos-port-queue-alarm {
    description
      "The alarm of port-queue occurs, only when the used queue is in excess of the configured length.";
    leaf interface-index {
      type int32;
      description
        "Interface index.";
    }
    leaf queue {
      type string {
        length "1..4";
      }
      description
        "Queue index.";
    }
    leaf trunk-index {
      type int32;
      description
        "Trunk interface index.";
    }
  }
  notification xqos-port-queue-alarm-resume {
    description
      "Port queue alarm cleared.";
    leaf interface-index {
      type int32;
      description
        "Interface index.";
    }
    leaf queue {
      type string {
        length "1..4";
      }
      description
        "Queue index.";
    }
    leaf trunk-index {
      type int32;
      description
        "Trunk interface index.";
    }
  }
  notification xqos-soft-pipe-alarm {
    description
      "The soft-pipe service on interface [InterfaceName] has reached [BandwidthUsage]%% of interface's soft-pipe capability.";
    leaf interface-name {
      type string {
        length "1..511";
      }
      description
        "Interface name of the soft pipe.";
    }
    leaf bandwidth-usage {
      type uint32;
      units "%";
      description
        "Bandwidth usage of the soft pipe.";
    }
  }
  notification xqos-soft-pipe-alarm-resume {
    description
      "The soft-pipe service alarm on interface [InterfaceName] has cleared.";
    leaf interface-name {
      type string {
        length "1..511";
      }
      description
        "Interface name of the soft pipe.";
    }
  }
  notification xqos-tm-performance-alarm {
    description
      "The traffic bandwidth usage almost reached the maximum forwarding capability of the TM chip.";
    leaf slot-id {
      type string {
        length "0..15";
      }
      description
        "Slot ID.";
    }
    leaf chip-id {
      type uint32;
      description
        "Chip ID.";
    }
  }
  notification xqos-tm-performance-alarm-resume {
    description
      "The TM performance alarm was cleared.";
    leaf slot-id {
      type string {
        length "0..15";
      }
      description
        "Slot ID.";
    }
    leaf chip-id {
      type uint32;
      description
        "Chip ID.";
    }
  }
  notification global-acl-not-support-board {
    description
      "The trap of the board does not support acl.";
    leaf slot-id {
      type uint32;
      description
        "Slot ID.";
    }
    leaf direction {
      type string {
        length "1..31";
      }
      description
        "Direction.";
    }
  }
  notification xqos-mode-channel-over-portshap-alarm {
    description
      "The channelization bandwidth configured on the interface [interface-name] exceeds the port shaping value.";
    leaf interface-name {
      type string {
        length "1..511";
      }
      description
        "Mode channel interface name.";
    }
  }

  notification xqos-mode-channel-over-portshap-alarm-resume {
    description
      "The channelization bandwidth configured on the interface [interface-name] exceeds the port shaping value has cleared.";
    leaf interface-name {
      type string {
        length "1..511";
      }
      description
        "Mode channel interface name.";
    }
  }
  notification xqos-mode-flexe-over-portshap-alarm {
    description
      "The flexe channel bandwidth configured on the interface [interface-name] exceeds the port shaping value.";
    leaf interface-name {
      type string {
        length "1..511";
      }
      description
        "Mode flexe interface name.";
    }
  }
  notification xqos-mode-flexe-over-portshap-alarm-resume {
    description
      "The flexe channel bandwidth configured on the interface [interface-name] exceeds the port shaping value has cleared.";
    leaf interface-name {
      type string {
        length "1..511";
      }
      description
        "Mode flexe interface name.";
    }
  }
  notification acl-resource-alarm {
    description
      "The service failed to be delivered because ACL resources were insufficient.";
    leaf slot-id {
      type string{
         length "1..31";
      }
      description
        "The infomation of chassis.";
    }
    leaf service-type {
      type string{
         length "1..31";
      }
      description
        'ACL Service Type: "MQC Service", "SACL Service", "Common ACL Service"';
    }
    leaf service-name {
      type string{
         length "1..31";
      }
      description
        "ACL Service Name.";
    }
    leaf apply-type {
      type string{
         length "1..31";
      }
      description
        'View: "Interface", "Vlan", "VlanIf", "Global".';
    }
    leaf interface-name {
      type string{
         length "1..31";
      }
      description
        'Interface name.';
    }
    leaf direction {
      type string{
         length "1..31";
      }
      description
        'Different stages of packet process: "Inbound", "Outbound".';
    }
    leaf service-view {
      type string{
         length "1..31";
      }
      description
        "Parameter 1 of the service.";
    }
    leaf packect-name{
      type string{
         length "1..31";
      }
      description
        "Parameter 2 of the service: packet name, policy name etc.";
    }
    leaf service-other {
      type string{
         length "1..63";
      }
      description
        "Parameter 3 of the service: Other parameter of service.";
    }
    leaf fail-reason {
      type string{
         length "1..511";
      }
      description
        'Fail Reason: "Group resource full", "Entry resource full".';
    }
  }
  notification acl-resource-alarm-resume {
    description
      "ACL resources are sufficient. ";
    leaf slot-id {
      type string{
         length "1..31";
      }
      description
        "The infomation of chassis.";
    }
    leaf service-type {
      type string{
         length "1..31";
      }
      description
        'ACL Service Type: "MQC Service", "SACL Service", "Common ACL Service".';
    }
    leaf service-name {
      type string{
         length "1..31";
      }
      description
        "ACL service name.";
    }
    leaf apply-type {
      type string{
         length "1..31";
      }
      description
        'View: "Interface", "Vlan", "VlanIf", "Global".';
    }
    leaf interface-name {
      type string{
         length "1..31";
      }
      description
        'Interface name.';
    }
    leaf direction {
      type string{
         length "1..31";
      }
      description
        'Different stages of packet process: "Inbound", "Outbound".';
    }
    leaf service-view {
      type string{
         length "1..31";
      }
      description
        "Parameter 1 of the service.";
    }
    leaf packect-name {
      type string{
         length "1..31";
      }
      description
        "Parameter 2 of the service: packet name, policy name etc.";
    }
    leaf service-other {
      type string{
         length "1..63";
      }
      description
        "Parameter 3 of the service: Other parameter of service.";
    }
    leaf fail-reason {
      type string{
         length "1..511";
      }
      description
        'Fail Reason: "Group resource full", "Entry resource full".';
    }
  }
  notification xqos-unsupported-feature-alarm {
    description
      "The board [board-id] does not support [feature-name].";
    leaf board-id {
      type string {
        length "1..16";
      }
      description
        "Board ID.";
    }
    leaf feature-name {
      type feature-type;
      description
        "Feature name.";
    }
  }
  notification xqos-unsupported-feature-alarm-resume {
    description
      "The board [board-id] does not support [feature-name] alarm has cleared.";
    leaf board-id {
      type string {
        length "1..16";
      }
      description
        "Board ID.";
    }
    leaf feature-name {
      type feature-type;
      description
        "Feature name.";
    }
  }
  notification xqos-user-queue-apply-pir-exhaust-alarm {
    description
      "The sum of the PIRs requested by all users from the resource pool exceeded the maximum configuration specification of the TM chip.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-user-queue-apply-pir-exhaust-resume {
    description
      "The alarm is cleared when the sum of PIRs requested by all users from the resource pool falls below the maximum configuration of the TM chip.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-user-queue-apply-pir-pre-alarm {
    description
      "The sum of the PIRs requested by all users from the resource pool exceeded 90% of the maximum configuration specification of the TM chip.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-user-queue-apply-pir-pre-resume {
    description
      "This alarm is cleared when the sum of PIRs requested by all users from the resource pool is less than 90% of the maximum configuration of the TM chip.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-user-queue-pir-adjust-alarm {
    description
      "When the user-queue PIR applied for by all users exceeds the threshold, bandwidth adjustment is triggered. During the adjustment, packet loss may occur.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-user-queue-pir-adjust-resume {
    description
      "Bandwidth adjustment is canceled when the user-queue PIR bandwidth applied for by all users is lower than the threshold.";
    leaf slot-id {
      type string {
        length "1..127";
      }
      description
        "Slot ID.";
    }
    leaf tm-chip-id {
      type uint32;
      description
        "TM chip ID.";
    }
    leaf pool-index {
      type uint32;
      description
        "Resource pool index.";
    }
  }
  notification xqos-unsupported-action-alarm {
    description
      "Actions in a traffic behavior for ACL will not take effect on the current board.";
    leaf slot-id {
      type string {
        length "1..128";
      }
      description
        "Slot ID.";
    }
    leaf action-name {
      type string {
        length "1..128";
      }
      description
        "Action Name.";
    }
    leaf direction {
      type qos-all-direction-type;
      description
        "Direction.";
    }
  }
  notification xqos-unsupported-action-resume {
    description
      "The alarm is cleared when an unsupported action is deleted from traffic behavior.";
    leaf slot-id {
      type string {
        length "1..128";
      }
      description
        "Slot ID.";
    }
    leaf action-name {
      type string {
        length "1..128";
      }
      description
        "Action Name.";
    }
    leaf direction {
      type qos-all-direction-type;
      description
        "Direction.";
    }
  }
  notification xqos-car-bindwidth-exceed-chip-limit-alarm {
    description
      "The bandwidth configured for CAR exceeds the rate limiting capability of the chip.";
    leaf slot-id {
      type string {
        length "1..128";
      }
      description
        "Slot ID.";
    }
    leaf car-type {
      type string {
        length "1..128";
      }
      description
        "Car type.";
    }
    leaf cir {
      type uint32;
      description
        "Committed Information Rate.";
    }
    leaf pir {
      type uint32;
      description
        "Peak Information Rate.";
    }
    leaf maximum-rate-limit {
      type uint32;
      description
        "Maximum rate limiting capability of the chip.";
    }
    leaf is-percent {
      type string {
        length "1..128";
      }
      description
        "Is percent mode or not.";
    }
  }
  notification xqos-car-bindwidth-exceed-chip-limit-resume {
    description
      "The alarm is cleared when current car configuration bandwidth falls below the rate limiting capability of the chip.";
    leaf slot-id {
      type string {
        length "1..128";
      }
      description
        "Slot ID.";
    }
    leaf car-type {
      type string {
        length "1..128";
      }
      description
        "Car type.";
    }
    leaf cir {
      type uint32;
      description
        "Committed Information Rate.";
    }
    leaf pir {
      type uint32;
      description
        "Peak Information Rate.";
    }
    leaf maximum-rate-limit {
      type uint32;
      description
        "Maximum rate limiting capability of the chip.";
    }
    leaf is-percent {
      type string {
        length "1..128";
      }
      description
        "Is percent mode or not.";
    }
  }
  notification xqos-board-hqos-fail-alarm {
    description
      "Some HQoS functions on the board do not take effect.";
    leaf service-type {
      type string {
        length "1..127";
      }
      description
        "HQoS service Type.";
    }
    leaf slot-id {
      type string {
        length "1..31";
      }
      description
        "Slot ID.";
    }
    leaf reason-id {
      type uint32;
      description
        "The ID of alarm reason.";
    }
    leaf reason-description {
      type string {
        length "1..511";
      }
      description
        "The description of the alarm cause.";
    }
  }
  notification xqos-board-hqos-fail-resume {
    description
      "The alarm is cleared when the unsupported HQoS service is processed.";
    leaf service-type {
      type string {
        length "1..127";
      }
      description
        "HQoS service Type.";
    }
    leaf slot-id {
      type string {
        length "1..31";
      }
      description
        "Slot ID.";
    }
    leaf reason-id {
      type uint32;
      description
        "The ID of alarm reason.";
    }
    leaf reason-description {
      type string {
        length "1..511";
      }
      description
        "The description of the alarm cause.";
    }
  }
  notification xqos-interface-hqos-fail-alarm {
    description
      "Some HQoS functions on the port do not take effect.";
    leaf service-type {
      type string {
        length "1..127";
      }
      description
        "HQoS service Type.";
    }
    leaf slot-id {
      type string {
        length "1..31";
      }
      description
        "Slot ID.";
    }
    leaf interface-name {
      type string {
        length "1..511";
      }
      description
        "Interface name.";
    }
    leaf reason-id {
      type uint32;
      description
        "The ID of alarm reason.";
    }
    leaf reason-description {
      type string {
        length "1..511";
      }
      description
        "The description of the alarm cause.";
    }
  }
  notification xqos-interface-hqos-fail-resume {
    description
      "The alarm is cleared when the unsupported HQoS service is processed.";
    leaf service-type {
      type string {
        length "1..127";
      }
      description
        "HQoS service Type.";
    }
    leaf slot-id {
      type string {
        length "1..31";
      }
      description
        "Slot ID.";
    }
    leaf interface-name {
      type string {
        length "1..511";
      }
      description
        "Interface name.";
    }
    leaf reason-id {
      type uint32;
      description
        "The ID of alarm reason.";
    }
    leaf reason-description {
      type string {
        length "1..511";
      }
      description
        "The description of the alarm cause.";
    }
  }
  notification xqos-received-multi-pause-frame-interface-down {
    description
      "After a large number of PAUSE frames are received within a short period of time, the trunk member interface link goes Down.";
    leaf interface-name {
      type string {
        length "1..511";
      }
      description
        "Trunk member interface name.";
    }
  }
  notification xqos-received-multi-pause-frame-interface-down-resume {
    description
      "The interface line protocol recovery up after received not too many PAUSE frames in a short time.";
    leaf interface-name {
      type string {
        length "1..511";
      }
      description
        "Trunk member interface name.";
    }
  }
  notification xqos-trunk-traffic-congestion {
    description
      "Traffic congestion occurs on the trunk interface, and traffic on all member interfaces may be affected.";
    leaf trunk-name {
      type string {
        length "1..511";
      }
      description
        "Trunk interface name.";
    }
    leaf slot-id {
      type string {
        length "1..128";
      }
      description
        "Slot ID.";
    }
  }
  notification xqos-trunk-traffic-congestion-resume {
    description
      "The alarm is cleared when the traffic congestion on the trunk interface is cleared.";
    leaf trunk-name {
      type string {
        length "1..511";
      }
      description
        "Trunk interface name.";
    }
    leaf slot-id {
      type string {
        length "1..128";
      }
      description
        "Slot ID.";
    }
  }
  notification xqos-forward-resource-over-load {
    description
      "The board forwarding engine resources were overload.";
    leaf slot-id {
      type string {
        length "1..31";
      }
      description
        "Slot ID.";
    }
    leaf reason-id {
      type uint32;
      description
        "The ID of alarm reason.";
    }
    leaf reason-description {
      type string {
        length "1..511";
      }
      description
        "The description of the alarm cause.";
    }
  }
  notification xqos-forward-resource-over-load-resume {
    description
      "The alarm is cleared when the board forwarding engine resources overload is recovered.";
    leaf slot-id {
      type string {
        length "1..31";
      }
      description
        "Slot ID.";
    }
    leaf reason-id {
      type uint32;
      description
        "The ID of alarm reason.";
    }
    leaf reason-description {
      type string {
        length "1..511";
      }
      description
        "The description of the alarm cause.";
    }
  }
  notification xqos-board-service-mismatch-trap {
    description
      "The service is not supported for the board hardware.";
    leaf entity-physical-index {
      type uint32;
      description
        "Index of an entity.";
    }
    leaf service-id {
      type uint32;
      description
        "Service ID.";
    }
    leaf entity-physical-name {
      type string {
        length "1..511";
      }
      description
        "Entity name.";
    }
    leaf service-name {
      type string {
        length "1..511";
      }
      description
        "Service name.";
    }
    leaf precautions {
      type string {
        length "1..511";
      }
      description
        "Precautions.";
    }
  }
  notification xqos-slot-traffic-congestion {
    description
      "Traffic congestion occurs on the slot, and traffic on all interfaces of the slot may be affected.";
    leaf slot-id {
      type string {
        length "1..32";
      }
      description
        "Slot ID.";
    }
  }
  notification xqos-slot-traffic-congestion-resume {
    description
      "Traffic congestion on the slot is cleared, and traffic on the slot recovers.";
    leaf slot-id {
      type string {
        length "1..32";
      }
      description
        "Slot ID.";
    }
  }
  notification xqos-ipv6-acl-mask-imprecise-alarm {
    description
      "In the IPv6 forwarding scenario, the rule configured in a downstream traffic policy matched only the lower 96 bits of the source IPv6 address.";
  }
  notification xqos-ipv6-acl-mask-imprecise-resume {
    description
      "In the IPv6 forwarding scenario, no rule matching the source IPv6 address existed in a downstream traffic policy.";
  }
  notification xqos-traffic-policy-rule-resource-pre-alarm {
    description
      "The usage of MF classification rules exceeded the pre-warning threshold.";
    leaf slot-id {
      type string {
        length "1..31";
      }
      description
        "Slot ID.";
    }
    leaf threshold {
      type uint32;
      description
        "Threshold.";
    }
    leaf reason-id {
      type int32;
      description
        "The ID of alarm reason.";
    }
    leaf reason-description {
      type string {
        length "1..511";
      }
      description
        "The description of the alarm cause.";
    }
  }
  notification xqos-traffic-policy-rule-resource-pre-alarm-resume {
    description
      "The usage of MF classification rules fell below the pre-warning threshold.";
    leaf slot-id {
      type string {
        length "1..31";
      }
      description
        "Slot ID.";
    }
    leaf reason-id {
      type int32;
      description
        "The ID of alarm reason.";
    }
    leaf reason-description {
      type string {
        length "1..511";
      }
      description
        "The description of the alarm cause.";
    }
  }
  notification qos-resource-overrun-alarm {
    description
      "The resource usage exceeds the alarm threshold.";
    leaf slot-id {
      type uint32;
      description
        "Slot ID.";
    }
    leaf resource-type {
      type string {
        length "1..31";
      }
      description
        "Type of the resource whose usage exceeds the threshold.";
    }
    leaf total-number {
      type uint32;
      description
        "Total number of resources.";
    }
    leaf free-number {
      type uint32;
      description
        "Number of remaining resources.";
    }
    leaf threshold-value {
      type uint32;
      units "%";
      description
        "Resource usage alarm threshold.";
    }
  }
  notification qos-resource-overrun-alarm-resume {
    description
      "The resource usage is lower than the alarm threshold.";
    leaf slot-id {
      type uint32;
      description
        "Slot ID.";
    }
    leaf resource-type {
      type string {
        length "1..31";
      }
      description
        "Type of the resource whose usage exceeds the threshold.";
    }
    leaf total-number {
      type uint32;
      description
        "Total number of resources.";
    }
    leaf free-number {
      type uint32;
      description
        "Number of remaining resources.";
    }
    leaf threshold-value {
      type uint32;
      units "%";
      description
        "Resource usage alarm threshold.";
    }
  }
  notification qos-resource-alarm {
    description
      "Services fail to be delivered due to insufficient resources.";
    leaf slot-id {
      type uint32;
      description
        "Slot ID.";
    }
    leaf resource-type {
      type string {
        length "1..31";
      }
      description
        "Resource type.";
    }
    leaf service-type {
      type string {
        length "1..31";
      }
      description
        "Service type.";
    }
  }
  notification qos-resource-alarm-resume {
    description
      "Resources are sufficient.";
    leaf slot-id {
      type uint32;
      description
        "Slot ID.";
    }
    leaf resource-type {
      type string {
        length "1..31";
      }
      description
        "Resource type.";
    }
    leaf service-type {
      type string {
        length "1..31";
      }
      description
        "Service type.";
    }
  }
  notification qos-port-queue-drop-alarm {
    description
      "Packet loss occurs on an interface.";
    leaf interface-name {
      type string {
        length "1..511";
      }
      description
        "Name of the interface where packet loss occurs.";
    }
    leaf queue-id {
      type uint32;
      description
        "Queue ID.";
    }
    leaf slot-id {
      type string {
        length "0..15";
      }
      description
        "Slot ID.";
    }
    leaf discard-packets {
      type uint64;
      description
        "Number of discarded packets.";
    }
    leaf discard-bytes {
      type uint64;
      description
        "Number of discarded bytes.";
    }
  }
  notification qos-port-queue-drop-alarm-resume {
    description
      "The interface recovered from packet loss.";
    leaf interface-name {
      type string {
        length "1..511";
      }
      description
        "Name of the interface where packet loss occurs.";
    }
    leaf queue-id {
      type uint32;
      description
        "Queue ID.";
    }
    leaf slot-id {
      type string {
        length "0..15";
      }
      description
        "Slot ID.";
    }
    leaf discard-packets {
      type uint64;
      description
        "Number of discarded packets.";
    }
    leaf discard-bytes {
      type uint64;
      description
        "Number of discarded bytes.";
    }
  }
}
