/*
Copyright (C) 2025 Huawei Technologies Co., Ltd. All rights reserved.
*/
module huawei-mac-notify-deviations-ar5710s {
  namespace "urn:huawei:yang:huawei-mac-notify-deviations-ar5710s";
  prefix mac-notify-devs-ar5710s;

  import huawei-mac-notify {
    prefix mac-notify;
  }
  import huawei-mac {
    prefix mac;
  }

  organization
    "Huawei Technologies Co., Ltd.";
  contact
    "Huawei Industrial Base
     Bantian, Longgang
     Shenzhen 518129
     People's Republic of China
     Website: http://www.huawei.com
     Email: support@huawei.com";
  description
    "This module defines deviation statements for huawei-mac-notify module.";

  revision 2025-02-24 {
    description
      "Initial revision.";
    reference "Huawei private.";
  }

  deviation "/mac:mac/mac-notify:mac-notification/mac-notify:full-report-interval-time" {
    deviate not-supported;
  }
  deviation "/mac:mac/mac-notify:mlag-notification" {
    deviate not-supported;
  }
}
