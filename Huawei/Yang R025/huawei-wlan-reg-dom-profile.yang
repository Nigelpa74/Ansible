/*
Copyright (C) 2022-2025 Huawei Technologies Co., Ltd. All rights reserved.
*/
module huawei-wlan-reg-dom-profile {
  yang-version 1;
  namespace "urn:huawei:yang:huawei-wlan-reg-dom-profile";
  prefix wlan-rdp;
  import huawei-extension {
    prefix ext;
  }
  import huawei-wlan-ap {
    prefix wlan-ap;
  }
  import huawei-wlan-ap-group-profile {
    prefix wlan-apg;
  }
  organization
    "Huawei Technologies Co., Ltd.";
  contact
    "Huawei Industrial Base
     Bantian, Longgang
     Shenzhen 518129
     People's Republic of China
     Website: http://www.huawei.com
     Email: support@huawei.com";
  description
    "Wlan regulatory service package.";
  revision 2025-09-05 {
    description
      "Add PY country code.";
    reference
      "Huawei private.";
  }
  revision 2025-08-15 {
    description
      "Add dbs config.";
    reference
      "Huawei private.";
  }
  revision 2025-07-15 {
    description
      "Add dca-5g-bandwidth 160mHz.";
    reference
      "Huawei private.";
  }
  revision 2024-11-28 {
    description
      "Add BD and MV country code.";
    reference
      "Huawei private.";
  }
  revision 2024-10-30 {
    description
      "Add CI country code.";
    reference
      "Huawei private.";
  }
  revision 2024-09-04 {
    description
      "Add DCA channel dynamic default.";
    reference
      "Huawei private.";
  }
  revision 2024-05-17 {
    description
      "The default profile cannot be deleted.";
    reference
      "Huawei private.";
  }
  revision 2024-03-19 {
    description
      "Add profile name pattern.";
    reference
      "Huawei private.";
  }
  revision 2024-03-11 {
    description
      "Add dca-channel set pattern.";
    reference
      "Huawei private.";
  }
  revision 2024-03-08 {
    description
      "Add profile name pattern.";
    reference
      "Huawei private.";
  }
  revision 2023-11-20 {
    description
      "Fix domain word spelling mistake.";
    reference
      "Huawei private.";
  }
  revision 2023-01-10 {
    description
      "Add KE country code.";
    reference
      "Huawei private.";
  }
  revision 2022-12-29 {
    description
      "Add dca 320mhz.";
    reference
      "Huawei private.";
  }
  revision 2022-11-21 {
    description
      "Modify channel-load-mode description.";
    reference
      "Huawei private.";
  }
  revision 2022-08-06 {
    description
      "Initial revision.";
    reference
      "Huawei private.";
  }
  grouping ap-binding-regular-domain-instance {
    description
      "Configure regular domain profile to ap.";
    container ap-binding-regular-domain-profile {
      leaf binding-regular-domain-profile {
        type leafref {
          path "/wlan-rdp:wlan-reg-dom-profile/wlan-rdp:regulatory-domain-profiles/wlan-rdp:regulatory-domain-profile/wlan-rdp:profile-name";
        }
        description
          "Binding a regular domain profile to a AP.";
      }
      description
        "Configure regular domain profile to ap.";
    }
  }
  grouping grp-binding-regular-domain-instance {
    description
      "Configure regular domain profile to ap-group.";
    container grp-binding-regular-domain-profile {
      leaf binding-regular-domain-profile {
        type leafref {
          path "/wlan-rdp:wlan-reg-dom-profile/wlan-rdp:regulatory-domain-profiles/wlan-rdp:regulatory-domain-profile/wlan-rdp:profile-name";
        }
        default "default";
        description
          "Binding a regular domain profile.";
      }
      description
        "Configure a regular domain profile.";
    }
  }
  container wlan-reg-dom-profile {
    description
      "Configure wlan-regulatory-domain-profile.";
    container regulatory-domain-profiles {
      description
        "List of wlan-regulatory-domain-profile.";
      list regulatory-domain-profile {
        ext:generated-by "system" {
          description
            "The default profile is generated by system.";
          ext:filter "profile-name='default'";
        }
        ext:operation-exclude "delete" {
          ext:filter "profile-name='default'";
          description
            "The default profile cannot be deleted.";
        }
        key "profile-name";
        description
          "Configure a regulatory domain profile contains various settings such as the country code, which take effect on APs using the regulatory domain profile.";
        leaf profile-name {
          type string {
            length "1..35";
            pattern '[^\s?]+';
            pattern '[!-~]+';
          }
          description
            "Regulate domain profile name.";
        }
        leaf country-code {
          type enumeration {
            enum "AE" {
              value 0;
              description
                "UNITED ARAB EMIRATES.";
            }
            enum "AM" {
              value 1;
              description
                "ARMENIA.";
            }
            enum "AR" {
              value 2;
              description
                "ARGENTINA.";
            }
            enum "AT" {
              value 3;
              description
                "AUSTRIA.";
            }
            enum "AU" {
              value 4;
              description
                "AUSTRALIA.";
            }
            enum "AZ" {
              value 5;
              description
                "AZERBAIJAN.";
            }
            enum "BE" {
              value 6;
              description
                "BELGIUM.";
            }
            enum "BG" {
              value 7;
              description
                "BULGARIA.";
            }
            enum "BH" {
              value 8;
              description
                "BAHRAIN.";
            }
            enum "BN" {
              value 9;
              description
                "BRUNEI DARUSSALAM.";
            }
            enum "BO" {
              value 10;
              description
                "BOLIVIA.";
            }
            enum "BR" {
              value 11;
              description
                "BRAZIL.";
            }
            enum "BY" {
              value 12;
              description
                "BELARUS.";
            }
            enum "BZ" {
              value 13;
              description
                "BELIZE.";
            }
            enum "CA" {
              value 14;
              description
                "CANADA.";
            }
            enum "CH" {
              value 15;
              description
                "SWITZERLAND.";
            }
            enum "CL" {
              value 16;
              description
                "CHILE.";
            }
            enum "CN" {
              value 17;
              description
                "CHINA.";
            }
            enum "CO" {
              value 18;
              description
                "COLOMBIA.";
            }
            enum "CR" {
              value 19;
              description
                "COSTA RICA.";
            }
            enum "CY" {
              value 20;
              description
                "CYPRUS.";
            }
            enum "CZ" {
              value 21;
              description
                "CZECH REPUBLIC.";
            }
            enum "DE" {
              value 22;
              description
                "GERMANY.";
            }
            enum "DK" {
              value 23;
              description
                "DENMARK.";
            }
            enum "DO" {
              value 24;
              description
                "DOMINICAN REPUBLIC.";
            }
            enum "EC" {
              value 25;
              description
                "ECUADOR.";
            }
            enum "EE" {
              value 26;
              description
                "ESTONIA.";
            }
            enum "EG" {
              value 27;
              description
                "EGYPT.";
            }
            enum "ES" {
              value 28;
              description
                "SPAIN.";
            }
            enum "FI" {
              value 29;
              description
                "FINLAND.";
            }
            enum "FR" {
              value 30;
              description
                "FRANCE.";
            }
            enum "GB" {
              value 31;
              description
                "UNITED KINGDOM.";
            }
            enum "GE" {
              value 32;
              description
                "GEORGIA.";
            }
            enum "GR" {
              value 33;
              description
                "GREECE.";
            }
            enum "GT" {
              value 34;
              description
                "GUATEMALA.";
            }
            enum "HK" {
              value 35;
              description
                "HONG KONG,SPECIAL ADMINISTRATIVE REGION OF CHINA.";
            }
            enum "HN" {
              value 36;
              description
                "HONDURAS.";
            }
            enum "HR" {
              value 37;
              description
                "CROATIA.";
            }
            enum "HU" {
              value 38;
              description
                "HUNGARY.";
            }
            enum "ID" {
              value 39;
              description
                "INDONESIA.";
            }
            enum "IE" {
              value 40;
              description
                "IRELAND.";
            }
            enum "IL" {
              value 41;
              description
                "ISRAEL.";
            }
            enum "IN" {
              value 42;
              description
                "INDIA.";
            }
            enum "IQ" {
              value 43;
              description
                "IRAQ.";
            }
            enum "IR" {
              value 44;
              description
                "IRAN.";
            }
            enum "IS" {
              value 45;
              description
                "ICELAND.";
            }
            enum "IT" {
              value 46;
              description
                "ITALY.";
            }
            enum "JO" {
              value 47;
              description
                "JORDAN.";
            }
            enum "JP" {
              value 48;
              description
                "JAPAN.";
            }
            enum "KP" {
              value 49;
              description
                "DEMOCRATIC PEOPLE'S REPUBLIC OF KOREA.";
            }
            enum "KR" {
              value 50;
              description
                "REPUBLIC OF KOREA.";
            }
            enum "KW" {
              value 51;
              description
                "KUWAIT.";
            }
            enum "KZ" {
              value 52;
              description
                "KAZAKHSTAN.";
            }
            enum "LB" {
              value 53;
              description
                "LEBANON.";
            }
            enum "LI" {
              value 54;
              description
                "LIECHTENSTEIN.";
            }
            enum "LK" {
              value 55;
              description
                "SRI LANKA.";
            }
            enum "LT" {
              value 56;
              description
                "LITHUANIA.";
            }
            enum "LU" {
              value 57;
              description
                "LUXEMBOURG.";
            }
            enum "LV" {
              value 58;
              description
                "LATVIA.";
            }
            enum "MA" {
              value 59;
              description
                "MOROCCO.";
            }
            enum "MC" {
              value 60;
              description
                "MONACO.";
            }
            enum "MK" {
              value 61;
              description
                "MACEDONIA.";
            }
            enum "MO" {
              value 62;
              description
                "MACAU,SPECIAL ADMINISTRATIVE REGION OF CHINA.";
            }
            enum "MT" {
              value 63;
              description
                "MALTA.";
            }
            enum "MX" {
              value 64;
              description
                "MEXICO.";
            }
            enum "MY" {
              value 65;
              description
                "MALAYSIA.";
            }
            enum "NG" {
              value 66;
              description
                "NIGERIA.";
            }
            enum "NL" {
              value 67;
              description
                "NETHERLANDS.";
            }
            enum "NO" {
              value 68;
              description
                "NORWAY.";
            }
            enum "NZ" {
              value 69;
              description
                "NEW ZEALAND.";
            }
            enum "OM" {
              value 70;
              description
                "OMAN.";
            }
            enum "PA" {
              value 71;
              description
                "PANAMA.";
            }
            enum "PE" {
              value 72;
              description
                "PERU.";
            }
            enum "PH" {
              value 73;
              description
                "PHILIPPINES.";
            }
            enum "PK" {
              value 74;
              description
                "PAKISTAN.";
            }
            enum "PL" {
              value 75;
              description
                "POLAND.";
            }
            enum "PR" {
              value 76;
              description
                "PUERTO RICO.";
            }
            enum "PT" {
              value 77;
              description
                "PORTUGAL.";
            }
            enum "QA" {
              value 78;
              description
                "QATAR.";
            }
            enum "RO" {
              value 79;
              description
                "ROMANIA.";
            }
            enum "RS" {
              value 80;
              description
                "SERBIA.";
            }
            enum "RU" {
              value 81;
              description
                "RUSSIA.";
            }
            enum "SA" {
              value 82;
              description
                "SAUDI ARABIA.";
            }
            enum "SE" {
              value 83;
              description
                "SWEDEN.";
            }
            enum "SG" {
              value 84;
              description
                "SINGAPORE.";
            }
            enum "SI" {
              value 85;
              description
                "SLOVENIA.";
            }
            enum "SK" {
              value 86;
              description
                "SLOVAKIA.";
            }
            enum "SV" {
              value 87;
              description
                "EL SALVADOR.";
            }
            enum "SY" {
              value 88;
              description
                "SYRIA.";
            }
            enum "TH" {
              value 89;
              description
                "THAILAND.";
            }
            enum "TN" {
              value 90;
              description
                "TUNISIA.";
            }
            enum "TR" {
              value 91;
              description
                "TURKEY.";
            }
            enum "TT" {
              value 92;
              description
                "TRINIDAD & TOBAGO.";
            }
            enum "TW" {
              value 93;
              description
                "TAIWAN,PROVINCE OF CHINA.";
            }
            enum "UA" {
              value 94;
              description
                "UKRAINE.";
            }
            enum "US" {
              value 95;
              description
                "UNITED STATES.";
            }
            enum "UY" {
              value 96;
              description
                "URUGUAY.";
            }
            enum "UZ" {
              value 97;
              description
                "UZBEKISTAN.";
            }
            enum "VE" {
              value 98;
              description
                "VENEZUELA.";
            }
            enum "VN" {
              value 99;
              description
                "VIET NAM.";
            }
            enum "YE" {
              value 100;
              description
                "YEMEN.";
            }
            enum "ZA" {
              value 101;
              description
                "SOUTH AFRICA.";
            }
            enum "ZW" {
              value 102;
              description
                "ZIMBABWE.";
            }
            enum "KE" {
              value 103;
              description
                "KENYA.";
            }
            enum "CI" {
              value 104;
              description
                "COTE D'IVOIRE.";
            }
            enum "BD" {
              value 105;
              description
                "BANGLADESH.";
            }
            enum "MV" {
              value 106;
              description
                "MALDIVES.";
            }
            enum "PY" {
              value 107;
              description
                "PARAGUAY.";
            }
          }
          default "CN";
          description
            "Configure country-code.";
        }
        leaf dca-channel-5g-bandwidth {
          type enumeration {
            enum "20mhz" {
              value 0;
              description
                "20Mhz.";
            }
            enum "40mhz" {
              value 1;
              description
                "40Mhz.";
            }
            enum "80mhz" {
              value 2;
              description
                "80Mhz.";
            }
            enum "auto" {
              value 3;
              description
                "Auto.";
            }
            enum "160mhz" {
              value 4;
              description
                "160Mhz.";
            }
          }
          default "auto";
          description
            "Set dca-channel-5g.";
        }
        leaf dca-channel-6g-bandwidth {
          type enumeration {
            enum "20mhz" {
              value 0;
              description
                "20Mhz.";
            }
            enum "40mhz" {
              value 1;
              description
                "40Mhz.";
            }
            enum "80mhz" {
              value 2;
              description
                "80Mhz.";
            }
            enum "160mhz" {
              value 3;
              description
                "160Mhz.";
            }
            enum "auto" {
              value 4;
              description
                "Auto.";
            }
            enum "320mhz" {
              value 5;
              description
                "320mhz.";
            }
          }
          default "auto";
          description
            "Set dca-channel-6g.";
        }
        leaf dbs-initial-bandwidth {
          type enumeration {
            enum "20mhz" {
              value 0;
              description
                "Configure the initial bandwidth of DBS to 20 MHz.";
            }
            enum "40mhz" {
              value 1;
              description
                "Configure the initial bandwidth of DBS to 40 MHz.";
            }
            enum "80mhz" {
              value 2;
              description
                "Configure the initial bandwidth of DBS to 80 MHz.";
            }
            enum "160mhz" {
              value 3;
              description
                "Configure the initial bandwidth of DBS to 160 MHz.";
            }
            enum "auto" {
              value 4;
              description
                "Set the initial bandwidth of DBS to automatic.";
            }
          }
          default "auto";
          description
            "Set the initial bandwidth of DBS.";
        }
        leaf dbs-sensitivity {
          type enumeration {
            enum "balance" {
              value 0;
              description
                "Set the DBS sensitivity to balanced.";
            }
            enum "high-bandwidth" {
              value 1;
              description
                "Configure DBS sensitivity to high bandwidth.";
            }
            enum "low-latency" {
              value 2;
              description
                "Configure DBS sensitivity for low latency.";
            }
          }
          default "balance";
          description
            "Set the DBS sensitivity.";
        }
        leaf dca-channel-2g-set {
          type string {
            length "1..256";
            pattern '(\d+,)*\d+';
          }
          ext:dynamic-default;
          description
            "Config dca 2g channel-set. Customers can select multiple channels and each channel is separated by ',' such as 1,2,3. The default set is 1,6,11.";
        }
        leaf dca-channel-5g-set {
          type string {
            length "1..256";
            pattern '(\d+,)*\d+';
          }
          ext:dynamic-default;
          description
            "Config dca 5g channel-set. Customers can select multiple channels and each channel is separated by ',' such as 1,2,3. The default set include all channels.";
        }
        leaf dca-channel-6g-set {
          type string {
            length "1..256";
            pattern '(\d+,)*\d+';
          }
          ext:dynamic-default;
          description
            "Config dca 6g channel-set. Customers can select multiple channels and each channel is separated by ',' such as 1,2,3. The default set include all channels.";
        }
        leaf channel-load-mode {
          type enumeration {
            enum "outdoor" {
              value 0;
              description
                "Set the AP channel mode to outdoor mode.";
            }
            enum "indoor" {
              value 1;
              description
                "Restores the AP channel mode to indoor mode.";
            }
          }
          default "outdoor";
          description
            "Set the AP channel mode to indoor mode or outdoor mode.
             In scenarios where indoor and outdoor boundaries are unclear, such as subway and train platforms, it is recommended that outdoor APs be deployed.
             When a large volume of data is transmitted, outdoor APs in outdoor channel mode have no sufficient channels to meet data transmission requirements.
            In this case, you can run the channel-load-mode indoor command to set the channel mode of the APs to indoor mode, so that data can be transmitted on more channels.";
        }
      }
    }
  }
  augment /wlan-ap:wlan-ap/wlan-ap:ap-instances/wlan-ap:ap-instance {
    uses wlan-rdp:ap-binding-regular-domain-instance;
    description
      "Configure regular-domain profile to ap.";
  }
  augment "/wlan-apg:wlan-ap-group-profile/wlan-apg:ap-group-profiles/wlan-apg:ap-group-profile" {
    uses wlan-rdp:grp-binding-regular-domain-instance;
    description
      "Configure regular-domain profile to ap-group.";
  }
  ext:task-name "wm";
}
