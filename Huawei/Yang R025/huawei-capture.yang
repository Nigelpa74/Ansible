/*
Copyright (C) 2020-2025 Huawei Technologies Co., Ltd. All rights reserved.
*/
module huawei-capture {
  yang-version 1;
  namespace "urn:huawei:yang:huawei-capture";
  prefix capture;
  import huawei-extension {
    prefix ext;
  }
  import huawei-ifm {
    prefix ifm;
  }
  import huawei-vlan {
    prefix vlan;
  }
  import huawei-acl {
    prefix acl;
  }
  import ietf-yang-types {
    prefix yang;
  }
  import huawei-pub-type {
    prefix pub-type;
  }
  import huawei-devm {
    prefix devm;
  }
  organization
    "Huawei Technologies Co., Ltd.";
  contact
    "Huawei Industrial Base
    Bantian, Longgang
    Shenzhen 518129
    People's Republic of China
    Website: http://www.huawei.com
    Email: support@huawei.com";
  description
    "Network capture.";
  revision 2025-08-19 {
    description
      "Add new typedef gtp-inner.";
    reference
      "Huawei private.";
  }
  revision 2025-08-07 {
    description
      "Change the line ending format to Unix-style.";
    reference
      "Huawei private.";
  }
  revision 2025-06-13 {
    description
      "Add new container.";
    reference
      "Huawei private.";
  }
  revision 2025-02-27 {
    description
      "Add new typedef vxlan-inner.";
    reference
      "Huawei private.";
  }
  revision 2024-09-18 {
    description
      "Add nodes offset of capture-packet.";
    reference
      "Huawei private.";
  }
  revision 2024-07-23 {
    description
      "Add soft-forward-drop-type and its enum.";
    reference
      "Huawei private.";
  }
  revision 2024-06-23 {
    description
      "Add new leaf.";
    reference
      "Huawei private.";
  }
  revision 2024-05-31 {
    description
      "Modify stop-capture and no-ip-packet description.";
    reference
      "Huawei private.";
  }
  revision 2024-02-28 {
    description
      "Add new type packet-match-type, add new nodes in capture and capture-packet.";
    reference
      "Huawei private.";
  }
  revision 2024-01-10 {
    description
      "Add no-in-packet in capture-packet interface.";
    reference
      "Huawei private.";
  }
  revision 2023-07-28 {
    description
      "Add soft-forward and soft-forward drop.";
    reference
      "Huawei private.";
  }
  revision 2023-01-17 {
    description
      "Add new nodes in capture-packet.";
    reference
      "Huawei private.";
  }
  revision 2022-07-13 {
    description
      "Modify packet-number range.";
    reference
      "Huawei private.";
  }
  revision 2022-05-05 {
    description
      "Modify time-out range, remove unused notification.";
    reference
      "Huawei private.";
  }
  revision 2020-01-11 {
    description
      "Initial revision.";
    reference
      "Huawei private.";
  }
  ext:task-name "capture";
  typedef tag-format {
    type enumeration {
      enum "none" {
        value 0;
        description
          "VXLAN overlay packets without VLAN tag.";
      }
      enum "single" {
        value 1;
        description
          "VXLAN overlay packets with single VLAN tag.";
      }
    }
    description
      "Tag format of VXLAN overlay packets.";
  }
  typedef result {
    type enumeration {
      enum "success" {
        value 0;
        description
          "The packet obtain result is successful.";
      }
      enum "fail" {
        value 1;
        description
          "The packet obtain result is fail.";
      }
    }
    description
      "Packet obtain result.";
  }
  typedef capture-index {
    type uint32 {
      range "1..8";
    }
    description
      "Index of the packet obtain instance.";
  }
  typedef direction {
    type enumeration {
      enum "inbound" {
        value 1;
        description
          "Inbound.";
      }
      enum "outbound" {
        value 2;
        description
          "Outbound.";
      }
      enum "both" {
        value 3;
        description
          "Both.";
      }
    }
    description
      "Packet obtain direction.";
  }
  typedef packet-header-status {
    type enumeration {
      enum "stopped" {
        value 0;
        description
          "Stop.";
      }
      enum "running" {
        value 1;
        description
          "Running.";
      }
    }
    description
      "Packet obtain status.";
  }
  typedef packet-header-link-type {
    type enumeration {
      enum "none" {
        value 0;
        description
          "Interface of linktype.";
      }
      enum "ethernet" {
        value 1;
        description
          "Ethernet of link type.";
      }
      enum "ppp" {
        value 2;
        description
          "PPP protocol of link type.";
      }
      enum "hdlc" {
        value 3;
        description
          "HDLC protocol of link type.";
      }
      enum "atm" {
        value 4;
        description
          "ATM of link type.";
      }
    }
    description
      "Packet header link type.";
  }
  typedef packet-match-type {
    type enumeration {
      enum "ip-srv6-inner" {
        value 1;
        description
          "IP SRv6 inner.";
      }
      enum "vxlan-inner" {
        value 3;
        description
          "Vxlan inner.";
      }
      enum "gtp-inner" {
        value 4;
        description
          "Gtp inner.";
      }
    }
    description
      "Packet match type.";
  }
  typedef acl-family-type {
    type enumeration {
      enum "acl" {
        value 1;
        description
          "ACL IPv4 and L2.";
      }
      enum "acl-ipv6" {
        value 2;
        description
          "ACL IPv6.";
      }
    }
    description
      "ACL family.";
  }
  typedef drop-type {
    type enumeration {
      enum "arp-nd" {
        value 1;
        description
          "Packet loss due to arp-nd.";
      }
      enum "ase" {
        value 2;
        description
          "Packet loss due to ase.";
      }
      enum "atk" {
        value 3;
        description
          "Packet loss due to atk.";
      }
      enum "atk-v6" {
        value 4;
        description
          "Packet loss due to atk-v6.";
      }
      enum "fib" {
        value 5;
        description
          "Packet loss due to fib.";
      }
      enum "frag" {
        value 6;
        description
          "Packet loss due to frag.";
      }
      enum "frag-v6" {
        value 7;
        description
          "Packet loss due to frag-v6.";
      }
      enum "gre" {
        value 8;
        description
          "Packet loss due to gre.";
      }
      enum "gtp" {
        value 9;
        description
          "Packet loss due to gtp.";
      }
      enum "hrp" {
        value 10;
        description
          "Packet loss due to hrp.";
      }
      enum "if-invalid" {
        value 11;
        description
          "Packet loss due to if-invalid.";
      }
      enum "ipsec" {
        value 12;
        description
          "Packet loss due to ipsec.";
      }
      enum "mpls" {
        value 13;
        description
          "Packet loss due to MPLS.";
      }
      enum "nat" {
        value 14;
        description
          "Packet loss due to nat.";
      }
      enum "other" {
        value 15;
        description
          "Packet loss due to other.";
      }
      enum "pkt-decode" {
        value 16;
        description
          "Packet loss due to pkt-decode.";
      }
      enum "pkt-decode-v6" {
        value 17;
        description
          "Packet loss due to pkt-decode-v6.";
      }
      enum "rate-limit" {
        value 18;
        description
          "Packet loss due to rate-limit.";
      }
      enum "sec-policy" {
        value 19;
        description
          "Packet loss due to sec-policy.";
      }
      enum "session" {
        value 20;
        description
          "Packet loss due to session.";
      }
      enum "slb" {
        value 21;
        description
          "Packet loss due to slb.";
      }
      enum "spr" {
        value 22;
        description
          "Packet loss due to spr.";
      }
      enum "srv6" {
        value 23;
        description
          "Packet loss due to srv6.";
      }
      enum "sslvpn" {
        value 24;
        description
          "Packet loss due to sslvpn.";
      }
      enum "sync" {
        value 25;
        description
          "Packet loss due to sync.";
      }
      enum "vpn" {
        value 26;
        description
          "Packet loss due to vpn.";
      }
      enum "blackhole-mac" {
        value 27;
        description
          "Packet loss due to blackhole-mac.";
      }
      enum "blackhole-route" {
        value 28;
        description
          "Packet loss due to blackhole-route.";
      }
      enum "ttl-exceed" {
        value 29;
        description
          "Packet loss due to ttl-exceed.";
      }
      enum "mac-flapping" {
        value 30;
        description
          "Packet loss due to mac-flapping.";
      }
    }
    description
      "Drop type of drop packets.";
  }
  container capture {
    description
      "Forwarding packet headers information.";
    container forwarding-bgp {
      presence "Enable/disable capture-forwarding bgp";
      description 
        "Enable/disable the function of capturing BGP keepalive packets.";
    }
    container capture-instances {
      config false;
      description
        "List of obtain packet headers instance.";
      list capture-instance {
        key "instance-id";
        description
          "Operational data of obtain packet headers instance.";
        leaf instance-id {
          type uint8 {
            range "1..8";
          }
          description
            "Instance ID.";
        }
        leaf inbound-instance {
          type uint32;
          description
            "Inbound instance.";
        }
        leaf outbound-instance {
          type uint32;
          description
            "Outbound instance.";
        }
        leaf total-instance {
          type uint32;
          description
            "Total instance statistic.";
        }
        leaf status {
          type packet-header-status;
          description
            "Obtain packet headers status.";
        }
        leaf timeout {
          type uint32 {
            range "1..86400";
          }
          units "s";
          description
            "Timeout.";
        }
        leaf record-packet-number {
          type uint32 {
            range "1..6000";
          }
          description
            "Record packet number.";
        }
        leaf total-memory-size {
          type uint32;
          units "MB";
          description
            "Record packet size.";
        }
        leaf obtain-packet-number {
          type uint32;
          description
            "Obtain packet number.";
        }
        leaf obtain-packet-size {
          type uint32;
          units "Byte";
          description
            "Obtain packet size.";
        }
        leaf saved-packet-number {
          type uint32;
          description
            "Saved packet number.";
        }
        leaf saved-packet-size {
          type uint32;
          units "Byte";
          description
            "Saved packet size.";
        }
        leaf delete-packet-number {
          type uint32;
          description
            "Delete packet number.";
        }
        leaf delete-packet-size {
          type uint32;
          units "Byte";
          description
            "Delete packet size.";
        }
        leaf first-packet-time {
          type yang:date-and-time;
          description
            "First packet time.";
        }
        leaf last-packet-time {
          type yang:date-and-time;
          description
            "Last packet time.";
        }
        leaf acl {
          type string {
            length "1..63";
          }
          description
            "Acl number or name.";
        }
        leaf acl-family {
          type acl-family-type;
          description
            "ACL or ACL-IPv6.";
        }
        leaf memory-packet-number {
          type uint32;
          description
            "Memory packet number.";
        }
        leaf remain-time {
          type uint32 {
            range "1..86400";
          }
          units "s";
          description
            "Remain time.";
        }
        leaf remain-time-delete {
          type uint32 {
            range "1..86400";
          }
          units "s";
          description
            "Remain time.";
        }
        leaf packet-device-name {
          type string {
            length "5..64";
          }
          description
            "Packet device name.";
        }
        leaf file-name {
          type string {
            length "5..64";
          }
          description
            "File name.";
        }
        leaf file-length {
          type uint8;
          units "MB";
          default "2";
          description
            "File length.";
        }
        leaf link-type {
          type packet-header-link-type;
          description
            "Link type.";
        }
        leaf interface-name {
          type leafref {
              path "/ifm:ifm/ifm:interfaces/ifm:interface/ifm:name";
          }
          description
            "Interface name.";
        }
        leaf direction {
          type direction;
          description
            "Direction.";
        }
        leaf packet-match-type {
          type packet-match-type;
          description
            "Packet match type.";
        }
      }
    }
  }
  rpc capture-packet {
    description
      "To start capture.";
    ext:node-ref "/capture:capture/capture:capture-instances";
    input  {
      leaf local-host {
        type boolean;
        default "false";
        description
          "Obtain packets sent to the CPU.";
      }
	  leaf soft-forward {
        type boolean;
        default "false";
        description
          "Obtain packets for soft forward.";
      }
	  leaf soft-forward-drop {
        type boolean;
        default "false";
        description
          "Obtain packets for soft forward drop.";
      }
	  leaf soft-forward-drop-type {
        when "../soft-forward-drop='true'";
        type drop-type;
        description
          "Drop type of packets from soft forward drop.";
      }
      choice tunnel {
        description
          "Configure the tunnel type for packet obtain.";
        case normal {
          description
            "Normal packet.";
          leaf vlan-id {
            type vlan:vlan-id;
            description
              "Outer VLAN ID.";
          }
          leaf cvlan-id {
            type vlan:vlan-id;
            description
              "Inner VLAN ID.";
          }
        }
        case vxlan {
          description
            "Vxlan packet.";
          leaf vxlan {
            type empty;
            mandatory true;
            description
              "Indicates that only VXLAN packets are captured.";
          }
          leaf vni-id {
            type uint32 {
              range "1..16777215";
            }
            description
              "VXLAN network identifier value.";
          }
          leaf tag-format {
            type tag-format;
            description
              "Tag format for vxlan packet.";
          }
        }
      }
      choice acl {
        description
          "Configure the acl for packet obtain.";
        case acl {
          description
            "IPv4 acl.";
          leaf acl-name {
            type leafref {
              path "/acl:acl/acl:groups/acl:group/acl:identity";
            }
            description
              "Acl number or name.";
          }
          leaf packet-match {
            type packet-match-type;
            description
              "Packet match type.";
          }
        }
        case acl6 {
          description
            "IPv6 acl.";
          leaf acl6-name {
            type leafref {
              path "/acl:acl/acl:group6s/acl:group6/acl:identity";
            }
            description
              "Acl number or name.";
          }
          leaf packet-match-v6 {
            type packet-match-type;
            description
              "Packet match type.";
          }
        }
        case no-ip-packet {
          description
            "Not ip packet.";
          leaf no-ip-packet {
            type empty;
            description
              "Not ip packet.";
          }
        }
      }
      leaf-list interface-name {
        type leafref {
          path "/ifm:ifm/ifm:interfaces/ifm:interface/ifm:name";
        }
        description
          "Interface name for packet obtain.";
      }
      leaf packet-number {
        type uint32 {
          range "1..6000";
        }
        default "100";
        description
          "Maximum number of packets to be captured.";
      }
      leaf packet-length {
        type uint16 {
          range "20..64";
        }
        units "Byte";
        default "64";
        description
          "Maximum packet length to be captured.";
      }
	  leaf sample-rate {
        type uint32 {
          range "1..10000";
        }
        default "100";
        description
          "Sample rate to be captured.";
      }
      leaf timeout {
        type uint32 {
          range "0..86400";
        }
        units "s";
        default "60";
        description
          "Timeout interval.";
      }
      leaf file-name {
        type string {
          length "5..64";
        }
        default "capture.cap";
        description
          "Name of the file for saving the obtain packets.";
      }
      leaf clear-payload {
        type boolean;
        default "false";
        description
          "Sets the data content of captured packets to 0. Only the data content of TCP and UDP packets can be set to 0.";
      }
      leaf direction {
        type direction;
        description
          "Packet obtain direction.";
      }
      choice vlan-mode {
        description
          "VLAN for packet obtain.";
        case vlan {
          description
            "VLAN for packet obtain.";
          leaf vlan-begin {
            type vlan:vlan-id;
            mandatory true;
            description
              "Begin VLAN ID for packet obtain.";
          }
          leaf vlan-end {
            type vlan:vlan-id;
            mandatory true;
            description
              "End VLAN ID for packet obtain.";
          }
        }
        case pe-and-ce {
          description
            "Pe and Ce VLAN for packet obtain.";
          leaf pe-vlan {
            type vlan:vlan-id;
            mandatory true;
            description
              "Pe VLAN ID for packet obtain.";
          }
          leaf ce-vlan-begin {
            type vlan:vlan-id;
            mandatory true;
            description
              "Begin inner VLAN ID for packet obtain.";
          }
          leaf ce-vlan-end {
            type vlan:vlan-id;
            mandatory true;
            description
              "End inner VLAN ID for packet obtain.";
          }
        }
      }
      leaf file-size {
        type uint8;
        units "MB";
        default "2";
        description
          "File size.";
      }
      leaf buffer-only {
        type boolean;
        default "false";
        description
          "Type buffer only.";
      }
      leaf overwrite {
        type boolean;
        default "false";
        description
          "Overwrite the buffer.";
      }
      leaf offset-value {
        type uint16 {
          range "0..200";
        }
        units "Byte";
        description
          "Offset value.";
      }
      leaf match-value {
        when "../offset-value";
        type pub-type:hex-binary;
        mandatory true;
        description
          "Match value.";
      }
      leaf match-value-second {
        when "../offset-value";
        type pub-type:hex-binary;
        description
          "Second match value.";
      }
      leaf offset-value1 {
        type uint32 {
          range "0..60";
        }
        units "Byte";
        description
          "Offset value.";
      }
      leaf match-value1 {
        when "../offset-value1";
        type pub-type:hex-binary;
        mandatory true;
        description
          "Match value.";
      }
      leaf match-mask1 {
        when "../offset-value1";
        type pub-type:hex-binary;
        mandatory true;
        description
          "Match mask.";
      }
      leaf offset-value2 {
        when "../offset-value1";
        type uint32 {
          range "0..60";
        }
        units "Byte";
        description
          "Offset value.";
      }
      leaf match-value2 {
        when "../offset-value2";
        type pub-type:hex-binary;
        mandatory true;
        description
          "Match value.";
      }
      leaf match-mask2 {
        when "../offset-value2";
        type pub-type:hex-binary;
        mandatory true;
        description
          "Match mask.";
      }
      leaf offset-value3 {
        when "../offset-value2";
        type uint32 {
          range "0..60";
        }
        units "Byte";
        description
          "Offset value.";
      }
      leaf match-value3 {
        when "../offset-value3";
        type pub-type:hex-binary;
        mandatory true;
        description
          "Match value.";
      }
      leaf match-mask3 {
        when "../offset-value3";
        type pub-type:hex-binary;
        mandatory true;
        description
          "Match mask.";
      }
      leaf offset-value4 {
        when "../offset-value3";
        type uint32 {
          range "0..60";
        }
        units "Byte";
        description
          "Offset value.";
      }
      leaf match-value4 {
        when "../offset-value4";
        type pub-type:hex-binary;
        mandatory true;
        description
          "Match value.";
      }
      leaf match-mask4 {
        when "../offset-value4";
        type pub-type:hex-binary;
        mandatory true;
        description
          "Match mask.";
      }
    }
    output  {
      leaf capture-index {
        type capture-index;
        description
          "Index of the packet obtain instance.";
      }
    }
  }
  rpc stop-capture {
    description
      "To stop capture.";
    ext:node-ref "/capture:capture/capture:capture-instances";
    input  {
      choice mode {
        mandatory true;
        description
          "Stop mode.";
        case all {
          description
            "All the packet obtain instance.";
          leaf all {
            type empty;
            description
              "All the packet obtain instance.";
          }
        }
        case index {
          description
            "The packet obtain instance with a specified index.";
          leaf capture-index {
            type capture-index;
            description
              "Index of the packet obtain instance.";
          }
        }
        case interface {
          description
            "The packet obtain instance with a specified interface.";
          leaf-list interface-name {
            type leafref {
              path "/ifm:ifm/ifm:interfaces/ifm:interface/ifm:name";
            }
            min-elements 1;
            max-elements 8;
            description
              "Interface name for packet obtain.";
          }
          leaf direction {
            type direction;
            description
              "Packet obtain direction.";
          }
        }
      }
    }
  }
  rpc free-packet-header-obtain {
    description
      "To free instance.";
    ext:node-ref "/capture:capture/capture:capture-instances";
    input {
      leaf instance-id {
        type uint8;
        description
          "Instance ID.";
      }
    }
  }
  augment "/devm:devm/devm:lpu-boards/devm:lpu-board" {
    description
      "Capture forward.";
    container capture {
      description
        "Configure forwarding packet headers information.";
      container forwarding-bgp {
        presence "Enable/disable capture-forwarding bgp";
        description 
          "Enable/disable the function of capturing BGP keepalive packets.";
      }
    }
  }
  augment "/devm:devm/devm:mpu-boards/devm:mpu-board" {
    description
      "Capture forward.";
    container capture {
      description
        "Configure forwarding packet headers information.";
      container forwarding-bgp {
        presence "Enable/disable capture-forwarding bgp";
        description 
          "Enable/disable the function of capturing BGP keepalive packets.";
      }
    }
  }
}
