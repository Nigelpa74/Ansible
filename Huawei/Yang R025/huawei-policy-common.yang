/******************************************************
 * Copyright (C) 2020-2025 Huawei Technologies Co., Ltd. All rights reserved.
 * Module description & tree structure:
 ***************************************************/
module huawei-policy-common {
  namespace "urn:huawei:yang:huawei-policy-common";
  prefix "hw-policy-common";

  import ietf-inet-types {
    prefix inet;
  }

  import huawei-pub-type {
    prefix hw-pub-type;
  }

  import huawei-address-set {
    prefix hw-address-set;
  }

  import huawei-domain-set {
    prefix hw-domain-set;
  }

  import huawei-nac-group {
    prefix hw-nac-group;
  }

  import huawei-extension {
    prefix ext;
  }

  import huawei-aaa {
    prefix aaa;
  }

  organization
    "Huawei Technologies Co., Ltd.";
  contact
    "Huawei Industrial Base
     Bantian, Longgang
     Shenzhen 518129
     People's Republic of China
     Website: http://www.huawei.com
     Email: support@huawei.com
     ";
  description
    "This module contains a set of YANG definitions for common data types for Huawei policies like security policy, nat policy, etc.";
  revision 2025-05-10 {
    description
      "Add geo-location-set.";
    reference "";
  }

  revision 2025-04-18 {
    description
      "Add user defined url in url category.";
    reference "";
  }

  revision 2025-04-15 {
    description
      "Adjust service-set type.";
    reference "";
  }

  revision 2025-04-08 {
    description
      "Add MAC address.";
    reference "";
  }
  revision 2024-03-22 {
    description
      "Add location.";
    reference "";
  }
  revision 2024-02-20 {
    description
      "Add url category.";
    reference "";
  }
  revision 2023-09-25 {
    description
      "Add asset tag.";
    reference "";
  }
  revision 2023-04-28 {
    description
      "Adjust user leaf-list.";
    reference "";
  }
  revision 2023-04-25 {
    description
      "Add user leaf-list.";
    reference "";
  }
  revision 2023-03-23 {
    description
      "Change two leaf-list named category and subcategory to a list.";
    reference "";
  }
  revision 2022-12-14 {
    description
      "Add hw-policy-common in type.";
    reference "";
  }
  revision 2022-11-29 {
    description
      "Add user configuration.";
    reference "";
  }
  revision 2022-11-18 {
    description
      "Modify application type.";
    reference "";
  }
  revision 2021-11-23 {
    description
      "Modify the maximum number of ports that can be configured.";
    reference "";
  }
  revision 2020-11-12 {
    description
      "Initial revision.";
    reference "";
  }

  ext:task-name "policy-common";

  typedef port-range {
    type hw-pub-type:id-range {
      pattern '((6553[0-5]|655[0-2][0-9]|65[0-4][0-9]{2}|6[0-4][0-9]{3}|[1-5][0-9]{4}|[0-9]{1,4})(-(6553[0-5]|655[0-2][0-9]|65[0-4][0-9]{2}|6[0-4][0-9]{3}|[1-5][0-9]{4}|[0-9]{1,4}))?(,((6553[0-5]|655[0-2][0-9]|65[0-4][0-9]{2}|6[0-4][0-9]{3}|[1-5][0-9]{4}|[0-9]{1,4})(-(6553[0-5]|655[0-2][0-9]|65[0-4][0-9]{2}|6[0-4][0-9]{3}|[1-5][0-9]{4}|[0-9]{1,4}))?)){0,63})';
      ext:value-range "0..65535";
    }
    description
      "Configure the port range, which consists of one or more numbers or one or more number ranges. For example, 21, 80-88.";
  }

  typedef icmp-code-range {
    type hw-pub-type:id-range {
      pattern '((25[0-5]|2[0-4][0-9]|1[0-9]{2}|[0-9]{1,2})(-(25[0-5]|2[0-4][0-9]|1[0-9]{2}|[0-9]{1,2}))?(,(25[0-5]|2[0-4][0-9]|1[0-9]{2}|[0-9]{1,2})(-(25[0-5]|2[0-4][0-9]|1[0-9]{2}|[0-9]{1,2}))?){0,63})';
      ext:value-range "0..255";
    }
    description
      "Configure the icmp code range, which consists of one or more numbers or one or more number ranges. For example, 1, 133-135.";
  }

  grouping address-item {
    description
      "The address items referenced by policies. An address item can be an address object, an address group,
       an IP address with a mask, or an IP address range. In addition, the exclude modifier is used to represent
       exclusion of these addresses. Traffic from the excluded addresses does not match the policy. Note that
       a address item should not be included in both the address without exclude and the address with exclude
       in the same policy, that is a conflict.";

    leaf-list address-object {
      type hw-address-set:address-object-ref;
      description "Configure the name of the address object.";
    }

    leaf-list address-group {
      type hw-address-set:address-group-ref;
      description "Configure the name of the address group.";
    }

    container address-ipv4s {
      description "List of IPv4 addresses based on mask.";
      list address-ipv4 {
        key "ipv4 mask";
        description "Configure an IPv4 address and mask.";
        leaf ipv4 {
          type inet:ipv4-address-no-zone;
          description "Configure the IPv4 address.";
        }
        leaf mask {
          type inet:ipv4-address-no-zone;
          description
            "Configure the IPv4 address mask, contiguous (such as 255.0.0.0) and discontiguous (such as 10.1.1.1) are legal.";
        }
      }
    }

    container address-ipv6s {
      description "List of IPv6 addresses based on prefix length.";
      list address-ipv6 {
        key "ipv6 prefix-length";
        description "Configure an IPv6 address and prefix length.";
        leaf ipv6 {
          type inet:ipv6-address-no-zone;
          description "Configure the IPv6 address.";
        }
        leaf prefix-length {
          type uint8 {
            range "1..128";
          }
          description "Configure the IPv6 address prefix length.";
        }
      }
    }

    container address-ipv4-ranges {
      description "List of IPv4 address ranges.";
      list address-ipv4-range {
        key "start-ipv4 end-ipv4";
        description "Configure the IPv4 range. The end address must be larger than the start address.";
        leaf start-ipv4 {
          type inet:ipv4-address-no-zone;
          description "Configure the start IPv4 address.";
        }
        leaf end-ipv4 {
          type inet:ipv4-address-no-zone;
          description "Configure the end IPv4 address.";
        }
      }
    }

    container address-ipv6-ranges {
      description "List of IPv6 address ranges.";
      list address-ipv6-range {
        key "start-ipv6 end-ipv6";
        description "Configure the IPv6 range. The end address must be larger than the start address.";
        leaf start-ipv6 {
          type inet:ipv6-address-no-zone;
          description "Configure the start IPv6 address.";
        }
        leaf end-ipv6 {
          type inet:ipv6-address-no-zone;
          description "Configure the end IPv6 address.";
        }
      }
    }

    leaf-list address-object-exclude {
      type hw-address-set:address-object-ref;
      description "Configure the name of the address object excluded.";
    }

    leaf-list address-group-exclude {
      type hw-address-set:address-group-ref;
      description "Configure the name of the address group excluded.";
    }

    container address-ipv4-excludes {
      description "List of excluded IPv4 addresses based on mask.";
      list address-ipv4-exclude {
        key "ipv4 mask";
        description "Configure an IPv4 address and mask.";
        leaf ipv4 {
          type inet:ipv4-address-no-zone;
          description "IPv4 address.";
        }
        leaf mask {
          type inet:ipv4-address-no-zone;
          description
            "IPv4 address mask, contiguous (such as 255.0.0.0) and discontiguous (such as 10.1.1.1) are legal.";
        }
      }
    }

    container address-ipv6-excludes {
      description "List of excluded IPv6 addresses based on prefix length.";
      list address-ipv6-exclude {
        key "ipv6 prefix-length";
        description "Configure an IPv6 address and prefix length.";
        leaf ipv6 {
          type inet:ipv6-address-no-zone;
          description "IPv6 address.";
        }
        leaf prefix-length {
          type uint8 {
            range "1..128";
          }
          description "IPv6 address prefix length.";
        }
      }
    }

    container address-ipv4-range-excludes {
      description "List of excluded IPv4 address ranges.";
      list address-ipv4-range-exclude {
        key "start-ipv4 end-ipv4";
        description "Configure the IPv4 range excluded. The end address must be larger than the start address.";
        leaf start-ipv4 {
          type inet:ipv4-address-no-zone;
          description "Configure the start IPv4 address.";
        }
        leaf end-ipv4 {
          type inet:ipv4-address-no-zone;
          description "Configure the end IPv4 address.";
        }
      }
    }

    container address-ipv6-range-excludes {
      description "List of excluded IPv6 address ranges.";
      list address-ipv6-range-exclude {
        key "start-ipv6 end-ipv6";
        description "Configure the IPv6 range excluded. The end address must be larger than the start address.";
        leaf start-ipv6 {
          type inet:ipv6-address-no-zone;
          description "Configure the start IPv6 address.";
        }
        leaf end-ipv6 {
          type inet:ipv6-address-no-zone;
          description "Configure the end IPv6 address.";
        }
      }
    }

    leaf-list domain-set {
      type hw-domain-set:domain-set-ref;
      description "Configure the name of the domain set.";
    }

    leaf-list geo-location {
      type string {
        length "1..64";
      }
      description "Configure the name of location.";
    }

    leaf-list geo-location-set {
      type string {
        length "1..63";
      }
      description "Configure the name of location set.";
    }

    leaf-list address-mac {
      type hw-pub-type:mac-address;
      description "Configure the mac address.";
    }
  }

  grouping service-protocol {
    description "A service-protocol data type is a protocol or a set of protocols.
                 A protocol is identified by certain information, such as the protocol type,
                 source port, and destination port, or icmp type and code.";

    container protocol-and-ports {
      description "List of protocols.";
      list protocol-and-port {
        key "protocol source-port dest-port";
        description "Configure a protocol made up of protocol type, source and destination port range.";
        leaf protocol {
          type enumeration {
            enum tcp {
              value 6;
              description "Indicates TCP.";
            }
            enum udp {
              value 17;
              description "Indicates UDP.";
            }
            enum sctp {
              value 132;
              description "Indicates SCTP.";
            }
          }
          description "Configure the protocol type.";
        }
        leaf source-port {
          type hw-policy-common:port-range;
          description "Configure the source port range.";
        }
        leaf dest-port {
          type hw-policy-common:port-range;
          description "Configure the destination port range.";
        }
      }
    }

    container icmpv4s {
      list icmpv4 {
        key "type code";
        description "Configure a combination of ICMPv4 type and code.";
        leaf type {
          type uint8;
          description "Configure the ICMPv4 type.";
        }
        leaf code {
          type hw-policy-common:icmp-code-range;
          description "Configure the ICMPv4 code.";
        }
      }
      description "List of ICMPv4 services. An ICMPv4 service can be identified by type and code.
                   Common service types and codes are as follows: echo (Type=8, Code=0),
                   echo-reply (Type=0, Code=0), fragmentneed-DFset (Type=3, Code=4),
                   host-redirect (Type=5, Code=1), host-tos-redirect (Type=5, Code=3),
                   host-unreachable (Type=3, Code=1), information-reply (Type=16, Code=0),
                   information-request (Type=15, Code=0), net-redirect (Type=5, Code=0),
                   net-tos-redirect (Type=5, Code=2), net-unreachable (Type=3, Code=0),
                   parameter-problem (Type=12, Code=0), port-unreachable (Type=3, Code=3),
                   protocol-unreachable (Type=3, Code=2), reassembly-timeout (Type=11, Code=1),
                   source-quench (Type=4, Code=0), source-route-failed (Type=3, Code=5),
                   timestamp-reply (Type=14, Code=0), timestamp-request (Type=13, Code=0),
                   ttl-exceeded (Type=11, Code=0).";
    }

    container icmpv6s {
      list icmpv6 {
        key "type code";
        description "Configure a combination of ICMPv6 type and code.";
        leaf type {
          type uint8;
          description "Configure the ICMPv6 type.";
        }
        leaf code {
          type hw-policy-common:icmp-code-range;
          description "Configure the ICMPv6 code.";
        }
      }
      description "List of ICMPv6 services. An ICMPv6 service can be identified by type and code.
                   Common service types and codes are as follows: redirect (Type=137, Code=0),
                   echo (Type=128, Code=0), echo-reply (Type=129, Code=0), err-header-field (Type=4, Code=0),
                   frag-time-exceeded (Type=3, Code=1), hop-limit-exceeded (Type=3, Code=0),
                   host-admin-prohib (Type=1, Code=1), host-unreachable (Type=1, Code=3),
                   neighbor-advertisement (Type=136, Code=0), neighbor-solicitation (Type=135, Code=0),
                   network-unreachable (Type=1, Code=0), packet-too-big (Type=2, Code=0),
                   port-unreachable (Type=1, Code=4), router-advertisement (Type=134, Code=0),
                   router-solicitation (Type=133, Code=0), unknown-opt (Type=4, Code=2),
                   unknown-next-hdr (Type=4, Code=1).";
    }

    container protocol {
      description "Configure protocol ID. Different from the port-based or type-code-based mode
                   in service-protocol container, this mode is more general and represents all
                   services with a specified ID.";

      leaf-list protocol-id {
        type uint8 {
          range "0..255";
        }
        description "Configure the protocol ID value.";
      }
    }
  }

  grouping service-item {
    description "Services can be used by policies to identify applications or protocols and
                 control network traffic. A service item can be an service object, an service
                 group or a protocol. In addition, the exclude modifier is used to indicate
                 exclusion of these services. Traffic from the excluded services does not match
                 the policy. Note that a service item should not be included in both the service
                 without exclude and the service with exclude in the same policy, that is a conflict.";

    leaf-list service-object {
      type string {
        length "1..63";
      }
      description "Configure the name of a service object.";
    }

    leaf-list service-group {
      type string {
        length "1..63";
      }
      description "Configure the name of a service group.";
    }

    container service-items {
      uses service-protocol;
      description "Configure the service protocols.";
    }

    leaf-list service-object-exclude {
      type string {
        length "1..63";
      }
      description "Configure the excluded service objects.";
    }

    leaf-list service-group-exclude {
      type string {
        length "1..63";
      }
      description "Configure the excluded service groups.";
    }

    container service-items-exclude {
      uses service-protocol;
      description "Configure the excluded service protocols.";
    }
  }

  grouping application-item {
    description "Configure the applications classified in multiple ways.";
    leaf-list predefined {
      type string {
        length "1..63";
      }
      description "Configure the name of the predefined application.";
    }

    leaf-list user-defined {
      type string {
        length "4..32";
      }
      description "Configure the name of the user-defined application.";
    }

    leaf-list label {
      type string {
        length "1..256";
      }
      description "Configure the name of the application label.";
    }

    container categories {
      description
        "List of application categories.";
      list category {
        key "name subcategory";
        description "Configure an application category.";

        leaf name {
          type string {
            length "1..32";
          }
          description "Configure the name of the application category.";
        }

        leaf subcategory {
          type string {
            length "0..32";
          }
          description "Configure the name of the application subcategory.";
        }
      }
    }

    leaf-list software {
      type string {
        length "1..128";
      }
      description "Configure the name of the software application.";
    }

    leaf-list group {
      type string {
        length "1..32";
      }
      description "Configure the name of the application group.";
    }
  }
  grouping user-item {
    description "Configure the user classified in multiple ways.";
    leaf-list ucl-group {
      type leafref {
        path "/hw-nac-group:nac-group/hw-nac-group:ucl-groups/hw-nac-group:ucl-group/hw-nac-group:name";
      }
      description "Configure the name of the user ucl group.";
    }
    leaf-list user {
      type leafref {
        path "/aaa:aaa/aaa:lam/aaa:access-users/aaa:access-user/aaa:name";
      }
      description "Configure the name of the local access user.";
    }
  }
  grouping asset-item {
    description "The tag and category of this rule configured.";
    list asset-tag {
      key "tag category";
      description "Configure the tag name and category of the asset tag.";
      leaf tag {
        type string {
          length "1..66";
        }
        description "Configure the tag name of the asset tag.";
      }
      leaf category {
        type string {
          length "1..66";
        }
        description "Configure the category of the asset tag.";
      }
    }
  }

  grouping url-category-item {
    description "Configure the url category.";
    container pre-defined {
      description "Configure the pre-defined url category.";
      leaf-list category {
        type string {
          length "1..128";
        }
        description "Configure the name of url category.";
      }
      leaf-list sub-category {
        type string {
          length "1..128";
        }
        description "Configure the name of url sub-category.";
      }
    }

    container user-defined {
      description "Configure the user-defined url category.";
      leaf-list sub-category {
        type string {
          length "1..128";
        }
        description "Configure the name of url category.";
      }
    }
  }
}
