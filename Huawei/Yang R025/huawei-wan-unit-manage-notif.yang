/*
Copyright (C) 2024-2025 Huawei Technologies Co., Ltd. All rights reserved.
*/
module huawei-wan-unit-manage-notif {
  yang-version 1;
  namespace "urn:huawei:yang:huawei-wan-unit-manage-notif";
  prefix huawei-wan-unit-manage-notif;

  import ietf-inet-types {
    prefix inet;
  }
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "Notification of wan unit manage.";
  revision 2025-08-22 {
    description "Modify the type of operation-type and upgrade-result.";
    reference "";
  }
  revision 2025-08-04 {
    description
      "Add wan unit upgrade result.";
    reference
      "Huawei private.";
  }
  revision 2024-01-23 {
    description
      "Initial revision.";
    reference
      "Huawei private.";
  }

  ext:task-name "rum";
  notification wan-unit-alarm-online {
    description
      "The wan unit was online.";
    leaf interface-name {
      type string {
        length "1..511";
      }
      description
        "Interface name.";
    }
    leaf wan-unit-index {
      type uint32;
      description
        "Wan unit index.";
    }
    leaf wan-unit-type {
      type string {
        length "1..31";
      }
      description
        "Type of the connected wan unit.";
    }
    leaf esn {
      type string {
        length "1..63";
      }
      description
        "Electronic label.";
    }
    leaf ip-address {
      type inet:ipv4-address-no-zone;
      description
        "IP address of the connected wan unit.";
    }
  }
  notification wan-unit-alarm-offline {
    description
      "The wan unit was offline.";
    leaf interface-name {
      type string {
        length "1..511";
      }
      description
        "Interface name.";
    }
    leaf wan-unit-index {
      type uint32;
      description
        "Wan unit index.";
    }
    leaf wan-unit-type {
      type string {
        length "1..31";
      }
      description
        "Type of the connected wan unit.";
    }
    leaf esn {
      type string {
        length "1..63";
      }
      description
        "Electronic label.";
    }
    leaf ip-address {
      type inet:ipv4-address-no-zone;
      description
        "IP address of the connected wan unit.";
    }
  }

  notification wan-unit-upgrade-result {
    description
      "Notificate wan unit upgrade result.";
    leaf interface-name {
      type string {
        length "1..64";
      }
      description
        "Interface name.";
    }
    leaf operation-type {
      type string {
        length "1..64";
      }
      description
        "Wan-unit operation type.";
    }
    leaf upgrade-result {
      type string {
        length "1..64";
      }
      description
        "Wan-unit upgrade result.";
    }
  }
}
