/*
Copyright (C) 2019 Huawei Technologies Co., Ltd. All rights reserved.
*/
module huawei-wlan-radio-2g-profile-deviations-ar5710s {
  yang-version 1;
  namespace "urn:huawei:yang:huawei-wlan-radio-2g-profile-deviations-ar5710s";
  prefix radio-2g-prof-devs-ar5710s;

  import huawei-wlan-radio-2g-profile {
    prefix radio-2g-prof;
  }

  organization
    "Huawei Technologies Co., Ltd.";
  contact
    "Huawei Industrial Base
     Bantian, Longgang
     Shenzhen 518129
     People's Republic of China
     Website: http://www.huawei.com
     Email: support@huawei.com";
  description
    "This module defines deviation statements for huawei-wlan-radio-2g-profile module.";

  revision 2019-11-06 {
    description
      "Initial revision.";
    reference "Huawei private.";
  }

  deviation "/radio-2g-prof:wlan-radio-2g-profile/radio-2g-prof:radio-2g-profiles/radio-2g-prof:radio-2g-profile/radio-2g-prof:short-preamble" {
    deviate not-supported;
  }
  deviation "/radio-2g-prof:wlan-radio-2g-profile/radio-2g-prof:radio-2g-profiles/radio-2g-prof:radio-2g-profile/radio-2g-prof:fragmentation-threshold" {
    deviate not-supported;
  }
  deviation "/radio-2g-prof:wlan-radio-2g-profile/radio-2g-prof:radio-2g-profiles/radio-2g-prof:radio-2g-profile/radio-2g-prof:edca/radio-2g-prof:wmm-mandatory" {
    deviate not-supported;
  }
  deviation "/radio-2g-prof:wlan-radio-2g-profile/radio-2g-prof:radio-2g-profiles/radio-2g-prof:radio-2g-profile/radio-2g-prof:edca/radio-2g-prof:wmm-edca-ap-acvo" {
    deviate not-supported;
  }
  deviation "/radio-2g-prof:wlan-radio-2g-profile/radio-2g-prof:radio-2g-profiles/radio-2g-prof:radio-2g-profile/radio-2g-prof:edca/radio-2g-prof:wmm-edca-ap-acvi" {
    deviate not-supported;
  }
  deviation "/radio-2g-prof:wlan-radio-2g-profile/radio-2g-prof:radio-2g-profiles/radio-2g-prof:radio-2g-profile/radio-2g-prof:edca/radio-2g-prof:wmm-edca-ap-acbe" {
    deviate not-supported;
  }
  deviation "/radio-2g-prof:wlan-radio-2g-profile/radio-2g-prof:radio-2g-profiles/radio-2g-prof:radio-2g-profile/radio-2g-prof:edca/radio-2g-prof:wmm-edca-ap-acbk" {
    deviate not-supported;
  }
  deviation "/radio-2g-prof:wlan-radio-2g-profile/radio-2g-prof:radio-2g-profiles/radio-2g-prof:radio-2g-profile/radio-2g-prof:smart-antenna" {
    deviate not-supported;
  }
  deviation "/radio-2g-prof:wlan-radio-2g-profile/radio-2g-prof:radio-2g-profiles/radio-2g-prof:radio-2g-profile/radio-2g-prof:anti-interference-parameters/radio-2g-prof:agc-high-threshold" {
    deviate not-supported;
  }
  deviation "/radio-2g-prof:wlan-radio-2g-profile/radio-2g-prof:radio-2g-profiles/radio-2g-prof:radio-2g-profile/radio-2g-prof:wifi-light" {
    deviate not-supported;
  }
  deviation "/radio-2g-prof:wlan-radio-2g-profile/radio-2g-prof:radio-2g-profiles/radio-2g-prof:radio-2g-profile/radio-2g-prof:vip-user-phy-protection" {
    deviate not-supported;
  }
  deviation "/radio-2g-prof:wlan-radio-2g-profile/radio-2g-prof:radio-2g-profiles/radio-2g-prof:radio-2g-profile/radio-2g-prof:interference" {
    deviate not-supported;
  }
  deviation "/radio-2g-prof:wlan-radio-2g-profile/radio-2g-prof:radio-2g-profiles/radio-2g-prof:radio-2g-profile/radio-2g-prof:dot11n-lsig-len-compatible-switch" {
    deviate not-supported;
  }
}
