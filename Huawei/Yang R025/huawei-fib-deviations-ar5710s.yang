/*
Copyright (C) 2025 Huawei Technologies Co., Ltd. All rights reserved.
*/
module huawei-fib-deviations-ar5710s {
  yang-version 1;
  namespace "urn:huawei:yang:huawei-fib-deviations-ar5710s";
  prefix fib-devs-ar5710s;

  import huawei-fib {
    prefix fib;
  }
  import huawei-devm {
    prefix devm;
  }

  organization
    "Huawei Technologies Co., Ltd.";
  contact
    "Huawei Industrial Base
     Bantian, Longgang
     Shenzhen 518129
     People's Republic of China
     Website: http://www.huawei.com
     Email: support@huawei.com";
  description
    "This module defines deviation statements for huawei-fib module.";

  revision 2025-02-24 {
    description
      "Initial revision.";
    reference "Huawei private.";
  }

  deviation "/fib:fib/fib:unicast-afs" {
    deviate not-supported;
  }
  deviation "/fib:fib/fib:route-statistics" {
    deviate not-supported;
  }
  deviation "/fib:fib/fib:m-lag-route-convergence-enhanced" {
    deviate not-supported;
  }
  deviation "/fib:fib/fib:ipv4-fib-checks" {
    deviate not-supported;
  }
  deviation "/fib:fib/fib:ipv6-fib-checks" {
    deviate not-supported;
  }
  deviation "/fib:fib/fib:fib-ipv4-on-demand" {
    deviate not-supported;
  }
  deviation "/fib:fib/fib:fib-ipv6-on-demand" {
    deviate not-supported;
  }
  deviation "/devm:devm/devm:lpu-boards/devm:lpu-board/fib:fib" {
    deviate not-supported;
  }
  deviation "/devm:devm/devm:mpu-boards/devm:mpu-board/fib:fib" {
    deviate not-supported;
  }
}
