/*
Copyright (C) 2025 Huawei Technologies Co., Ltd. All rights reserved.
*/
module huawei-openconfig-lacp-deviations-ar5710s {
  namespace "urn:huawei:yang:huawei-openconfig-lacp-deviations-ar5710s";
  prefix oc-lacp-devs-ar5710s;

  import openconfig-lacp {
    prefix oc-lacp;
  }

  organization
    "Huawei Technologies Co., Ltd.";
  contact
    "Huawei Industrial Base
     Bantian, Longgang
     Shenzhen 518129
     People's Republic of China
     Website: http://www.huawei.com
     Email: support@huawei.com";
  description
    "This module defines deviation statements for openconfig-lacp module.";

  revision 2025-02-24 {
    description
      "Initial revision.";
    reference "Huawei private.";
  }

  deviation "/oc-lacp:lacp" {
    deviate not-supported;
  }
}
