/*
Copyright (C) 2025 Huawei Technologies Co., Ltd. All rights reserved.
*/
module huawei-hips-notification-deviations-ar5710s {
  namespace "urn:huawei:yang:huawei-hips-notification-deviations-ar5710s";
  prefix hips-notification-devs-ar5710s;

  import huawei-hips-notification {
    prefix hips-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-hips-notification module.";

  revision 2025-02-24 {
    description
      "Initial revision.";
    reference "Huawei private.";
  }

  deviation "/hips-notification:abnormal-behavior-resolved" {
    deviate not-supported;
  }
}
