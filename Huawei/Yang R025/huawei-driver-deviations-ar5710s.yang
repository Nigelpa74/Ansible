/*
Copyright (C) 2023 Huawei Technologies Co., Ltd. All rights reserved.
*/
module huawei-driver-deviations-ar5710s {
  yang-version 1;
  namespace "urn:huawei:yang:huawei-driver-deviations-ar5710s";
  prefix driver-devs-ar5710s;

  import huawei-driver {
    prefix driver;
  }
  import huawei-devm {
    prefix devm;
  }
  import huawei-license {
    prefix lcs;
  }

  organization
    "Huawei Technologies Co., Ltd.";
  contact
    "Huawei Industrial Base
     Bantian, Longgang
     Shenzhen 518129
     People's Republic of China
     Website: http://www.huawei.com
     Email: support@huawei.com";
  description
    "This module defines deviation statements for huawei-driver module.";

  revision 2023-10-27 {
    description
      "The deviations of the huawei-driver module were modified.";
    reference "Huawei private.";
  }
  revision 2023-02-24 {
    description
      "Initial revision.";
    reference "Huawei private.";
  }

  typedef system-work-mode-type-deviations {
    type enumeration {
      enum p-series {
        value 0;
        description
          "The system work mode is p-series.";
      }
      enum x-series {
        value 1;
        description
          "The system work mode is x-series.";
      }
      enum e-series {
        value 2;
        description
          "The system work mode is e-series.";
      }
      enum standard-forward {
        value 4;
        description
          "The system work mode is standard-forward.";
      }
      enum low-latency {
        value 8;
        description
          "The system work mode is low-latency.";
      }
      enum jx-series {
        value 16;
        description
          "The system work mode is jx-series.";
      }
      enum j-series {
        value 32;
        description
          "The system work mode is j-series.";
      }
      enum j2x-series {
        value 128;
        description
          "The system work mode is j2x-series.";
      }
    }
    description
      "Information of enum type system-work-mode-type.";
  }

  typedef fan-workmode-deviations {
    type enumeration {
      enum auto {
        value 0;
        description
          "Automatic.";
      }
      enum manual {
        value 1;
        description
          "Percent.";
      }
      enum minimum-percent {
        value 2;
        description
          "Minimum-percent.";
      }
    }
    description
      "Information of enum type fan-workmode.";
  }

  typedef energy-mode-type-deviations {
    type enumeration {
      enum basic {
        value 0;
        description
          "Basic.";
      }
      enum standard {
        value 1;
        description
          "Standard.";
      }
      enum deep {
        value 2;
        description
          "Deep.";
      }
    }
    description
      "Information of enum type energy-mode-type.";
  }

  typedef device-type-deviations {
    type enumeration {
      enum usb-disk {
        value 0;
        description
          "USB disk.";
      }
    }
    description
      "Device type of LED.";
  }

  deviation "/driver:driver/driver:global-attribute/driver:board-power-on-delay" {
    deviate not-supported;
  }
  deviation "/driver:driver/driver:global-attribute/driver:card-power-on-delay" {
    deviate not-supported;
  }
  deviation "/driver:driver/driver:global-attribute/driver:dustproof-check" {
    deviate not-supported;
  }
  deviation "/driver:driver/driver:global-attribute/driver:support-mode-list" {
    deviate not-supported;
  }
  deviation "/driver:driver/driver:global-attribute/driver:deep-sub-mode" {
    deviate not-supported;
  }
  deviation "/driver:driver/driver:global-attribute/driver:energy-saving-pm" {
    deviate not-supported;
  }
  deviation "/driver:driver/driver:global-attribute/driver:energy-saving-fabric-fiber" {
    deviate not-supported;
  }
  deviation "/driver:driver/driver:global-attribute/driver:entity-fault-board-isolate" {
    deviate not-supported;
  }
  deviation "/driver:driver/driver:global-attribute/driver:entity-fault-card-isolate" {
    deviate not-supported;
  }
  deviation "/driver:driver/driver:global-attribute/driver:fault-strategy" {
    deviate not-supported;
  }
  deviation "/driver:driver/driver:global-attribute/driver:high-temp-switch" {
    deviate not-supported;
  }
  deviation "/driver:driver/driver:global-attribute/driver:interface-match-check" {
    deviate not-supported;
  }
  deviation "/driver:driver/driver:global-attribute/driver:least-sfu-number" {
    deviate not-supported;
  }
  deviation "/driver:driver/driver:global-attribute/driver:offline-function" {
    deviate not-supported;
  }
  deviation "/driver:driver/driver:global-attribute/driver:optional-entity-fault-isolate" {
    deviate not-supported;
  }
  deviation "/driver:driver/driver:global-attribute/driver:pic-reload-cycle" {
    deviate not-supported;
  }
  deviation "/driver:driver/driver:global-attribute/driver:sfu-switch-mode" {
    deviate not-supported;
  }
  deviation "/driver:driver/driver:global-attribute/driver:system-trap" {
    deviate not-supported;
  }
  deviation "/driver:driver/driver:global-attribute/driver:temp-query-mode" {
    deviate not-supported;
  }
  deviation "/driver:driver/driver:global-attribute/driver:vlt-query-mode" {
    deviate not-supported;
  }
  deviation "/driver:driver/driver:global-attribute/driver:sfu-mode" {
    deviate not-supported;
  }
  deviation "/driver:driver/driver:global-attribute/driver:cur-forward-mode" {
    deviate not-supported;
  }
  deviation "/driver:driver/driver:global-attribute/driver:next-forward-mode" {
    deviate not-supported;
  }
  deviation "/driver:driver/driver:global-attribute/driver:cur-work-mode" {
    deviate not-supported;
  }
  deviation "/driver:driver/driver:global-attribute/driver:next-work-mode" {
    deviate not-supported;
  }
  deviation "/driver:driver/driver:global-attribute/driver:warm-backup-states" {
    deviate not-supported;
  }
  deviation "/driver:driver/driver:global-attribute/driver:warm-backup-mode" {
    deviate not-supported;
  }
  deviation "/driver:driver/driver:global-attribute/driver:cur-device-work-mode" {
    deviate not-supported;
  }
  deviation "/driver:driver/driver:global-attribute/driver:next-device-work-mode" {
    deviate not-supported;
  }
  deviation "/driver:driver/driver:global-attribute/driver:dcn-management-plane-lock-status" {
    deviate not-supported;
  }
  deviation "/driver:driver/driver:global-attribute/driver:cur-dcn-plane-mode" {
    deviate not-supported;
  }
  deviation "/driver:driver/driver:global-attribute/driver:next-dcn-plane-mode" {
    deviate not-supported;
  }
  deviation "/driver:driver/driver:global-attribute/driver:cur-system-mode" {
    deviate not-supported;
  }
  deviation "/driver:driver/driver:global-attribute/driver:next-system-mode" {
    deviate not-supported;
  }
  deviation "/driver:driver/driver:global-attribute/driver:auto-upgrade-model" {
    deviate not-supported;
  }
  deviation "/driver:driver/driver:global-attribute/driver:chassis-last-change-time" {
    deviate not-supported;
  }
  deviation "/driver:driver/driver:global-attribute/driver:cur-chassis-number" {
    deviate not-supported;
  }
  deviation "/driver:driver/driver:global-attribute/driver:max-chassis-number" {
    deviate not-supported;
  }
  deviation "/driver:driver/driver:global-attribute/driver:power-consumption" {
    deviate not-supported;
  }
  deviation "/driver:driver/driver:global-attribute/driver:split-resume" {
    deviate not-supported;
  }
  deviation "/driver:driver/driver:global-attribute/driver:switch-port-mode" {
    deviate not-supported;
  }
  deviation "/driver:driver/driver:global-attribute/driver:system-service-type" {
    deviate not-supported;
  }
  deviation "/driver:driver/driver:global-attribute/driver:usb-uart-status" {
    deviate not-supported;
  }
  deviation "/driver:driver/driver:global-attribute/driver:cur-system-mac-address" {
    deviate not-supported;
  }
  deviation "/driver:driver/driver:global-attribute/driver:board-channel-check-status" {
    deviate not-supported;
  }
  deviation "/driver:driver/driver:global-attribute/driver:energy-saving-pm-status" {
    deviate not-supported;
  }
  deviation "/driver:driver/driver:global-attribute/driver:service-forward-ability" {
    deviate not-supported;
  }
  deviation "/driver:driver/driver:global-attribute/driver:power-input-mode" {
    deviate not-supported;
  }
  deviation "/driver:driver/driver:global-attribute/driver:factory-configuration-button-switch" {
    deviate not-supported;
  }
  deviation "/driver:driver/driver:global-attribute/driver:pm-auto-balance" {
    deviate not-supported;
  }
  deviation "/driver:driver/driver:global-attribute/driver:temp-change-enable" {
    deviate not-supported;
  }
  deviation "/driver:driver/driver:opt-electronic-labels" {
    deviate not-supported;
  }
  deviation "/driver:driver/driver:power-global-attribute/driver:alarm-pm-cable" {
    deviate not-supported;
  }
  deviation "/driver:driver/driver:power-global-attribute/driver:power-reserved" {
    deviate not-supported;
  }
  deviation "/driver:driver/driver:io-inspect-states" {
    deviate not-supported;
  }
  deviation "/driver:driver/driver:io-inspect-attributes" {
    deviate not-supported;
  }
  deviation "/driver:driver/driver:temperatures" {
    deviate not-supported;
  }
  deviation "/driver:driver/driver:voltageinfos" {
    deviate not-supported;
  }
  deviation "/driver:driver/driver:electric-current-infos" {
    deviate not-supported;
  }
  deviation "/driver:driver/driver:interface-match-check-states" {
    deviate not-supported;
  }
  deviation "/driver:driver/driver:area-energyinfos/driver:area-energyinfo/driver:area-real-power" {
    deviate not-supported;
  }
  deviation "/driver:driver/driver:area-energyinfos/driver:area-energyinfo/driver:area-power-mode" {
    deviate not-supported;
  }
  deviation "/driver:driver/driver:area-energyinfos/driver:area-energyinfo/driver:others-power" {
    deviate not-supported;
  }
  deviation "/driver:driver/driver:area-energyinfos/driver:area-energyinfo/driver:board-energys/driver:board-energy/driver:type" {
    deviate not-supported;
  }
  deviation "/driver:driver/driver:area-energyinfos/driver:area-energyinfo/driver:board-energys/driver:board-energy/driver:energy-saving-mode-status" {
    deviate not-supported;
  }
  deviation "/driver:driver/driver:area-energyinfos/driver:area-energyinfo/driver:board-energys/driver:board-energy/driver:average-power" {
    deviate not-supported;
  }
  deviation "/driver:driver/driver:area-energyinfos/driver:area-energyinfo/driver:board-energys/driver:board-energy/driver:saved-power" {
    deviate not-supported;
  }
  deviation "/driver:driver/driver:area-energyinfos/driver:area-energyinfo/driver:board-energys/driver:board-energy/driver:expected-saved-power" {
    deviate not-supported;
  }
  deviation "/driver:driver/driver:area-energyinfos/driver:area-energyinfo/driver:board-energys/driver:board-energy/driver:energy-saving-mode-states" {
    deviate not-supported;
  }
  deviation "/driver:driver/driver:board-powers" {
    deviate not-supported;
  }
  deviation "/driver:driver/driver:electronic-labels/driver:electronic-label/driver:barcode" {
    deviate not-supported;
  }
  deviation "/driver:driver/driver:electronic-labels/driver:electronic-label/driver:bom-english-desc" {
    deviate not-supported;
  }
  deviation "/driver:driver/driver:electronic-labels/driver:electronic-label/driver:bom-local-desc" {
    deviate not-supported;
  }
  deviation "/driver:driver/driver:electronic-labels/driver:electronic-label/driver:manufacturer-name" {
    deviate not-supported;
  }
  deviation "/driver:driver/driver:electronic-labels/driver:electronic-label/driver:manufacturer-date" {
    deviate not-supported;
  }
  deviation "/driver:driver/driver:electronic-labels/driver:electronic-label/driver:manufacturer-code" {
    deviate not-supported;
  }
  deviation "/driver:driver/driver:electronic-labels/driver:electronic-label/driver:board-type" {
    deviate not-supported;
  }
  deviation "/driver:driver/driver:electronic-labels/driver:electronic-label/driver:entity-asset-id" {
    deviate not-supported;
  }
  deviation "/driver:driver/driver:electronic-labels/driver:electronic-label/driver:entity-clei-code" {
    deviate not-supported;
  }
  deviation "/driver:driver/driver:electronic-labels/driver:electronic-label/driver:entity-update-log" {
    deviate not-supported;
  }
  deviation "/driver:driver/driver:electronic-labels/driver:electronic-label/driver:archives-info-version" {
    deviate not-supported;
  }
  deviation "/driver:driver/driver:electronic-labels/driver:electronic-label/driver:entity-open-bomid" {
    deviate not-supported;
  }
  deviation "/driver:driver/driver:electronic-labels/driver:electronic-label/driver:entity-issue-number" {
    deviate not-supported;
  }
  deviation "/driver:driver/driver:electronic-labels/driver:electronic-label/driver:entity-model" {
    deviate not-supported;
  }
  deviation "/driver:driver/driver:electronic-labels/driver:electronic-label/driver:entity-elabel-version" {
    deviate not-supported;
  }
  deviation "/driver:driver/driver:electronic-labels/driver:electronic-label/driver:entity-elabel-extend" {
    deviate not-supported;
  }
  deviation "/driver:driver/driver:electronic-labels/driver:electronic-label/driver:silk-screen" {
    deviate not-supported;
  }
  deviation "/driver:driver/driver:mbusnodes" {
    deviate not-supported;
  }
  deviation "/driver:driver/driver:check-running-software-safes" {
    deviate not-supported;
  }
  deviation "/driver:driver/driver:bootinfos" {
    deviate not-supported;
  }
  deviation "/driver:driver/driver:multi-chassis-attributes" {
    deviate not-supported;
  }
  deviation "/driver:driver/driver:chassis-run-modes" {
    deviate not-supported;
  }
  deviation "/driver:driver/driver:stratum-3-clocks" {
    deviate not-supported;
  }
  deviation "/driver:driver/driver:system-sync-clocks" {
    deviate not-supported;
  }
  deviation "/driver:driver/driver:rollback-attribute" {
    deviate not-supported;
  }
  deviation "/driver:driver/driver:slave-defaults" {
    deviate not-supported;
  }
  deviation "/driver:driver/driver:inner-links" {
    deviate not-supported;
  }
  deviation "/driver:driver/driver:slot-statistics" {
    deviate not-supported;
  }
  deviation "/driver:driver/driver:leds/driver:led/driver:duration" {
    deviate not-supported;
  }
  deviation "/driver:driver/driver:cluster-fiber" {
    deviate not-supported;
  }
  deviation "/driver:driver/driver:battery" {
    deviate not-supported;
  }
  deviation "/driver:set-usb-uart-stat" {
    deviate not-supported;
  }
  deviation "/driver:power-off-board/driver:input/driver:auto-power-on" {
    deviate not-supported;
  }
  deviation "/driver:power-off-lpu/driver:input/driver:auto-power-on" {
    deviate not-supported;
  }
  deviation "/driver:power-on-ecu" {
    deviate not-supported;
  }
  deviation "/driver:power-off-ecu" {
    deviate not-supported;
  }
  deviation "/driver:power-on-icu" {
    deviate not-supported;
  }
  deviation "/driver:power-off-icu" {
    deviate not-supported;
  }
  deviation "/driver:reset-lcd" {
    deviate not-supported;
  }
  deviation "/driver:reset-ecu-board" {
    deviate not-supported;
  }
  deviation "/driver:reset-icu-board" {
    deviate not-supported;
  }
  deviation "/driver:reset-cmu-board" {
    deviate not-supported;
  }
  deviation "/driver:reset-fan-board" {
    deviate not-supported;
  }
  deviation "/driver:reset-dustproof-net" {
    deviate not-supported;
  }
  deviation "/driver:reset-mbus-node" {
    deviate not-supported;
  }
  deviation "/driver:set-slave-default" {
    deviate not-supported;
  }
  deviation "/driver:set-flash-lock" {
    deviate not-supported;
  }
  deviation "/driver:auto-upgrade-models" {
    deviate not-supported;
  }
  deviation "/driver:interface-match-check-recovery" {
    deviate not-supported;
  }
  deviation "/driver:rollback" {
    deviate not-supported;
  }
  deviation "/driver:set-multi-chassis-id" {
    deviate not-supported;
  }
  deviation "/driver:set-chassis-run-mode" {
    deviate not-supported;
  }
  deviation "/driver:set-next-work-mode" {
    deviate not-supported;
  }
  deviation "/driver:set-split-resume" {
    deviate not-supported;
  }
  deviation "/driver:set-led-flash" {
    deviate not-supported;
  }
  deviation "/driver:set-slot-led-flash" {
    deviate not-supported;
  }
  deviation "/driver:set-run-led-flash-off" {
    deviate not-supported;
  }
  deviation "/driver:board-channel-check" {
    deviate not-supported;
  }
  deviation "/driver:set-vsu-service-type" {
    deviate not-supported;
  }
  deviation "/driver:check-hardware-compatibility" {
    deviate not-supported;
  }
  deviation "/driver:check-system-software" {
    deviate not-supported;
  }
  deviation "/driver:check-hardware-version" {
    deviate not-supported;
  }
  deviation "/driver:clear-nv-port-bip8-err-alarm" {
    deviate not-supported;
  }
  deviation "/driver:clear-nv-port-crc-err-alarm" {
    deviate not-supported;
  }
  deviation "/driver:clear-nv-port-input-err-alarm" {
    deviate not-supported;
  }
  deviation "/driver:clear-nv-port-output-err-alarm" {
    deviate not-supported;
  }
  deviation "/driver:clear-nv-port-sdh-err-alarm" {
    deviate not-supported;
  }
  deviation "/driver:clear-nv-port-symbol-err-alarm" {
    deviate not-supported;
  }
  deviation "/driver:clear-nv-port-trans-alarm" {
    deviate not-supported;
  }
  deviation "/driver:clear-nv-port-tx-pause-err-alarm" {
    deviate not-supported;
  }
  deviation "/driver:clear-port-bip8-err-alarm" {
    deviate not-supported;
  }
  deviation "/driver:clear-port-tx-pause-err-alarm" {
    deviate not-supported;
  }
  deviation "/driver:set-nv-laser-turn" {
    deviate not-supported;
  }
  deviation "/driver:check-lcm-channel" {
    deviate not-supported;
  }
  deviation "/driver:multi-level-alarm-boolean" {
    deviate not-supported;
  }
  deviation "/driver:sysmac-load" {
    deviate not-supported;
  }
  deviation "/driver:set-next-system-mode" {
    deviate not-supported;
  }
  deviation "/driver:set-next-run-mode" {
    deviate not-supported;
  }
  deviation "/driver:set-next-chassis-id" {
    deviate not-supported;
  }
  deviation "/driver:set-dcn-management-plane-lock" {
    deviate not-supported;
  }
  deviation "/driver:set-power-pm-input-mode" {
    deviate not-supported;
  }
  deviation "/driver:refresh-power-pm-input" {
    deviate not-supported;
  }
  deviation "/driver:set-next-fiber-connect-mode" {
    deviate not-supported;
  }
  deviation "/driver:set-service-forward-ability" {
    deviate not-supported;
  }
  deviation "/driver:reset-cmu-switch-fog" {
    deviate not-supported;
  }
  deviation "/devm:devm/devm:chassiss/devm:chassis/driver:fan-attribute/driver:area-fan-attributes" {
    deviate not-supported;
  }
  deviation "/devm:devm/devm:chassiss/devm:chassis/driver:power-supply-attribute/driver:pm-input-voltage-110" {
    deviate not-supported;
  }
  deviation "/devm:devm/devm:chassiss/devm:chassis/driver:power-supply-attribute/driver:power-supply-mode" {
    deviate not-supported;
  }
  deviation "/devm:devm/devm:chassiss/devm:chassis/driver:power-supply-attribute/driver:power-supply-input" {
    deviate not-supported;
  }
  deviation "/devm:devm/devm:chassiss/devm:chassis/driver:power-supply-attribute/driver:power-supply-temp" {
    deviate not-supported;
  }
  deviation "/devm:devm/devm:chassiss/devm:chassis/driver:power-supply-attribute/driver:power-supply-alarm-limit" {
    deviate not-supported;
  }
  deviation "/devm:devm/devm:chassiss/devm:chassis/driver:power-supply-attribute/driver:power-supply-average" {
    deviate not-supported;
  }
  deviation "/devm:devm/devm:chassiss/devm:chassis/driver:power-supply-attribute/driver:power-supply-others" {
    deviate not-supported;
  }
  deviation "/devm:devm/devm:chassiss/devm:chassis/driver:dustproof-attribute" {
    deviate not-supported;
  }
  deviation "/devm:devm/devm:chassiss/devm:chassis/driver:chassis-id" {
    deviate not-supported;
  }
  deviation "/devm:devm/devm:chassiss/devm:chassis/driver:chassis-run-mode" {
    deviate not-supported;
  }
  deviation "/devm:devm/devm:chassiss/devm:chassis/driver:chassis-sfu-mode" {
    deviate not-supported;
  }
  deviation "/devm:devm/devm:chassiss/devm:chassis/driver:pm-input-attribute" {
    deviate not-supported;
  }
  deviation "/devm:devm/devm:chassiss/devm:chassis/driver:temperature-attribute" {
    deviate not-supported;
  }
  deviation "/devm:devm/devm:mpu-boards/devm:mpu-board/driver:boot-status" {
    deviate not-supported;
  }
  deviation "/devm:devm/devm:lpu-boards/devm:lpu-board/driver:driver" {
    deviate not-supported;
  }
  deviation "/devm:devm/driver:driver/driver:cmus" {
    deviate not-supported;
  }
  deviation "/devm:devm/driver:driver/driver:pms/driver:pm/driver:single-input" {
    deviate not-supported;
  }
  deviation "/devm:devm/driver:driver/driver:pms/driver:pm/driver:board-type" {
    deviate not-supported;
  }
  deviation "/devm:devm/driver:driver/driver:pms/driver:pm/driver:entity-index" {
    deviate not-supported;
  }
  deviation "/devm:devm/driver:driver/driver:pms/driver:pm/driver:monitor-cable-state" {
    deviate not-supported;
  }
  deviation "/devm:devm/driver:driver/driver:pms/driver:pm/driver:input-voltage-value" {
    deviate not-supported;
  }
  deviation "/devm:devm/driver:driver/driver:pms/driver:pm/driver:input-electrical-value" {
    deviate not-supported;
  }
  deviation "/devm:devm/driver:driver/driver:pms/driver:pm/driver:pm-area" {
    deviate not-supported;
  }
  deviation "/devm:devm/driver:driver/driver:ccus" {
    deviate not-supported;
  }
  deviation "/devm:devm/driver:driver/driver:dacss" {
    deviate not-supported;
  }
  deviation "/devm:devm/driver:driver/driver:ecus" {
    deviate not-supported;
  }
  deviation "/devm:devm/driver:driver/driver:fans/driver:fan/driver:area-id" {
    deviate not-supported;
  }
  deviation "/devm:devm/driver:driver/driver:fans/driver:fan/driver:running-status" {
    deviate not-supported;
  }
  deviation "/devm:devm/driver:driver/driver:fans/driver:fan/driver:sub-fans" {
    deviate not-supported;
  }
  deviation "/devm:devm/driver:driver/driver:icus" {
    deviate not-supported;
  }
  deviation "/devm:devm/driver:driver/driver:lcds" {
    deviate not-supported;
  }
  deviation "/devm:devm/driver:driver/driver:pmus" {
    deviate not-supported;
  }
  deviation "/devm:devm/driver:driver/driver:power-supplys/driver:power-supply/driver:work-mode" {
    deviate not-supported;
  }
  deviation "/devm:devm/driver:driver/driver:power-supplys/driver:power-supply/driver:monitor-cable-state" {
    deviate not-supported;
  }
  deviation "/devm:devm/driver:driver/driver:power-supplys/driver:power-supply/driver:power-environments/driver:power-environment/driver:electrical-value" {
    deviate not-supported;
  }
  deviation "/devm:devm/driver:driver/driver:dmus" {
    deviate not-supported;
  }
  deviation "/devm:devm/driver:driver/driver:pdus" {
    deviate not-supported;
  }
  deviation "/devm:devm/driver:driver/driver:vsus" {
    deviate not-supported;
  }
  deviation "/lcs:license/driver:lcs-boards" {
    deviate not-supported;
  }
  deviation "/lcs:license/driver:lcs-usage-board-capacitys" {
    deviate not-supported;
  }
  deviation "/driver:driver/driver:global-attribute/driver:sampling-period" {
    deviate delete {
      default "one-hour";
    }
  }
  deviation "/driver:driver/driver:temperature2s/driver:temperature2/driver:fan-adjust-high-temperature" {
    deviate replace {
      mandatory false;
    }
  }
  deviation "/driver:driver/driver:temperature2s/driver:temperature2/driver:fan-adjust-low-temperature" {
    deviate replace {
      mandatory false;
    }
  }
  deviation "/driver:driver/driver:fan-attributes/driver:fan-attribute/driver:workmode" {
    deviate replace {
      type driver-devs-ar5710s:fan-workmode-deviations;
    }
  }
  deviation "/driver:driver/driver:fan-attributes/driver:fan-attribute/driver:speed" {
    deviate replace {
      type uint32 {
        range "20..100";
      }
    }
  }
  deviation "/devm:devm/devm:chassiss/devm:chassis/driver:fan-attribute/driver:workmode" {
    deviate replace {
      type driver-devs-ar5710s:fan-workmode-deviations;
    }
  }
  deviation "/devm:devm/devm:chassiss/devm:chassis/driver:fan-attribute/driver:speed" {
    deviate replace {
      type uint32 {
        range "20..100";
      }
    }
  }
  deviation "/devm:devm/driver:driver/driver:pms" {
    deviate replace {
      config false;
    }
  }
  deviation "/driver:reset-cpu" {
    deviate not-supported;
  }
  deviation "/driver:offline-disk" {
    deviate not-supported;
  }
  deviation "/driver:online-disk" {
    deviate not-supported;
  }
  deviation "/devm:devm/driver:driver/driver:disks" {
    deviate not-supported;
  }
  deviation "/driver:power-on-card" {
    deviate not-supported;
  }
  deviation "/driver:power-off-card" {
    deviate not-supported;
  }
  deviation "/driver:driver/driver:global-attribute/driver:energy-mode" {
    deviate not-supported;
  }
  deviation "/driver:driver/driver:global-attribute/driver:cur-system-work-mode" {
    deviate not-supported;
  }
  deviation "/driver:set-next-system-work-mode" {
    deviate not-supported;
  }
  deviation "/driver:driver/driver:global-attribute/driver:system-mac-address" {
    deviate not-supported;
  }
  deviation "/driver:driver/driver:global-attribute/driver:system-mac-number" {
    deviate not-supported;
  }
  deviation "/driver:driver/driver:global-attribute/driver:next-system-work-mode" {
    deviate not-supported;
  }
  deviation "/driver:power-on-mpu" {
    deviate not-supported;
  }
  deviation "/driver:power-off-mpu" {
    deviate not-supported;
  }
  deviation "/driver:power-on-sfu" {
    deviate not-supported;
  }
  deviation "/driver:power-off-sfu" {
    deviate not-supported;
  }
  deviation "/driver:reset-chassis" {
    deviate not-supported;
  }
  deviation "/driver:driver/driver:global-attribute/driver:sysmac-switch-time" {
    deviate not-supported;
  }
  deviation "/driver:driver/driver:cpu-isolates" {
    deviate not-supported;
  }
  deviation "/driver:set-led/driver:input/driver:type" {
    deviate replace {
      type driver-devs-ar5710s:device-type-deviations;
    }
  }
}
