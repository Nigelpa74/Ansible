/*
* Copyright (C) 2022-2025 Huawei Technologies Co., Ltd. All rights reserved.
*/
module huawei-wlan-group-radio {
  yang-version 1;
  namespace "urn:huawei:yang:huawei-wlan-group-radio";
  prefix hw-grd;
  import huawei-wlan-ap-group-profile {
    prefix hw-wlan-agp;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "Group radio service package.";
  revision 2025-08-28 {
    description
      "Modify data-3d-calibrate.";
    reference
      "Huawei private.";
  }
  revision 2025-08-06 {
    description
      "Modify leaf asfn-roam.";
    reference
      "Huawei private.";
  }
  revision 2025-08-04 {
    description
      "Add leaf asfn-roam.";
    reference
      "Huawei private.";
  }
  revision 2025-05-07 {
    description
      "Extend radio-id.";
    reference
      "Huawei private.";
  }

  revision 2025-02-24 {
    description
      "Extend radio-id.";
    reference
      "Huawei private.";
  }
  revision 2024-12-27 {
    description
      "Add leaf reference-data-analysis.";
    reference
      "Huawei private.";
  }
  revision 2024-11-26 {
    description
      "Add dynamic default value.";
    reference
      "Huawei private.";
  }

  revision 2024-09-29 {
    description
      "Fix spelling error.";
    reference
      "Huawei private.";
  }
  revision 2024-08-23 {
    description
      "Modify radio 1 support frequency configuration.";
    reference
      "Huawei private.";
  }
  revision 2024-08-15 {
    description
      "Modify the type of unused spectrum-analysis leaf.";
    reference
      "Huawei private.";
  }
  revision 2024-07-16 {
    description
      "Modify the type of unused spectrum analysis leaf.";
    reference
      "Huawei private.";
  }
  revision 2024-07-09 {
    description
      "Add coverage distance configuration.";
    reference
      "Huawei private.";
  }
  revision 2024-05-10 {
    description
      "Modify channel config check.";
    reference
      "Huawei private.";
  }
  revision 2024-03-05 {
    description
      "Modify radio instances as generated-by system.";
    reference
      "Huawei private.";
  }
  revision 2023-11-20 {
    description
      "Fix bandwidth-320mhz case bug.";
    reference
      "Huawei private.";
  }
  revision 2022-12-29 {
    description
      "Add bandwidth-320mhz.";
    reference
      "Huawei private.";
  }
  revision 2022-12-22 {
    description
      "Add spectrum-analysis switch and 3d-data calibrate switch.";
    reference
      "Huawei private.";
  }
  revision 2022-11-19 {
    description
      "Fix bandwidth-40mhz-minus description.";
    reference
      "Huawei private.";
  }
  revision 2022-09-23 {
    description
      "Add work mode.";
    reference
      "Huawei private.";
  }
  revision 2022-08-19 {
    description
      "Add YANG node of V6R22C10.";
    reference
      "Huawei private.";
  }
  revision 2022-07-15 {
    description
      "Add freq when check.";
    reference
      "Huawei private.";
  }
  revision 2022-06-15 {
    description
      "Fix task name.";
    reference
      "Huawei private.";
  }
  revision 2022-04-08 {
    description
      "Initial revision.";
    reference
      "Huawei private.";
  }
  grouping radio-instances {
    description
      "Radio instances.";
    list radio-instance {
      ext:generated-by "system" {
        description
          "The radio instance is generated by system.";
      }
      key "radio-id";
      description
        "Configure attribute to specify radio instance.";
      leaf radio-id {
        type uint8 {
          range "0..4";
        }
        description
          "Radio id.";
      }
      leaf radio-switch {
        type enumeration {
          enum "disable" {
            value 0;
            description
              "Disable.";
          }
          enum "enable" {
            value 1;
            description
              "Enable.";
          }
        }
        default "enable";
        description
          "Set radio enable or disable.";
      }
      container channel-info {
        presence
          "Configure ap individual bandwidth and channel.";
        choice bandwidth {
          mandatory true;
          description
            "Bandwidth of each channel.";
          case bandwidth-20mhz {
            leaf bandwidth-20mhz {
              type empty;
              description
                "20mhz.";
            }
            description
              "20mhz.";
          }
          case bandwidth-40mhz-minus {
            leaf bandwidth-40mhz-minus {
              type empty;
              description
                "40mhz-minus.";
            }
            description
              "40mhz-minus.";
          }
          case bandwidth-40mhz-plus {
            leaf bandwidth-40mhz-plus {
              type empty;
              description
                "40mhz-plus.";
            }
            description
              "40mhz-plus.";
          }
          case bandwidth-80mhz {
            when "(../radio-id = '1') or (../radio-id = '2') or (../radio-id = '3') or (../radio-id = '4') or ((../radio-id = '0') and (../frequency = '5G'))";
            leaf bandwidth-80mhz {
              type empty;
              description
                "80mhz.";
            }
            description
              "80mhz.";
          }
          case bandwidth-80plus80mhz {
            when "(../radio-id = '1') or (../radio-id = '2') or (../radio-id = '3') or (../radio-id = '4') or ((../radio-id = '0') and (../frequency = '5G'))";
            leaf bandwidth-80plus80mhz {
              type empty;
              description
                "80plus80mhz.";
            }
            description
              "80plus80mhz.";
          }
          case bandwidth-160mhz {
            when "(../radio-id = '1') or (../radio-id = '2') or (../radio-id = '3') or (../radio-id = '4') or ((../radio-id = '0') and (../frequency = '5G'))";
            leaf bandwidth-160mhz {
              type empty;
              description
                "160mhz.";
            }
            description
              "160mhz.";
          }
          case bandwidth-320mhz {
            when "(../radio-id = '1') or (../radio-id = '2') or (../radio-id = '3') or (../radio-id = '4') or ((../radio-id = '0') and (../frequency = '5G'))";
            leaf bandwidth-320mhz {
              type empty;
              description
                "320mhz.";
            }
            description
              "320mhz.";
          }
        }
        leaf channel {
          type uint8;
          mandatory true;
          description
            "Channel configuration.";
        }
        description
          "Configure ap individual bandwidth and channel.";
      }
      leaf eirp {
        type uint8 {
          range "1..127";
        }
        default "127";
        description
          "Eirp configuration.";
      }
      leaf auto-channel-select {
        type enumeration {
          enum "enable" {
            value 0;
            description
              "Channel auto select enable.";
          }
          enum "disable" {
            value 1;
            description
              "Channel auto select disable.";
          }
        }
        default "enable";
        description
          "Channel auto select configuration.";
      }
      leaf auto-txpower-select {
        type enumeration {
          enum "enable" {
            value 0;
            description
              "Txpower auto select enable.";
          }
          enum "disable" {
            value 1;
            description
              "Txpower auto select disable.";
          }
        }
        default "enable";
        description
          "Txpower auto select configuration.";
      }
      leaf frequency {
        type enumeration {
          enum "2G" {
            value 1;
            description
              "Frequency is 2.4G.";
          }
          enum "5G" {
            value 2;
            description
              "Frequency is 5G.";
          }
          enum "6G" {
            value 3;
            description
              "Frequency is 6G.";
          }
        }
        ext:dynamic-default {
          ext:default-value "2G" {
            when "../radio-id = '0'";
            description
              "The default value is 2G when radio id is 0.";
          }
          ext:default-value "5G" {
            when "../radio-id = '1'";
            description
              "The default value is 5G when radio id is 1.";
          }
          ext:default-value "6G" {
            when "(../radio-id = '2') or (../radio-id = '3') or (../radio-id = '4')";
            description
              "The default value is 6G when radio id is 2.";
          }
        }
        description
          "Configure frequency.";
      }
      leaf auto-bandwidth-select {
        type enumeration {
          enum "disable" {
            value 1;
            description
              "Disable.";
          }
          enum "enable" {
            value 2;
            description
              "Enable.";
          }
        }
        default "disable";
        description
          "Calibrate auto-bandwidth-select.";
      }
      leaf flexible-radio {
        type enumeration {
          enum "disable" {
            value 0;
            description
              "Disables DFA of group radios.";
          }
          enum "enable" {
            value 1;
            description
              "Enable DFA of specified radio.";
          }
        }
        default "enable";
        description
          "Disable or enable DFA of specified radios.";
      }
      leaf channel-monitor {
        type enumeration {
          enum "disable" {
            value 0;
            description
              "Disable the function of monitoring the status of all channels.";
          }
          enum "enable" {
            value 1;
            description
              "Enable the function of monitoring the status of all channels.";
          }
        }
        default "disable";
        description
          "Enable or disable the function of monitoring the status of all channels.
           By default, the function of monitoring the status of all channels is disabled.";
      }
      leaf antenna-gain {
        type int32 {
          range "-10..30";
        }
        units "dB";
        description
          "Config antenna-gain.";
      }
      leaf work-mode {
        type enumeration {
          enum "monitor" {
            value 0;
            description
              "Indicates the monitor mode.";
          }
          enum "normal" {
            value 1;
            description
              "Indicates the normal mode.";
          }
        }
        default "normal";
        description
          "Configure the working mode for all AP radios in a specified AP radio.";
      }
      leaf spectrum-analysis-switch {
        type enumeration {
          enum "disable" {
            value 0;
            description
              "Disable spectrum-analysis.";
          }
          enum "enable" {
            value 1;
            description
              "Enable spectrum-analysis.";
          }
        }
        default "disable";
        description
          "Enable/disable the function of spectrum analysis.";
      }
      leaf data-3d-calibrate {
        type enumeration {
          enum "disable" {
            value 0;
            description
              "Disable 3d-data-calibrate.";
          }
          enum "enable" {
            value 1;
            description
              "Enable 3d-data-calibrate.";
          }
        }
        description
          "Configure 3d-data-calibrate, the default is disable.";
      }
      container coverage {
        description
          "Configure coverage parameters.";
        leaf distance {
          type uint16 {
            range 1..400;
          }
          units "100 m";
          description
            "Configure coverage distance.";
        }
      }
      leaf reference-data-analysis {
        type enumeration {
          enum "disable" {
            value 0;
            description
              "Disable reference-data-analysis.";
          }
          enum "enable" {
            value 1;
            description
              "Enable reference-data-analysis.";
          }
        }
        default "enable";
        description
          "Configure reference-data-analysis.";
      }
      container asfn-roam {
        must "./high-level-margin > ./low-level-margin";
        description
          "Configure asfn roam.";
        leaf high-level-margin {
          type int32 {
            range 5..25;
          }
          units "dB";
          default 10;
          description
            "High level margin value.";
        }
        leaf low-level-margin {
          type int32 {
            range 3..15;
          }
          units "dB";
          default 5;
          description
            "Low level margin value.";
        }
      }
    }
  }
  augment "/hw-wlan-agp:wlan-ap-group-profile/hw-wlan-agp:ap-group-profiles/hw-wlan-agp:ap-group-profile" {
    description
      "Augment ap group radio instance.";
    container radio-instances {
      description
        "Configure group radio.";
      uses hw-grd:radio-instances;
    }
  }
  ext:task-name "wm";
}
