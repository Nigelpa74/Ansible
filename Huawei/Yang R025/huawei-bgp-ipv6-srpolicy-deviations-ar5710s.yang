/*
Copyright (C) 2025 Huawei Technologies Co., Ltd. All rights reserved.
*/
module huawei-bgp-ipv6-srpolicy-deviations-ar5710s {
  yang-version 1;
  namespace "urn:huawei:yang:huawei-bgp-ipv6-srpolicy-deviations-ar5710s";
  prefix bgp-ipv6-srpolicy-devs-ar5710s;

  import huawei-bgp-ipv6-srpolicy {
    prefix bgp-ipv6-srpolicy;
  }
  import huawei-bgp {
    prefix bgp;
  }
  import huawei-network-instance {
    prefix ni;
  }
  import huawei-bgp-routing-table {
    prefix bgp-rt;
  }

  organization
    "Huawei Technologies Co., Ltd.";
  contact
    "Huawei Industrial Base
     Bantian, Longgang
     Shenzhen 518129
     People's Republic of China
     Website: http://www.huawei.com
     Email: support@huawei.com";
  description
    "This module defines deviation statements for huawei-bgp-ipv6-srpolicy module.";

  revision 2025-02-24 {
    description
      "Initial revision.";
    reference "Huawei private.";
  }

  deviation "/ni:network-instance/ni:instances/ni:instance/bgp:bgp/bgp:base-process/bgp:afs/bgp:af/bgp-ipv6-srpolicy:ipv6-srpolicy/bgp-ipv6-srpolicy:common/bgp-ipv6-srpolicy:route-target-orf-enable" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:group-name" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:import-policy-type/bgp-ipv6-srpolicy:xpl-ref" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:export-policy-type/bgp-ipv6-srpolicy:xpl-ref" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:nexthop-configure" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:nexthop-effective" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:route-target-orf-disable" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:option/bgp-ipv6-srpolicy:advertise-non-standard-slid" {
    deviate not-supported;
  }
  deviation "/ni:network-instance/ni:instances/ni:instance/bgp:bgp/bgp:base-process/bgp:peers/bgp:peer/bgp:afs/bgp:af/bgp-ipv6-srpolicy:ipv6-srpolicy/bgp-ipv6-srpolicy:option/bgp-ipv6-srpolicy:discard-non-standard-slid" {
    deviate not-supported;
  }
  deviation "/ni:network-instance/ni:instances/ni:instance/bgp:bgp/bgp:base-process/bgp:peer-groups/bgp:peer-group/bgp:afs/bgp:af/bgp-ipv6-srpolicy:ipv6-srpolicy" {
    deviate not-supported;
  }
  deviation "/bgp:bgp/bgp:base-process/bgp-rt:bgp-route/bgp-ipv6-srpolicy:ipv6-srpolicy/bgp-ipv6-srpolicy:routes/bgp-ipv6-srpolicy:route/bgp-ipv6-srpolicy:advertise-nexthop" {
    deviate not-supported;
  }
  deviation "/bgp:bgp/bgp:base-process/bgp-rt:bgp-route/bgp-ipv6-srpolicy:ipv6-srpolicy/bgp-ipv6-srpolicy:peer-receive-routes/bgp-ipv6-srpolicy:peer-receive-route/bgp-ipv6-srpolicy:advertise-nexthop" {
    deviate not-supported;
  }
  deviation "/ni:network-instance/ni:instances/ni:instance/bgp:bgp/bgp:base-process/bgp:afs/bgp:af/bgp-ipv6-srpolicy:ipv6-srpolicy/bgp-ipv6-srpolicy:slow-peer/bgp-ipv6-srpolicy:absolute-detection-threshold" {
    deviate replace {
      default "60";
    }
  }
  deviation "/ni:network-instance/ni:instances/ni:instance/bgp:bgp/bgp:base-process/bgp:peers/bgp:peer/bgp:afs/bgp:af/bgp-ipv6-srpolicy:ipv6-srpolicy" {
    deviate add {
      must "contains(../../../bgp:address,':')";
    }
  }
}
