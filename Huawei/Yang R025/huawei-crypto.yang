/*
Copyright (C) 2019-2022 Huawei Technologies Co., Ltd. All rights reserved.
*/
module huawei-crypto {
  namespace "urn:huawei:yang:huawei-crypto";
  prefix crypto;
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "Crypto mode.";
  revision 2022-11-02 {
    description
      "Add crypto-mode nodes.";
    reference
      "Huawei private.";
  }   
  revision 2022-05-07 {
    description
      "Modify weak-algorithm nodes.";
    reference
      "Huawei private.";
  }
  revision 2022-05-06 {
    description
      "Add weak-algorithm nodes.";
    reference
      "Huawei private.";
  }
  revision 2021-11-17 {
    description
      "Add fips-mode nodes.";
    reference
      "Huawei private.";
  }
  revision 2019-05-23 {
    description
      "Init revision.";
    reference
      "Huawei private.";
  }
  ext:task-name  "system";
  typedef algorithm-type {
    type enumeration {
      enum "default" {
        value 0;
        description
          "Default encryption type, more secure.";
      }
      enum "hmac-sha256" {
        value 1;
        description
          "Encryption type of hmac-sha256.";
      }
    }
    description
      "The encryption type of irreversible algorithm.";
  }
  typedef crypto-mode-type {
    type enumeration {
      enum "default" {
        value 0;
        description
          "The device uses the default algorithm.";
      }
      enum "fips-mode" {
        value 1;
        description
          "The device uses the algorithm used for FIPS certification.";
      }
      enum "sm-mode" {
        value 2;
        description
          "The device uses the Chinese cryptographic algorithm.";
      }
    }
    description
      "Encryption mode.";
  }
  container crypto {
    description
      "Crypto mode.";
    container drbg {
      description
        "Configure DRBG.";
      leaf is-drbg-enabled {
        type boolean;
        default "true";
        description
          "Enable/disable DRBG.";
      }
    }
    container encryption-algorithm {
      description
        "Configure password encryption.";
      leaf type {
        type algorithm-type;
        default "default";
        description
          "Password encryption irreversible algorithm.";
      }
    }
    container crypto-mode {
      config false;
      description
        "Operational state of the encryption mode.";
      leaf type {
        type crypto-mode-type;
        default "default";
        description
          "Obtain the encryption mode.";
      }
    }
    container fips-mode {
      config false;
      description
        "Operational state of fips mode.";
      leaf enable {
        type boolean;
        default "false";
        description
          "Query fips mode.";
      }
    }
    container weak-algorithm {
      description
        "Configure state of weak algorithm.";
      leaf enable {
        type boolean;
        default "false";
        description
          "Enable/disable the weak algorithm.";
      }
    }
  }
}
