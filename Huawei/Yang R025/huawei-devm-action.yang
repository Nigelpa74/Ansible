/*
Copyright (C) 2019-2024 Huawei Technologies Co., Ltd. All rights reserved.
*/
submodule huawei-devm-action {
  belongs-to huawei-devm {
    prefix devm;
  }

  import huawei-pub-type {
    prefix pub-type;
  }
  import ietf-inet-types {
    prefix inet;
  }
  
  import huawei-extension {
    prefix ext;
  }
  include huawei-devm-type;

  organization
    "Huawei Technologies Co., Ltd.";
  contact
    "Huawei Industrial Base
     Bantian, Longgang
     Shenzhen 518129
     People's Republic of China
     Website: http://www.huawei.com
     Email: support@huawei.com";
  description
    "The submodule of devm : devm_action.";

  revision 2024-07-18 {
    description
      "Add warm-reboot, set-warm-reboot-switch and get-warm-reboot-switch.";
    reference
      "Huawei private.";
  }

  revision 2024-06-19 {
    description
      "Add rpc remote-reboot.";
    reference
      "Huawei private.";
  }

   revision 2023-11-30 {
    description
      "Delete the reason leaf node in the reboot command.";
    reference
      "Huawei private.";
  }

   revision 2023-08-18 {
    description
      "Add reason leaf node.";
    reference
      "Huawei private.";
  }

   revision 2022-12-27 {
    description
      "Add mandatory field.";
    reference
      "Huawei private.";
  }

   revision 2022-11-04 {
    description
      "Add reset-peak-rate.";
    reference
      "Huawei private.";
  }

  revision 2020-08-07 {
    description
      "Add clear-active-hardware-alarm and clear-history-hardware-alarm.";
    reference
      "Huawei private.";
  }

  revision 2020-04-10 {
    description
      "Modify description warnings.";
    reference
      "Huawei private.";
  }
	
  revision 2019-09-09 {
    description
      "Change description.";
    reference
      "Huawei private.";
  }

  revision 2019-04-03 {
    description
      "Initial revision.";
    reference
      "Huawei private.";
  }
  
  rpc reset-board {
    description
      "Reset board.";
    input {
      leaf board-position {
        type string {
          length "1..32";
        }
        mandatory true;
        description
          "Board position.";
      }
    }
  }
  rpc reset-mpu-board {
    description
      "Reset MPU.";
    ext:node-ref "/devm/mpu-boards/mpu-board";
    input {
      leaf board-position {
        type string {
          length "1..32";
        }
        mandatory true;
        description
          "Board position.";
      }
    }
  }
  rpc reset-lpu-board {
    description
      "Reset LPU.";
    ext:node-ref "/devm/lpu-boards/lpu-board";
    input {
      leaf board-position {
        type string {
          length "1..32";
        }
        mandatory true;
        description
          "Board position.";
      }
    }
  }
  rpc reset-sfu-board {
    description
      "Reset SFU.";
    ext:node-ref "/devm/sfu-boards/sfu-board"; 
    input {
      leaf board-position {
        type string {
          length "1..32";
        }
        mandatory true;
        description
          "Board position.";
      }
    }
  }

  rpc reset-card {
    description
      "Reset Card.";
    ext:node-ref "/devm/cards/card";
    input {
      leaf card-position {
        type string {
          length "1..32";
        }
        mandatory true;
        description
          "Card position.";
      }
    }
  }

  rpc reboot {
    description
      "Reboot.";
    input {
      leaf save-flag {
        type boolean;
        default "true";
        description
          "Flag indicating whether to save the configuration. True: save; False: not save.";
      }
    }
  }
  rpc transfer-pnpp {
    description
      "Transfer pnpp files.";
    input {
      leaf server-ip-address {
        type inet:ip-address-no-zone;
        mandatory true;
        description
          "FTP server IP address.";
      }
      leaf server-port {
        type uint32 {
          range "21..65535";
        }
        default "21";
        description
          "Server port.";
      }
      leaf vpn-instance-name {
        type string {
          length "1..128";
        }
        description
          "VPN instance name.";
      }
      leaf source-ipv4-address {
        type inet:ipv4-address-no-zone;
        description
          "Source IPv4 address.";
      }
      leaf source-interface-name {
        type pub-type:if-name;
        description
          "Source interface name.";
      }
      leaf server-type {
        type server-type;
        default "ftp";
        description
          "Server type.";
      }
      leaf command-type {
        type trans-type;
        default "put";
        description
          "Transmission type.";
      }
      leaf user-name {
        type string {
          length "1..85";
        }
        mandatory true;
        description
          "User name.";
      }
      leaf password {
        type pub-type:password;
        mandatory true;
        description
          "Password.";
      }
      leaf local-file-name {
        type string {
          length "1..128";
        }
        default "pnpp.7z";
        description
          "Local file name.";
      }
      leaf remote-file-name {
        type string {
          length "1..128";
        }
        description
          "File name on the FTP server.";
      }
      leaf remote-extension {
        type string {
          length "1..5";
        }
        default ".hw!";
        description
          "Temporary file name extension used for reliability.";
      }
      container secure-transfer-options {
        description
          "Transfer encryption options.";
        leaf prefer-kex {
          type prefer-kex-type;
          description
            "Encryption algorithm.";
        }
        leaf prefer-stoc-cipher {
          type cipher-type;
          description
            "Encryption algorithm for messages from a client to server.";
        }
        leaf prefer-ctos-cipher {
          type cipher-type;
          description
            "Encryption algorithm for messages from a server to client.";
        }
        leaf prefer-stoc-hmac {
          type stoc-hmac-type;
          description
            "Prefer Stoc Hmac.";
        }
        leaf prefer-ctos-hmac {
          type stoc-hmac-type;
          description
            "Prefer Ctos Hmac.";
        }
        leaf keep-alive-interval {
          type uint32 {
            range "0..60";
          }
          default "0";
          description
            "Keepalive interval.";
        }
        leaf keep-alive-count {
          type uint32 {
            range "0..100";
          }
          default "0";
          description
            "Number of Keepalive packets.";
        }
      }
    }
  }
  rpc reset-offline-config {
    description
      "Reset offline configuration.";
    input {
      leaf board-position {
        type string {
          length "1..32";
        }
        mandatory true;
        description
          "Board position.";
      }
    }
  }
  rpc clear-inactive-config {
    description
      "Clear Inactive Configuration.";
    input {
      leaf entity-class {
        type offline-class-type;
        mandatory true;
        description
          "Class.";
      }
      leaf position {
        type string {
          length "1..32";
        }
        mandatory true;
        description
          "Position.";
      }
    }
  }
  rpc cold-reset-lpu {
    description
      "Cold reset LPU.";
    ext:node-ref "/devm/lpu-boards/lpu-board";
    input {
      leaf board-position {
        type string {
          length "1..32";
        }
        mandatory true;
        description
          "Board position.";
      }
    }
  }
  rpc warm-reset-lpu {
    description
      "Warm reset LPU.";
    ext:node-ref "/devm/lpu-boards/lpu-board";
    input {
      leaf board-position {
        type string {
          length "1..32";
        }
        mandatory true;
        description
          "Board position.";
      }
    }
  }
  rpc cold-reset-mpu {
    description
      "Cold reset MPU.";
    ext:node-ref "/devm/mpu-boards/mpu-board";
    input {
      leaf board-position {
        type string {
          length "1..32";
        }
        mandatory true;
        description
          "Board position.";
      }
    }
  }
  rpc warm-reset-mpu {
    description
      "Warm reset MPU.";
    ext:node-ref "/devm/mpu-boards/mpu-board";
    input {
      leaf board-position {
        type string {
          length "1..32";
        }
        mandatory true;
        description
          "Board position.";
      }
    }
  }
  rpc warm-reboot {
    description
      "Warm reboot system.";
  }
  rpc set-warm-reboot-switch {
    description
      "Enable/Disable warm reboot.";
    input {
      leaf enable {
        type boolean;
        description
          "Enable/Disable.";
      }
    }
  }
  rpc get-warm-reboot-switch {
    description
      "Get the warm reboot enabling state.";
    output {
      leaf enable {
        type boolean;
        description
        "Enabled/Disabled.";
      }
    }
  }
  rpc schedule-reboot-at-time {
    description
      "Schedule reboot at time.";
    input {
      leaf schedule-date {
        type pub-type:date;
        mandatory true;
        description
          "Date.";
      }
      leaf schedule-datetime {
        type pub-type:time-hhmm;
        mandatory true;
        description
          "Time.";
      }
      leaf save-flag {
          type boolean;
          default true;
          description
            "Flag indicating whether save config.";
        }
    }
  }  
  rpc schedule-reboot-delay-time {
    description
      "Schedule reboot delay time.";
    input {
      leaf delay-time {
        type string {
          length "1..6";
        }
        mandatory true;
        description
          "Delay time, total minutes or hours:minutes (mm or hh:mm), the max value is 720 hours.";
      }
      leaf save-flag {
          type boolean;
          default true;
          description
            "Flag indicating whether save config.";
        }
    }
  } 
  rpc undo-schedule-reboot {
    description
      "Undo Schedule reboot.";
  }
  rpc clear-active-hardware-alarm {
    description
      "Clear active hardware alarm.";
    input {
      choice clear-mode {
          default all;
          description
            "The mode to clear alarm.";
          case all {
            description
              "Clear all alarm.";
            leaf all {
              type empty;
              description
                "Clear all alarm.";
            }
          }
          case position {
            description
              "Clear alarm by hardware entity position.";
            leaf position {
              type string {
                length "1..32";
              }
              mandatory true;
              description
                "Hardware entity position.";
            }
          }
          case sequence {
            description
              "Clear alarm by sequence.";
            leaf sequence {
              type uint32 {
                range "1..4294967295";
              }
              mandatory true;
              description
                "The sequence of all active alarm.";
            }
          }
      }
    }
  }
  rpc clear-history-hardware-alarm {
    description
      "Clear history hardware alarm.";
    input {
      choice clear-mode {
          default all;
          description
            "The mode to clear alarm.";
          case all {
            description
              "Clear all alarm.";
            leaf all {
              type empty;
              description
                "Clear all alarm.";
            }
          }
          case position {
            description
              "Clear alarm by hardware entity position.";
            leaf position {
              type string {
                length "1..32";
              }
              mandatory true;
              description
                "Hardware entity position.";
            }
          }
      }
    }
  } 
  rpc get-reboot-info {
    description
      "Get reboot info on certain slot.";
    input {
      leaf slot-index {
        type string {
          length "1..32";
        }
        description
          "Slot-index information.";
      }
    }
    output {
      container reboot-info-lists {
        description
          "List of reboot-info.";
        list reboot-info-list {
          key "slot-index time";
          description
            "Slot's reboot info.";
          leaf slot-index {
            type string {
              length "1..32";
            }
            description
              "Slot-index information.";
          }
          leaf time {
            type string {
              length "1..32";
            }
            description
              "Reboot time.";
          }
          leaf reason {
            type string {
              length "1..256";
            }
            description
              "Reboot reason.";
          }
        }
      }
    }
  }
  rpc get-reset-reason {
    description
      "Get reset reason list.";
    input {
      leaf slot-index {
        type string {
          length "1..32";
        }
        description
          "Slot-index information, for example: 1/9.";
      }
    }
    output {
      container reset-reason-lists {
        description
          "List of reset reason.";
        list reset-reason-list {
          key "slot-index reset-time";
          description
            "Slot's reset reason.";
          leaf slot-index {
            type string {
              length "1..32";
            }
            description
              "Slot-index information, for example: 1/9.";
          }
          leaf reset-time {
            type string {
              length "1..32";
            }
            description
              "Reset time.";
          }
          leaf reason {
            type string {
              length "1..256";
            }
            description
              "Reset reason.";
          }
        }
      }
    }
  }
  rpc reset-port-peak-rate {
    description
    "Reset port prak rate.";
    input {
      choice port {
          description
          "Choose to reset all ports or one port.";
        case all {
            description
            "Reset peak rates for all ports.";
            leaf all {
              type empty;
              mandatory true;
              description
              "Reset peak rates for all ports.";
            }
        }
        case name {
          description
          "Reset peak rate of one port by port name.";
          leaf name {
            type string {
              length "1..63";
            }
            mandatory true;
            description 
            "Reset peak rate of one port by port name.";
          }
        }
      }
    }
  }
  rpc remote-reboot {
    description
      "Remote reboot.";
    input {
      leaf ap-id {
        type uint32 {
          range "1024..8191";
        }
        mandatory true;
        description
          "AP ID.";
      }
    }
  }
}
