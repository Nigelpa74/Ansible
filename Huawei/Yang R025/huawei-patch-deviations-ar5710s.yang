/*
Copyright (C) 2023 Huawei Technologies Co., Ltd. All rights reserved.
*/
module huawei-patch-deviations-ar5710s {
  namespace "urn:huawei:yang:huawei-patch-deviations-ar5710s";
  prefix patch-devs-ar5710s;

  import huawei-patch {
    prefix patch;
  }

  organization
    "Huawei Technologies Co., Ltd.";
  contact
    "Huawei Industrial Base
     Bantian, Longgang
     Shenzhen 518129
     People's Republic of China
     Website: http://www.huawei.com
     Email: support@huawei.com";
  description
    "This module defines deviation statements for huawei-patch module.";

  revision 2023-03-28 {
    description
      "Initial revision.";
    reference "Huawei private.";
  }

  deviation "/patch:patch/patch:operation-schedules/patch:operation-schedule/patch:name" {
    deviate not-supported;
  }
  deviation "/patch:patch/patch:download-package-schedule" {
    deviate not-supported;
  }
  deviation "/patch:patch/patch:download-package-load-path" {
    deviate not-supported;
  }
  deviation "/patch:delete-patch/patch:input/patch:name" {
    deviate not-supported;
  }
  deviation "/patch:reset-startup-patch/patch:input/patch:name" {
    deviate not-supported;
  }
  deviation "/patch:download-patch-file" {
    deviate not-supported;
  }
  deviation "/patch:synchronize-patch" {
    deviate not-supported;
  }
}
