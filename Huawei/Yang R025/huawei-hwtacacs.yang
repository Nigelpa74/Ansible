/*
Copyright (C) 2020-2024 Huawei Technologies Co., Ltd. All rights reserved.
*/
module huawei-hwtacacs {
  yang-version 1;
  namespace "urn:huawei:yang:huawei-hwtacacs";
  prefix hwtacacs;
  import huawei-pub-type {
    prefix pub-type;
  }
  import ietf-inet-types {
    prefix inet;
  }
  import huawei-extension {
    prefix ext;
  }
  import huawei-network-instance {
    prefix ni;
  }
  import huawei-ifm {
    prefix ifm;
  }
  organization
    "Huawei Technologies Co., Ltd.";
  contact
    "Huawei Industrial Base
    Bantian, Longgang
    Shenzhen 518129
    People's Republic of China
    Website: http://www.huawei.com
    Email: support@huawei.com";
  description
    "Huawei Terminal Access Controller Access-Control System.";
  revision 2024-10-24 {
    description
      "Add server-IPv6-hosts.";
    reference
      "Huawei private.";
  }
  revision 2024-06-17 {
    description
      "Delete case-sensitivity of hwtacacs-template's name.";
    reference
      "Huawei private.";
  }
  revision 2024-06-03 {
    description
      "Refresh pattern of hwtacacs-template's name.";
    reference
      "Huawei private.";
  }
  revision 2024-05-14 {
    description
      "Rename node change-user-password to hwtacacs-change-user-password.";
    reference
      "Huawei private.";
  }
  revision 2024-04-22 {
    description
      "Add leaf is-mux-mode-enable.";
    reference
      "Huawei private.";
  }
  revision 2024-01-23 {
    description
      "Add rpc change-user-password.";
    reference
      "Huawei private.";
  }
  revision 2024-01-09 {
    description
      "Add leaf IPv6-address of server-host.";
    reference
      "Huawei private.";
  }
  revision 2023-08-08 {
    description
      "Add leaf encode-name-flag.";
    reference
      "Huawei private.";
  }
  revision 2023-02-13 {
    description
      "Modify leaf quiet-time.";
    reference
      "Huawei private.";
  }
  revision 2020-07-06 {
    description
      "Add server-hosts.";
    reference
      "Huawei private.";
  }
  revision 2020-06-30 {
    description
      "Initial revision.";
    reference
      "Huawei private.";
  }
  typedef hwtacacs-server-state {
    type enumeration {
      enum "up" {
        value 0;
        description
          "The server is active.";
      }
      enum "down" {
        value 1;
        description
          "The server is inactive.";
      }
    }
    description
      "The type of hwtacacs server state.";
  }
  typedef hwtacacs-server-type {
    type enumeration {
      enum "authentication" {
        value 0;
        description
          "The server is an authentication server.";
      }
      enum "authorization" {
        value 1;
        description
          "The server is an authorization server.";
      }
      enum "accounting" {
        value 2;
        description
          "The server is an accounting server.";
      }
      enum "common" {
        value 3;
        description
          "The server is a common server.";
      }
    }
    description
      "The type of hwtacacs server.";
  }
  typedef server-priority-type {
    type enumeration {
      enum "authentication" {
        value 0;
        description
          "The server is a master authentication server.";
      }
      enum "authorization" {
        value 1;
        description
          "The server is a master authorization server.";
      }
      enum "accounting" {
        value 2;
        description
          "The server is a master accounting server.";
      }
      enum "authentication-secondary" {
        value 3;
        description
          "The server is a secondary authentication server.";
      }
      enum "authorization-secondary" {
        value 4;
        description
          "The server is a secondary authorization server.";
      }
      enum "accounting-secondary" {
        value 5;
        description
          "The server is s secondary accounting server.";
      }
      enum "authentication-third" {
        value 6;
        description
          "The server is a third authentication server.";
      }
      enum "authorization-third" {
        value 7;
        description
          "The server is a third authorization server.";
      }
      enum "accounting-third" {
        value 8;
        description
          "The server is a third accounting server.";
      }
    }
    description
      "The type of hwtacacs server.";
  }
  typedef hwtacacs-domain-include {
    type enumeration {
      enum "domain-exclude" {
        value 0;
        description
          "User name excludes domain.";
      }
      enum "domain-include" {
        value 1;
        description
          "User name includes domain.";
      }
      enum "original" {
        value 2;
        description
          "User name same as user input.";
      }
    }
    description
      "The type of domain mode.";
  }
  typedef traffic-unit-type {
    type enumeration {
      enum "byte" {
        value 0;
        description
          "Byte.";
      }
      enum "kbyte" {
        value 1;
        description
          "KByte.";
      }
      enum "mbyte" {
        value 2;
        description
          "MByte.";
      }
      enum "gbyte" {
        value 3;
        description
          "GByte.";
      }
    }
    description
      "Traffice unit type.";
  }
  typedef priority-type {
    type enumeration {
      enum "master" {
        value 0;
        description
          "Master server.";
      }
      enum "secondary" {
        value 1;
        description
          "Secondary server.";
      }
      enum "third" {
        value 2;
        description
          "Third server.";
      }
      enum "fourth" {
        value 3;
        description
          "Fourth server.";
      }
    }
    description
      "Priority type.";
  }
  typedef ip-type {
    type enumeration {
      enum "ipv4-flag" {
        value 0;
        description
          "IPv4.";
      }
      enum "ipv6-flag" {
        value 1;
        description
          "IPv6.";
      }
    }
    description
      "IP type.";
  }
  container hwtacacs {
    description
      "Huawei Terminal Access Controller Access-Control System.";
    container global {
      description
        "Configure HWTACACS global.";
      leaf is-enable {
        type boolean;
        default "true";
        description
          "Enable/disable the HWTACACS server.";
      }
      leaf service-name {
        type string {
          length "1..32";
        }
        description
          "HWTACACS service name.";
      }
      leaf default-remote-address {
        type string {
          length "1..31";
        }
        description
          "Default remote address of HWTACACS server.";
      }
      leaf acct-stop-packet-resend-times {
        type uint16 {
          range "0..300";
        }
        default "100";
        description
          "Specify the number of packets that can be retransmitted each time. Zero is disable.";
      }
    }
    container templates {
      description
        "List of HWTACACS templates.";
      list template {
        key "name";
        max-elements  "255";
        description
          "Configure HWTACACS template.";
        leaf name {
          type string {
            length "1..32";
            pattern "[a-zA-Z0-9._-]+";
          }
          description
            "Name of a HWTACACS template. The template name can have alphabets a to z or A to Z and numbers from 0 to 9 or symbols ('.', '-' and '_').";
        }
        leaf response-timeout {
          type uint32 {
            range "1..300";
          }
          units "s";
          default "5";
          description
            "Server response timeout period.";
        }
        leaf quiet-time {
          type uint32 {
            range "0..255";
          }
          units "min";
          default "5";
          description
            "Time period after which the primary server restores to active. The time period can be modified no matter whether users are using the HWTACACS template.";
        }
        leaf shared-key {
          type pub-type:password-extend {
            length "1..432";
          }
          description
            "Shared key for a HWTACACS server, which is a string ranging from 1 to 255 characters for a unencrypted key and 20 to 432 characters for a encrypted key. Configuring a shared key improves the communication security between a router and HWTACACS server. By default, no shared key is configured.";
        }
        choice source-address {
          description
            "Source IP address of the packets sent to the server.";
          case ip {
            description
              "IP case.";
            leaf source-ip-address {
              type inet:ipv4-address;
              description
                "IP address.";
            }
          }
          case interface {
            description
              "Interface case.";
            leaf interface-name {
              type leafref {
                path "/ifm:ifm/ifm:interfaces/ifm:interface/ifm:name";
              }
              description
                "Interface name.";
            }
          }
        }
        choice source-ipv6-address {
          description
            "Source IPv6 address of the packets sent to the server.";
          case ip {
            description
              "Case IP.";
            leaf ipv6-address {
              type inet:ipv6-address;
              description
                "IPv6 address.";
            }
          }
          case interface {
            description
              "Case interface.";
            leaf ipv6-interface-name {
              type leafref {
                path "/ifm:ifm/ifm:interfaces/ifm:interface/ifm:name";
              }
              description
                "Interface name.";
            }
          }
        }
        leaf domain-mode {
          type hwtacacs-domain-include;
          default "domain-include";
          description
            "To configure domain Mode.";
        }
        leaf traffic-unit {
          type traffic-unit-type;
          description
            "Configure traffic unit.";
        }
        leaf encode-name-flag {
          type boolean;
          default "false";
          description
            "Enable/disable user-name is carried in authen-start message.";
        }
        container servers {
          description
            "List of HWTACACS servers.";
          list server {
            key "ip-address type ni-name";
            max-elements 32;
            description
              "Configure HWTACACS server.";
            leaf ip-address {
              type inet:ip-address;
              description
                "Server address. Must be a valid unicast IP address.";
            }
            leaf type {
              type hwtacacs-server-type;
              description
                "Server type.";
            }
            leaf ni-name {
              type leafref {
                path "/ni:network-instance/ni:instances/ni:instance/ni:name";
              }
              description
                "VPN instance name.";
            }
            leaf public-net {
              when "../ni-name = '_public_'";
              type boolean;
              mandatory true;
              description
                "Enable/disable the public-net. If public-net is false, server uses manage vpn.";
            }
            leaf priority {
              type priority-type;
              mandatory true;
              description
                "Set the server priority.";
            }
            leaf port {
              type inet:port-number {
                range "1..65535";
              }
              default "49";
              description
                "Server port.";
            }
            leaf is-mux-mode-enable {
              type boolean;
              default "false";
              description
                "Enable/disable the MUX mode for the server.";
            }
            leaf shared-key {
              type pub-type:password-extend {
                length "1..432";
              }
              description
                "Shared key for a HWTACACS server, which is a string ranging from 1 to 255 characters for a plaintext key and 20 to 432 characters for a ciphertext key. Configuring a shared key improves the communication security between a router and HWTACACS server. By default, no shared key is configured.";
            }
            container status {
              config false;
              description
                "Operational state of HWTACACS template.";
              leaf authen-open-num {
                type uint32;
                description
                  "Number of times that the HWTACACS client connected to the authentication server.";
              }
              leaf authen-close-num {
                type uint32;
                description
                  "Number of times that the HWTACACS client disconnected from the authentication server.";
              }
              leaf authen-req-num {
                type uint32;
                description
                  "Authentication request number.";
              }
              leaf authen-rsp-num {
                type uint32;
                description
                  "Authentication response number.";
              }
              leaf author-open-num {
                type uint32;
                description
                  "Number of times that the HWTACACS client connected to the authorization server.";
              }
              leaf author-close-num {
                type uint32;
                description
                  "Number of times that the HWTACACS client disconnected from the authorization server.";
              }
              leaf author-req-num {
                type uint32;
                description
                  "Authorization request number.";
              }
              leaf author-rsp-num {
                type uint32;
                description
                  "Authorization response number.";
              }
              leaf acct-req-num {
                type uint32;
                description
                  "Accounting request number.";
              }
              leaf acct-rsp-num {
                type uint32;
                description
                  "Accounting response number.";
              }
              leaf acct-server-open-num {
                type uint32;
                description
                  "Number of times that the HWTACACS client connected to the accounting server.";
              }
              leaf acct-close-num {
                type uint32;
                description
                  "Number of times that the HWTACACS client disconnected from the accounting server.";
              }
              leaf server-current-state {
                type hwtacacs-server-state;
                description
                  "Server running status.";
              }
              leaf is-current-server {
                type boolean;
                description
                  "Whether the server is being used.";
              }
            }
          }
        }
        container server-hosts {
          description
            "List of HWTACACS servers.";
          list server-host {
            key "type priority";
            description
              "Configure HWTACACS servers.";
            leaf type {
              type hwtacacs-server-type;
              description
                "Server type.";
            }
            leaf priority {
              type priority-type;
              description
                "Set the server priority.";
            }
            leaf is-mux-mode-enable {
              type boolean;
              default "false";
              description
                "Enable/disable the MUX mode for the server.";
            }
            leaf host-name {
              type string {
                length "1..255";
              }
              description
                "Set host name.";
            }
            leaf ip-address {
              type inet:ip-address;
              description
                "Server address. Must be a valid unicast IP address.";
            }
            leaf ipv6-address {
              type inet:ipv6-address-no-zone;
              description
                "Server IPv6 address. Must be a valid unicast IP address.";
            }
            leaf vpn-name {
              type leafref {
                path "/ni:network-instance/ni:instances/ni:instance/ni:name";
              }
              description
                "VPN instance name.";
            }
            leaf public-net {
              when "../vpn-name = '_public_'";
              type boolean;
              mandatory true;
              description
                "Enable/disable the public-net.";
            }
            leaf port {
              type inet:port-number {
                range "1..65535";
              }
              default "49";
              description
                "Server port.";
            }
            leaf shared-key {
              type pub-type:password-extend {
                length "1..428";
              }
              description
                "Shared key for a HWTACACS server, which is a string ranging from 1 to 255 characters for a plaintext key and 128 to 428 characters for a ciphertext key.";
            }
          }
        }
        container server-ipv6-hosts {
          description
            "List of HWTACACS servers.";
          list server-ipv6-host {
            key "type priority";
            description
              "Configure HWTACACS servers.";
            leaf type {
              type hwtacacs-server-type;
              description
                "Server type.";
            }
            leaf priority {
              type priority-type;
              description
                "Set the server priority.";
            }
            leaf is-mux-mode-enable {
              type boolean;
              default "false";
              description
                "Enable/disable the MUX mode for the server.";
            }
            leaf ip-address {
              type inet:ipv6-address-no-zone;
              description
                "Server address. Must be a valid unicast IPv6 address.";
            }
            leaf vpn-name {
              type leafref {
                path "/ni:network-instance/ni:instances/ni:instance/ni:name";
              }
              description
                "VPN instance name.";
            }
            leaf public-net {
              when "../vpn-name = '_public_'";
              type boolean;
              mandatory true;
              description
                "Enable/disable the public-net.";
            }
            leaf port {
              type inet:port-number {
                range "1..65535";
              }
              default "49";
              description
                "Server port.";
            }
            leaf shared-key {
              type pub-type:password-extend {
                length "1..428";
              }
              description
                "Shared key for a HWTACACS server, which is a string ranging from 1 to 255 characters for a plaintext key and 128 to 428 characters for a ciphertext key.";
            }
          }
        }
        container hwtacacs-servers {
          description
            "List of HWTACACS servers.";
          list hwtacacs-server {
            key "server-type ip-type";
            description
              "Configure HWTACACS servers.";
            leaf server-type {
              type server-priority-type;
              description
                "Server type.";
            }
            leaf ip-type {
              type ip-type;
              description
                "Set the server ip type.";
            }
            leaf ipv4-address {
              when "../ip-type='ipv4-flag'";
              type inet:ipv4-address;
              mandatory true;
              description
                "IPv4 server address. Must be a valid unicast IP address.";
            }
            leaf ipv6-address {
              when "../ip-type='ipv6-flag'";
              type inet:ipv6-address;
              mandatory true;
              description
                "IPv6 server address. Must be a valid unicast IP address.";
            }
            leaf vpn-name {
              type leafref {
                path "/ni:network-instance/ni:instances/ni:instance/ni:name";
              }
              description
                "VPN instance name.";
            }
            leaf public-net {
              when "../vpn-name = '_public_'";
              type boolean;
              mandatory true;
              description
                "Enable/disable the public-net.";
            }
            leaf port {
              type inet:port-number {
                range "1..65535";
              }
              default "49";
              description
                "Server port.";
            }
            leaf shared-key {
              type pub-type:password-extend {
                length "1..428";
              }
              description
                "Shared key for a HWTACACS server, which is a string ranging from 1 to 255 characters for a plaintext key and 128 to 428 characters for a ciphertext key.";
            }
          }
        }
        container ipv4-servers {
          description
            "List of HWTACACS servers.";
          list ipv4-server {
            key "server-ip-address server-type is-secondary-server vpn-name is-public-net";
            max-elements 32;
            description
              "Configure HWTACACS IPv4 server.";
            leaf server-ip-address {
              type inet:ipv4-address-no-zone;
              description
                "Server IPv4 address. Must be a valid unicast IP address.";
            }
            leaf server-type {
              type hwtacacs-server-type;
              description
                "Server type (authentication, authorization, accounting, common).";
            }
            leaf is-secondary-server {
              type boolean;
              description
                "Enable/disable the secondary server. By default, a server is a secondary server. A template does not support multiple primary servers of the same type.";
            }
            leaf vpn-name {
              type leafref {
                path "/ni:network-instance/ni:instances/ni:instance/ni:name";
              }
              must "not(../is-public-net='true') or (../is-public-net='true' and ../vpn-name='_public_')";
              description
                "VPN instance name. It must be an existing VPN instance.";
            }
            leaf is-public-net {
              type boolean;
              description
                "Enable/disable the public-net.";
            }
            leaf server-port {
              type uint32 {
                range "1..65535";
              }
              default "49";
              description
                "Server port.";
            }
            leaf is-mux-mode-enable {
              type boolean;
              default "false";
              description
                "Enable/disable the MUX mode for the server.";
            }
            leaf shared-key {
              type pub-type:password-extend {
                length "1..432";
              }
              description
                "Shared key for a HWTACACS server, which is a string ranging from 1 to 255 characters for a unencrypted key and 20 to 432 characters for a encrypted key. Configuring a shared key improves the communication security between a router and HWTACACS server. By default, no shared key is configured.";
            }
            leaf authen-server-open-num {
              type uint32;
              config false;
              description
                "Number of times that the HWTACACS client connected to the authentication server.";
            }
            leaf authen-server-close-num {
              type uint32;
              config false;
              description
                "Number of times that the HWTACACS client disconnected from the authentication server.";
            }
            leaf authen-req-num {
              type uint32;
              config false;
              description
                "Number of authentication requests.";
            }
            leaf authen-rsp-num {
              type uint32;
              config false;
              description
                "Number of authentication responses.";
            }
            leaf author-server-open-num {
              type uint32;
              config false;
              description
                "Number of times that the HWTACACS client connected to the authorization server.";
            }
            leaf author-server-close-num {
              type uint32;
              config false;
              description
                "Number of times that the HWTACACS client disconnected from the authorization server.";
            }
            leaf author-req-num {
              type uint32;
              config false;
              description
                "Number of authorization requests.";
            }
            leaf author-rsp-num {
              type uint32;
              config false;
              description
                "Number of authorization responses.";
            }
            leaf acct-req-num {
              type uint32;
              config false;
              description
                "Number of accounting requests.";
            }
            leaf acct-rsp-num {
              type uint32;
              config false;
              description
                "Number of accounting responses.";
            }
            leaf acct-server-open-num {
              type uint32;
              config false;
              description
                "Number of times that the HWTACACS client connected to the accounting server.";
            }
            leaf acct-server-close-num {
              type uint32;
              config false;
              description
                "Number of times that the HWTACACS client disconnected from the accounting server.";
            }
            leaf server-current-state {
              type hwtacacs-server-state;
              config false;
              description
                "Server running status.";
            }
            leaf is-current-server {
              type boolean;
              config false;
              description
                "Whether the server is being used.";
            }
          }
        }
        container ipv6-servers {
          description
            "List of HWTACACS servers.";
          list ipv6-server {
            key "server-ip-address server-type is-secondary-server vpn-name";
            max-elements 32;
            description
              "Configure HWTACACS IPv6 server.";
            leaf server-ip-address {
              type inet:ipv6-address-no-zone;
              description
                "Server IPv6 address. Must be a valid unicast IP address.";
            }
            leaf server-type {
              type hwtacacs-server-type;
              description
                "Server type (authentication, authorization, accounting, common).";
            }
            leaf is-secondary-server {
              type boolean;
              description
                "Enable/disable whether the server is secondary. By default, a server is a secondary server. A template does not support multiple primary servers of the same type.";
            }
            leaf vpn-name {
              type string {
                length "1..31";
              }
              description
                "Configure the vpn-instance name. It must be an existing VPN instance.";
            }
            leaf server-port {
              type uint32 {
                range "1..65535";
              }
              default "49";
              description
                "Server port.";
            }
            leaf is-mux-mode-enable {
              type boolean;
              default "false";
              description
                "Enable/disable the MUX mode for the server. By default, the MUX mode is disabled.";
            }
            leaf shared-key {
              type pub-type:password-extend {
                length "1..432";
              }
              description
                "Shared key for a HWTACACS server, which is a string ranging from 1 to 255 characters for a unencrypted key and 20 to 432 characters for a encrypted key. Configuring a shared key improves the communication security between a router and HWTACACS server. By default, no shared key is configured.";
            }
          }
        }
        container status {
          config false;
          description
            "Operational state of HWTACACS template.";
          leaf pri-authen-server {
            type string {
              length "1..255";
            }
            description
              "IP address of the primary authentication server.";
          }
          leaf pri-author-server {
            type string {
              length "1..255";
            }
            description
              "IP address of the primary authorization server.";
          }
          leaf pri-common-server {
            type string {
              length "1..255";
            }
            description
              "IP address of the primary common server.";
          }
          leaf cur-authen-server {
            type string {
              length "1..255";
            }
            description
              "IP address of the authentication server being used.";
          }
          leaf cur-author-server {
            type string {
              length "1..255";
            }
            description
              "IP address of authorization server being used.";
          }
          leaf sec-authen-server-num {
            type uint32;
            description
              "Total number of configured secondary authentication servers in the template.";
          }
          leaf sec-common-server-num {
            type uint32;
            description
              "Total number of configured secondary common servers in the template.";
          }
          leaf sec-author-server-num {
            type uint32;
            description
              "Total number of configured secondary authorization servers in the template.";
          }
          leaf pri-authen-port {
            type uint32;
            description
              "Port of the primary authentication server.";
          }
          leaf pri-common-port {
            type uint32;
            description
              "Port of the primary common server.";
          }
          leaf pri-author-port {
            type uint32;
            description
              "Port of the primary authorization server.";
          }
          leaf cur-authen-port {
            type uint32;
            description
              "Authentication server port being used.";
          }
          leaf cur-author-port {
            type uint32;
            description
              "Authorization server port being used.";
          }
          leaf authen-server-open-num {
            type uint32;
            description
              "Number of times that the HWTACACS client connected to the authentication server.";
          }
          leaf authen-server-close-num {
            type uint32;
            description
              "Number of times that the HWTACACS client disconnected from the authentication server.";
          }
          leaf authen-req-num {
            type uint32;
            description
              "Number of authentication requests.";
          }
          leaf authen-rsp-num {
            type uint32;
            description
              "Number of authentication responses.";
          }
          leaf authen-unknown-num {
            type uint32;
            description
              "Number of unknown authentication packets received by the HWTACACS client.";
          }
          leaf authen-timeout-num {
            type uint32;
            description
              "Number of times that authentication times out.";
          }
          leaf authen-pkt-drop-num {
            type uint32;
            description
              "Number of times that authentication packets are dropped.";
          }
          leaf authen-change-password-num {
            type uint32;
            description
              "Number of times that the password is changed for authentication.";
          }
          leaf authen-login-num {
            type uint32;
            description
              "Number of authentication logins.";
          }
          leaf authen-send-num {
            type uint32;
            description
              "Number of authentication requests sent to server.";
          }
          leaf authen-send-password-num {
            type uint32;
            description
              "Number of authentication password requests sent to the server.";
          }
          leaf authen-abort-num {
            type uint32;
            description
              "Number of authentication abort requests sent to server.";
          }
          leaf authen-connect-num {
            type uint32;
            description
              "Number of authentication connection requests sent to server.";
          }
          leaf authen-rsp-err-num {
            type uint32;
            description
              "Number of authentication error responses received from server.";
          }
          leaf authen-rsp-fail-num {
            type uint32;
            description
              "Number of authentication response failures received from server.";
          }
          leaf authen-follow-num {
            type uint32;
            description
              "Number of authentication Follow responses received from server.";
          }
          leaf authen-get-data-num {
            type uint32;
            description
              "Number of authentication date responses received from server.";
          }
          leaf authen-get-password-num {
            type uint32;
            description
              "Number of authentication password responses received from server.";
          }
          leaf authen-get-user-num {
            type uint32;
            description
              "Number of authentication user responses received from server.";
          }
          leaf authen-rsp-pass-num {
            type uint32;
            description
              "Number of authentication-pass responses received from server.";
          }
          leaf authen-restart-num {
            type uint32;
            description
              "Number of authentication-restart responses received from server.";
          }
          leaf authen-not-proc-req-num {
            type uint32;
            description
              "Number of authentication requests that are not processed.";
          }
          leaf authen-round-trip-time {
            type uint32;
            units "s";
            description
              "Time (in tick) taken to complete the authentication.";
          }
          leaf authen-malform-num {
            type uint32;
            description
              "Number of authentication errors.";
          }
          leaf author-server-open-num {
            type uint32;
            description
              "Number of times that the HWTACACS client connected to the authorization server.";
          }
          leaf author-server-close-num {
            type uint32;
            description
              "Number of times that the HWTACACS client disconnected from the authorization server.";
          }
          leaf author-req-num {
            type uint32;
            description
              "Number of authorization requests.";
          }
          leaf author-rsp-num {
            type uint32;
            description
              "Number of authorization responses.";
          }
          leaf author-unknown-num {
            type uint32;
            description
              "Number of unknown authorization packets received by HWTACACS client.";
          }
          leaf author-timeout-num {
            type uint32;
            description
              "Number of times that authorization times out.";
          }
          leaf author-pkt-drop-num {
            type uint32;
            description
              "Number of times that authorization packets are dropped.";
          }
          leaf author-exec-num {
            type uint32;
            description
              "Number of authorization requests for EXEC.";
          }
          leaf author-ppp-num {
            type uint32;
            description
              "Number of authorization requests for PPP.";
          }
          leaf author-vpdn-num {
            type uint32;
            description
              "Number of authorization requests for VPDN.";
          }
          leaf author-rsp-err-num {
            type uint32;
            description
              "Number of authorization error responses.";
          }
          leaf author-rsp-exec-num {
            type uint32;
            description
              "Number of authorization EXEC responses.";
          }
          leaf author-rsp-ppp-num {
            type uint32;
            description
              "Number of authorization PPP responses.";
          }
          leaf author-rsp-vpdn-num {
            type uint32;
            description
              "Number of authorization VPDN responses.";
          }
          leaf author-round-trip-time {
            type uint32;
            units "s";
            description
              "Time (in tick) taken to complete authorization.";
          }
          leaf author-not-proc-req-num {
            type uint32;
            description
              "Number of authorization requests that are not processed.";
          }
          leaf author-malform-num {
            type uint32;
            description
              "Number of authorization errors.";
          }
          leaf sec-account-server-num {
            type uint32;
            description
              "Number of secondary accounting servers in the template.";
          }
          leaf cur-account-port {
            type uint32;
            description
              "Accounting server port being used.";
          }
          leaf pri-account-port {
            type uint32;
            description
              "Port of the primary accounting server.";
          }
          leaf cur-account-server {
            type string {
              length "1..255";
            }
            description
              "Accounting server port being used.";
          }
          leaf pri-account-server {
            type string {
              length "1..255";
            }
            description
              "Primary accounting server.";
          }
          leaf acct-stop-pkt-num {
            type uint32;
            description
              "Number of responses to accounting-stop packets.";
          }
          leaf acct-rsp-pass-num {
            type uint32;
            description
              "Number of responses to accounting-pass packets.";
          }
          leaf acct-rsp-num {
            type uint32;
            description
              "Number of responses to accounting requests.";
          }
          leaf acct-server-open-num {
            type uint32;
            description
              "Number of times that the HWTACACS client connected to the accounting server.";
          }
          leaf acct-start-pkt-num {
            type uint32;
            description
              "Number of responses to accounting-start packets.";
          }
          leaf acct-req-num {
            type uint32;
            description
              "Number of accounting requests sent to the server.";
          }
          leaf acct-server-close-num {
            type uint32;
            description
              "Number of times that the HWTACACS client disconnected from the accounting server.";
          }
          leaf acct-rsp-err-num {
            type uint32;
            description
              "Number of abnormal accounting responses received from the server.";
          }
          leaf acct-follow-num {
            type uint32;
            description
              "Number of accounting Follow responses received from server.";
          }
          leaf acct-not-proc-req-num {
            type uint32;
            description
              "Number of accounting requests that are not processed.";
          }
        }
      }
    }
  }
  rpc hwtacacs-change-user-password {
    description
      "Change password function.";
    input  {
      leaf template-name {
        type string {
          length "1..32";
          pattern "[a-zA-Z0-9._-]+";
        }
        mandatory true;
        description
          "HWTACACS server template's name.";
      }
      leaf old-password {
        type pub-type:password-extend;
        mandatory true;
        description
          "The old password of the user.";
      }
      leaf new-password {
        type pub-type:password-extend;
        mandatory true;
        description
          "New password to set.";
      }
    }
  }
  ext:task-name "hwtacacs";
}
