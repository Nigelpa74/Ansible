/*
Copyright (C) 2019 Huawei Technologies Co., Ltd. All rights reserved.
*/
module huawei-cellular-notification-deviations-ar5710s {
  namespace "urn:huawei:yang:huawei-cellular-notification-deviations-ar5710s";
  prefix cellular-notification-devs-ar5710s;

  import huawei-cellular-notification {
    prefix cellular-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-cellular-notification module.";

  revision 2019-11-06 {
    description
      "Initial revision.";
    reference "Huawei private.";
  }

  deviation "/cellular-notification:modem-reboot" {
    deviate not-supported;
  }
  deviation "/cellular-notification:modem-reboot-completed" {
    deviate not-supported;
  }
  deviation "/cellular-notification:net-reject" {
    deviate not-supported;
  }
  deviation "/cellular-notification:net-reject-resume" {
    deviate not-supported;
  }
  deviation "/cellular-notification:service-emergency" {
    deviate not-supported;
  }
  deviation "/cellular-notification:service-emergency-resume" {
    deviate not-supported;
  }
  deviation "/cellular-notification:signal-weak" {
    deviate not-supported;
  }
  deviation "/cellular-notification:signal-weak-resume" {
    deviate not-supported;
  }
}
