/*
Copyright (C) 2020 Huawei Technologies Co., Ltd. All rights reserved.
*/
module huawei-nat-deviations-ar5710s {
  namespace "urn:huawei:yang:huawei-nat-deviations-ar5710s";
  prefix nat-devs-ar5710s;

  import huawei-ifm {
    prefix ifm;
  }
  import huawei-nat {
    prefix hw-nat;
  }

  organization
    "Huawei Technologies Co., Ltd.";
  contact
    "Huawei Industrial Base
     Bantian, Longgang
     Shenzhen 518129
     People's Republic of China
     Website: http://www.huawei.com
     Email: support@huawei.com";
  description
    "This module defines deviation statements for huawei-nat module.";

  revision 2020-12-30 {
    description
      "Initial revision.";
    reference "Huawei private.";
  }

  deviation "/ifm:ifm/ifm:interfaces/ifm:interface/hw-nat:nat/hw-nat:nat64-enable" {
    deviate not-supported;
  }
}
