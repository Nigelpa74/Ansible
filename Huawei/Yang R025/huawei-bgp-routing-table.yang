/*
Copyright (C) 2019-2025 Huawei Technologies Co., Ltd. All rights reserved.
*/
module huawei-bgp-routing-table {
  namespace "urn:huawei:yang:huawei-bgp-routing-table";
  prefix bgp-rt;
  import huawei-bgp {
    prefix bgp;
  }
  import huawei-extension {
    prefix ext;
  }
  import ietf-inet-types {
    prefix inet;
  }
  import huawei-pub-type {
    prefix pub-type;
  }
  import huawei-network-instance {
    prefix ni;
  }
  organization
    "Huawei Technologies Co., Ltd.";
  contact
    "Huawei Industrial Base
    Bantian, Longgang
    Shenzhen 518129
    People's Republic of China
    Website: http://www.huawei.com
    Email: support@huawei.com";
  description
    "Inter-AS routing protocol that exchanges Network Layer Reachability Information (NLRI) with other BGP systems.";
  revision 2025-02-13 {
    description
      "Add leaf service-sid-type.";
    reference "Huawei private.";
  }
  revision 2024-08-03 {
    description
      "Modify Xsec description.";
    reference "Huawei private.";
  }
  revision 2023-12-14 {
    description
      "Add default color.";
    reference "Huawei private.";
  }
  revision 2023-11-28 {
    description
      "Add the xsec node.";
    reference "Huawei private.";
  }
  revision 2023-06-02 {
    description
      "Modify the attribute node.";
    reference "Huawei private.";
  }
  revision 2023-03-22 {
    description
      "Modify routing table attribute behavior datatype from uint16 to character string (1..32).";
    reference "Huawei private.";
  }
  revision 2023-03-18 {
    description
      "Add path label.";
    reference "Huawei private.";
  }
  revision 2022-11-23 {
    description
      "Add routing table attribute behavior.";
    reference "Huawei private.";
  }
  revision 2022-02-23 {
    description
      "Add IPv4 labeled-unicast routing table and multi-instance IPv4 unicast routing table. Add l2vpn-ad routing table. Add mdt routing table.";
    reference "Huawei private.";
  }
  revision 2021-09-15 {
    description
      "The YANG descriptions are modified according to new standards.";
    reference "Huawei private.";
  }
  revision 2019-03-22 {
    description
      "Initial revision.";
    reference
      "Huawei private.";
  }
  ext:task-name  "bgp";
  
  typedef bgp-origin-type {
    type enumeration {
      enum "igp" {
        value 1;
        description
          "IBGP route.";
      }
      enum "egp" {
        value 2;
        description
          "EBGP route.";
      }
      enum "incomplete" {
        value 3;
        description
          "Route whose source is unknown.";
      }
    }
    description
      "The origin of bgpcommon.";
  }
  typedef flapping-af-type {
    type enumeration {
      enum "ipv4uni" {
        value 1;
        description
          "IPv4 unicast address family.";
      }
      enum "ipv4multi" {
        value 2;
        description
          "IPv4 multicast address family.";
      }
      enum "ipv4vpn" {
        value 3;
        description
          "IPv4 VPN address family.";
      }
      enum "ipv4labeluni" {
        value 4;
        description
          "IPv4 labeled address family.";
      }
      enum "ipv6uni" {
        value 5;
        description
          "IPv6 unicast address family.";
      }
      enum "ipv6vpn" {
        value 6;
        description
          "IPv6 VPN address family.";
      }
    }
    description
      "The address family type of flapping.";
  }
  typedef ifit-nhp-af-type {
    type enumeration {
      enum "ipv4vpn" {
        value 3;
        description
          "IPv4 VPN address family.";
      }
      enum "ipv6vpn" {
        value 6;
        description
          "IPv6 VPN address family.";
      }
      enum "evpn" {
        value 9;
        description
          "EVPN address family.";
      }
    }
    description
      "The address family type of ifit next hop address.";
  }
  typedef ifit-nhp-instance-af-type {
    type enumeration {
      enum "ipv4vpn" {
        value 3;
        description
          "IPv4 VPN address family.";
      }
    }
    description
      "The address family type of ifit next hop address.";
  }
  typedef bgp-external-flag-type {
    type bits {
      bit "type5-ip-prefix" {
        position 5;
        description
          "Ip prefix.";
      }
      bit "type2-irb" {
        position 13;
        description
          "IRB.";
      }
    }
    description
      "Route external flags.";
  }
  typedef hierarchy-convergence-type {
    type enumeration {
      enum "base" {
        value 1;
        description
          "Base route.";
      }
      enum "hierarchy" {
        value 2;
        description
          "Hierarchy route.";
      }
    }
    description
      "Hierarchy route flags.";
  }

  typedef bgp-route-type-flag {
    type bits {
      bit ibgp {
        description
          "IBGP route.";
      }
      bit ebgp {
        description
          "EBGP route.";
      }
      bit network {
        description
          "Network route.";
      }
      bit import {
        description
          "Imported route.";
      }
      bit auto-summary {
        description
          "Automatically summarized route.";
      }
      bit aggregate {
        description
          "Aggregated route.";
      }
      bit cpri {
        description
          "Route received by CBGP from PD-BGP.";
      }
      bit pcri {
        description
          "Route received by PD-BGP from CBGP.";
      }
      bit suppressed {
        description
          "Suppressed.";
      }
      bit nhp-empty {
        description
          "NHP-empty.";
      }
      bit no-adv {
        description
          "Routes that are not advertised to other routers.";
      }
      bit local-cross {
        description
          "Locally crossed routes.";
      }
      bit remote-cross {
        description
          "Remotely crossed routes.";
      }
      bit vd-bgp {
        description
          "VD-BGP route.";
      }
      bit path-local {
        description
          "Path_Local route.";
      }
      bit path-gateway {
        description
          "Path_Gateway route.";
      }
      bit policy-nopass {
        description
          "Policy_NoPass route.";
      }
      bit supprenet {
        description
          "Supernet route.";
      }
      bit dampened {
        description
          "Dampened route.";
      }
      bit history {
        description
          "History route.";
      }
      bit select {
        description
          "Selected route.";
      }
      bit best {
        description
          "Best route.";
      }
      bit backup {
        description
          "Backup route.";
      }
      bit attr-change {
        description
          "ATTR_Change route.";
      }
      bit nhlfe-created {
        description
          "NHLFE_Created route.";
      }
      bit ilm-created {
        description
          "ILM_Created route.";
      }
      bit nexthop-change {
        description
          "Route whose next hop changed.";
      }
      bit invalid {
        description
          "Invalid route.";
      }
      bit source-change {
        description
          "Route whose source address changed.";
      }
      bit in-selectedq {
        description
          "Route in a selected queue.";
      }
      bit exitif-error {
        description
          "EXITIF_ERROR route.";
      }
      bit group-head {
        description
          "GROUP_HEAD route.";
      }
    }
    description
      "BGP-route-type-flag.";
  }
  typedef region-validation-result-type {
    type enumeration {
      enum "valid" {
        value 1;
        description
          "The BGP region validation result is valid.";
      }
      enum "invalid" {
        value 2;
        description
          "The BGP region validation result is invalid.";
      }
    }
    description
      "The type of BGP region validation result.";
  }
  typedef l3esi {
    type string {
      length "1..24";
      pattern '(04(([0-9a-fA-F]){2}\.(([0-9a-fA-F]){4}\.){1}(([0-9a-fA-F]){2}00){1}\.0000\.0000))';
    }
    description
      "L3 Static ESI.";
  }
  typedef service-sid-type {
    type enumeration {
      enum "unicast" {
        value 0;
        description
          "Unicast service SID.";
      }
      enum "anycast" {
        value 2;
        description
          "Anycast service SID.";
      }
    }
    description
      "L3VPN service SID type.";
  }
  grouping xsec-information {
    description
      "BGP vpn-instance Xsec information.";
    leaf esi {
      type bgp-rt:l3esi;
      description
        "ESI.";
    }
    leaf xsec-encrypted {
      type boolean;
      description
        "Determines whether Xsec encryption is used.";
      ext:support-filter "true";
    }
    leaf xsec-router-id {
      type inet:ip-address-no-zone;
      description
        "Show Xsec router ID.";
    }
    leaf xsec-sa-id {
      type uint32;
      description
        "Show Xsec Sa ID.";
    }
  }
  grouping routing-table-vpn-name {
    description
      "BGP routing-table attributes.";
    leaf vpn-name {
      type leafref {
        path "/ni:network-instance/ni:instances/ni:instance/ni:name";
      }
      description
        "VPN name of a BGP instance.";
    }
  }
  grouping routing-table-peer-address {
    description
      "BGP neighbour address.";
    leaf remote-peer-address {
      type inet:ip-address-no-zone;
      description
        "BGP neighbour address.";
    }
  }
  grouping advertise-nexthop {
    description
      "Advertise nexthop.";
    leaf advertise-nexthop {
      type inet:ip-address-no-zone;
      description
        "Advertise nexthop.";
    }
  }
  grouping routing-table-prefix-base-peer {
    description
      "BGP routing-table attributes.";
    leaf nexthop {
      type inet:ip-address-no-zone;
      description
        "Next hop address to which packets are forwarded.";
    }
    leaf flag-string {
      type string {
        length "1..100";
      }
      description
        "Route flag that contains a string of characters.";
    }
    leaf time {
      type pub-type:time-tick;
      description
        "Time stamp of a route.";
    }
    leaf interface-name {
      type string {
        length "1..63";
      }
      description
        "Name of the outbound interface of a route.";
    }
    leaf remote-route-id {
      type inet:ipv4-address-no-zone;
      description
        "Router ID of a peer.";
    }
    leaf relay-nexthop {
      type inet:ip-address-no-zone;
      description
        "Next hop to which a route is iterated.";
    }
  }
  grouping routing-table-route-distinguisher {
    description
      "BGP routing-table attributes.";
    leaf route-distinguisher {
      type string {
        length "1..22";
      }
      description
        "Route distinguisher.";
    }
  }
  grouping routing-table-prefix {
    description
      "BGP routing-table attributes.";
    leaf prefix {
      type inet:ip-address-no-zone;
      description
        "BGP route prefix.";
    }
  }
  grouping routing-table-mask-length {
    description
      "BGP routing-table attributes.";
    leaf mask-length {
      type uint8;
      description
        "Prefix mask length.";
    }
  }
  grouping routing-table-route-type {
    description
      "BGP routing-table attributes.";
    leaf route-type {
      type bgp-rt:bgp-route-type-flag;
      description
        "Route type.";
    }
  }
  grouping routing-table-im-table-id {
    description
      "BGP routing-table attributes.";
    leaf im-table-id {
      type uint32;
      description
        "ID of the routing table to which routes are imported.";
    }
  }
  grouping routing-table-from {
    description
      "BGP routing-table attributes.";
    leaf from {
      type inet:ip-address-no-zone;
      description
        "Source peer that sends a route.";
    }
  }
  grouping routing-table-path-id {
    description
      "BGP routing-table attributes.";
    leaf path-id {
      type string {
        length "1..50";
      }
      description
        "Path ID.";
    }
  }
  grouping routing-table-key-type {
    description
      "BGP routing-table attributes.";
    uses routing-table-route-distinguisher;
    uses routing-table-prefix;
    uses routing-table-mask-length;
    uses routing-table-route-type;
    uses routing-table-im-table-id;
    uses routing-table-from;
    uses routing-table-path-id;
  }
  grouping routing-table-prefix-base-type {
    description
      "BGP routing-table attributes.";
    leaf nexthop {
      type inet:ip-address-no-zone;
      description
        "Next hop address to which packets are forwarded.";
    }
    leaf flag-string {
      type string {
        length "1..100";
      }
      description
        "Route flag that contains a string of characters.";
    }
    leaf worse-reason {
      type string {
        length "1..50";
      }
      description
        "Reason why a route is not selected.";
    }
    leaf time {
      type pub-type:time-tick;
      description
        "Time stamp of a route.";
    }
    leaf interface-name {
      type string {
        length "1..63";
      }
      description
        "Name of the outbound interface of a route.";
    }
    leaf remote-route-id {
      type inet:ipv4-address-no-zone;
      description
        "Router ID of a peer.";
    }
    leaf relay-nexthop {
      type inet:ip-address-no-zone;
      description
        "Next hop to which a route is iterated.";
    }
  }
  grouping routing-relay-tunnel-name {
    description
      "BGP routing-table attributes.";
    leaf relay-tunnel-name {
      type string {
        length "1..64";
      }
      description
        "Name of a tunnel to which a route is iterated.";
    }
  }
  grouping routing-relay-tunnel-name-ext {
    description
      "BGP routing-table attributes.";
    leaf relay-tunnel-name {
      type string {
        length "1..300";
      }
      description
        "Name of a tunnel to which a route is iterated.";
    }
  }
  grouping routing-table-prefix-base-attr-type {
    description
      "BGP routing-table attributes.";
    uses routing-table-prefix-base-type;
    uses routing-relay-tunnel-name;
  }
  grouping routing-table-prefix-base-attr-type-ext {
    description
      "BGP routing-table attributes.";
    uses routing-table-prefix-base-type;
    uses routing-relay-tunnel-name-ext;
  }
  grouping routing-table-label {
    description
      "BGP routing-table attributes.";
    leaf in-label {
      type uint32;
      description
        "In-label.";
    }
    leaf out-label {
      type uint32;
      description
        "Out-label.";
    }
  }
  grouping routing-table-iterated-vpn {
    description
      "BGP routing-table attributes.";
    leaf iterated-vpn {
      type string {
        length "1..31";
      }
      description
        "Iterated vrf.";
    }
  }
  grouping routing-table-external-flags {
    description
      "BGP routing-table attributes.";
    leaf external-flags {
      type bgp-rt:bgp-external-flag-type;
      description
        "Route External Flags.";
    }
  }
  grouping routing-table-prefix-type {
    description
      "BGP routing-table attributes.";
    uses routing-table-key-type;
    uses routing-table-prefix-base-attr-type-ext;
    uses routing-table-label;
    uses routing-table-iterated-vpn;
    uses routing-table-external-flags;
  }
  grouping routing-table-type {
    description
      "BGP routing-table attributes.";
    uses routing-table-prefix-type;
    leaf remote-nexthop-tunnel-address {
      type inet:ip-address-no-zone;
      description
        "The remote next hop tunnel address.";
    }
    leaf remote-nexthop-mac-address {
      type pub-type:mac-address;
      description
        "The remote next hop mac.";
    }
    leaf local-preference {
      type uint32;
      description
        "Local priority. The attribute is only fit for the routes from IBGP peer, not suit for which of EBGP peer.";
    }
    leaf preferred-value {
      type uint32;
      description
        "Preferred value of a protocol.";
    }
    leaf preference {
      type uint8;
      description
        "Priority of BGP routes.";
    }
    leaf path-as {
      type string {
        length "1..300";
      }
      description
        "List of the AS_Paths that packets pass through.";
    }
    leaf origin {
      type bgp-rt:bgp-origin-type;
      description
        "Route origin.";
    }
    leaf med {
      type uint32;
      description
        "Route MED.The attribute is only fit for the routes from EBGP peer, not suit for which of IBGP peer.";
    }
    leaf sending-peers {
      type string {
        length "1..300";
      }
      description
        "List of route sending peers.";
    }
    leaf community {
      type string {
        length "1..300";
      }
      description
        "Community attribute.";
    }
    leaf large-community {
      type string {
        length "1..200";
      }
      description
        "Large-community attribute information.";
    }
    leaf ext-community {
      type string {
        length "1..300";
      }
      description
        "Extended community attribute.";
    }
    leaf originator {
      type inet:ip-address-no-zone;
      description
        "Router ID of the route initiator.";
    }
    leaf cluster-list {
      type string {
        length "1..300";
      }
      description
        "List of cluster IDs.";
    }
    leaf atomic-aggregate {
      type boolean;
      description
        "Route carrying the atomic-aggregate attribute.";
    }
    leaf aggregator-as {
      type string {
        length "1..11";
      }
      description
        "AS number of the route summarizer.";
    }
    leaf aggregator-id {
      type inet:ip-address-no-zone;
      description
        "ID of the route summarizer.";
    }
    leaf remote-nexthop-vni {
      type uint32;
      description
        "The remote next hop vni.";
    }
    leaf advertise-nexthop {
      type inet:ip-address-no-zone;
      description
        "Advertise next hop.";
    }
    leaf aigp {
      type uint64;
      description
        "AIGP attribute information of route.";
    }
    leaf attribute-set {
      type string {
        length "1..300";
      }
      description
        "The attribute set information of route.";
    }
    leaf gateway-ip {
      type inet:ip-address-no-zone;
      description
        "Gateway IP address.";
    }
    leaf hierarchy-convergence-route-type {
      type bgp-rt:hierarchy-convergence-type;
      description
        "Hierarchy convergence route type.";
    }
    leaf hierarchy-route-relay-ip {
      when "../hierarchy-convergence-route-type='hierarchy'";
      type inet:ip-address-no-zone;
      description
        "BGP route prefix.";
    }
    leaf hierarchy-route-relay-ip-mask {
      when "../hierarchy-convergence-route-type='hierarchy'";
      type uint8;
      description
        "Prefix mask length.";
    }
  }
  grouping routing-table-attribute-deprecated-type {
    description
      "BGP routing-table attributes.";
    leaf prefix-sid {
      type string {
        length "1..60";
      }
      status deprecated;
      description
        "Prefix SID attribute information of route.";
    }
  }
  grouping routing-table-attribute-type {
    description
      "BGP routing-table attributes.";
    leaf prefix-sid {
      type string {
        length "1..60";
      }
      description
        "Prefix SID attribute information of route.";
    }
  }
  grouping loop-type {
    description
      "Information about loop.";
    leaf-list loop {
      type string {
        length "1..30";
      }
      max-elements 4;
      description
        "Statistics of loop attribute. Loop attribute is composed of paired vrfId and random.";
    }
  }
  grouping prefix-sid-type {
    description
      "Information about prefix SID.";
    container prefix-sids {
      description
        "List of prefix SID attribute.";
      list prefix-sid {
        key "sid";
        description
          "Operational data of prefix SID attribute.";
        leaf sid {
          type string {
            length "1..60";
          }
          description
            "Prefix SID attribute information of route.";
        }
        leaf structure {
          type string {
            length "1..36";
          }
          description
            "Sid-structure attribute information of route.";
        }
        leaf behavior {
          type string {
            length "1..32";
          }
          description
            "Endpoint behavior.";
        }
        leaf service-sid-type {
          type service-sid-type; 
          description
            "L3VPN service SID type.";
        }
      }
    }
  }
  grouping route-attribute-type {
    description
      "Information about routes attribute.";
    container attributes {
      description
        "List of attributes of BGP routes.";
      list attribute {
        key "vpn-name index";
        description
          "BGP routes attributes state.";
        uses routing-table-vpn-name;
        leaf index {
          type uint64;
          description
            "BGP route attribute id.";
        }
        uses loop-type;
        uses prefix-sid-type;
      }
    }
  }
  grouping routing-public-attributes {
    description
      "BGP routing-table attributes.";
    leaf preferred-value {
      type uint32;
      description
        "Preferred value of a protocol.";
    }
    leaf preference {
      type uint8;
      description
        "Priority of BGP routes.";
    }
  }
  grouping ipv4vpn-route-type {
    description
      "Information about routes.";
    container routes {
      config false;
      description
        "List of displayed route information in an address family.";
      list route {
        key "vpn-name route-distinguisher prefix mask-length route-type im-table-id from path-id";
        description
          "Statistics of routes.";
        uses routing-table-vpn-name;
        uses routing-table-type;
        uses routing-table-attribute-deprecated-type {
          refine prefix-sid {
            description
              "Prefix SID attribute information of route. The leaf prefix-sid is deprecated. The '/bgp:bgp/bgp:base-process/bgp-rt:bgp-route/bgp-rt:ipv4-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv4-vpn/bgp-rt:attributes/bgp-rt:attribute/bgp-rt:index";
          }
          description
            "The ID of attribute.";
        }
      }
    }
  }
  grouping ipv4vpn-peer-advertise-route-type {
    description
      "Information about advertised routes.";
    container peer-advertise-routes {
      config false;
      description
        "List of displayed advertised route information in an address family.";
      list peer-advertise-route {
        key "vpn-name remote-peer-address route-distinguisher prefix mask-length route-type im-table-id from path-id";
        description
          "Statistics of advertised routes.";
        uses routing-table-vpn-name;
        leaf remote-peer-address {
          type inet:ip-address-no-zone;
          description
            "BGP neighbour address.";
        }
        uses routing-table-type;
        uses routing-table-attribute-deprecated-type {
          refine prefix-sid {
            description
              "Prefix SID attribute information of route. The leaf prefix-sid is deprecated. The '/bgp:bgp/bgp:base-process/bgp-rt:bgp-route/bgp-rt:ipv4-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv4-vpn/bgp-rt:attributes/bgp-rt:attribute/bgp-rt:index";
          }
          description
            "The ID of attribute.";
        }
      }
    }
  }
  grouping ipv4vpn-peer-receive-route-type {
    description
      "Information about received routes.";
    container peer-receive-routes {
      config false;
      description
        "List of displayed received route information in an address family.";
      list peer-receive-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses routing-table-type;
        uses routing-table-attribute-deprecated-type {
          refine prefix-sid {
            description
              "Prefix SID attribute information of route. The leaf prefix-sid is deprecated. The '/bgp:bgp/bgp:base-process/bgp-rt:bgp-route/bgp-rt:ipv4-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv4-vpn/bgp-rt:attributes/bgp-rt:attribute/bgp-rt:index";
          }
          description
            "The ID of attribute.";
        }
      }
    }
  }

  grouping ifit-nexthops {
    description
      "Information about BGP address family next hop address.";
    container ifit-nexthops {
      config false;
      description
        "List of BGP address family next hop address.";
      list ifit-nexthop {
        key "address-family peer-route-nexthop";
        description
          "Operational data of BGP address family next hop address.";
        leaf address-family {
          type ifit-nhp-af-type;
          description
            "The address family type.";
        }
        leaf peer-route-nexthop {
          type inet:ip-address-no-zone;
          description
            "Original next hop address.";
        }
      }
    }
 }
  grouping instance-ifit-nexthops {
    description
      "Information about BGP address family next hop address.";
    container ifit-nexthops {
      config false;
      description
        "List of BGP address family next hop address.";
      list ifit-nexthop {
        key "address-family peer-route-nexthop";
        description
          "Operational data of BGP address family next hop address.";
        leaf address-family {
          type ifit-nhp-instance-af-type;
          description
            "The address family type.";
        }
        leaf peer-route-nexthop {
          type inet:ip-address-no-zone;
          description
            "Original next hop address.";
        }
      }
    }
 }
  grouping ipv6vpn-route-type {
    description
      "Information about routes.";
    container routes {
      config false;
      description
        "List of displayed route information in an address family.";
      list route {
        key "vpn-name route-distinguisher prefix mask-length route-type im-table-id from path-id";
        description
          "Statistics of routes.";
        uses routing-table-vpn-name;
        uses routing-table-type;
        uses routing-table-attribute-deprecated-type {
          refine prefix-sid {
            description
              "Prefix SID attribute information of route. The leaf prefix-sid is deprecated. The '/bgp:bgp/bgp:base-process/bgp-rt:bgp-route/bgp-rt:ipv6-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv6-vpn/bgp-rt:attributes/bgp-rt:attribute/bgp-rt:index";
          }
          description
            "The ID of attribute.";
        }
      }
    }
  }
  grouping ipv6vpn-peer-advertise-route-type {
    description
      "Information about advertised routes.";
    container peer-advertise-routes {
      config false;
      description
        "List of displayed advertised route information in an address family.";
      list peer-advertise-route {
        key "vpn-name remote-peer-address route-distinguisher prefix mask-length route-type im-table-id from path-id";
        description
          "Statistics of advertised routes.";
        uses routing-table-vpn-name;
        leaf remote-peer-address {
          type inet:ip-address-no-zone;
          description
            "BGP neighbour address.";
        }
        uses routing-table-type;
        uses routing-table-attribute-deprecated-type {
          refine prefix-sid {
            description
              "Prefix SID attribute information of route. The leaf prefix-sid is deprecated. The '/bgp:bgp/bgp:base-process/bgp-rt:bgp-route/bgp-rt:ipv6-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv6-vpn/bgp-rt:attributes/bgp-rt:attribute/bgp-rt:index";
          }
          description
            "The ID of attribute.";
        }
      }
    }
  }
  grouping ipv6vpn-peer-receive-route-type {
    description
      "Information about received routes.";
    container peer-receive-routes {
      config false;
      description
        "List of displayed received route information in an address family.";
      list peer-receive-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses routing-table-type;
        uses routing-table-attribute-deprecated-type {
          refine prefix-sid {
            description
              "Prefix SID attribute information of route. The leaf prefix-sid is deprecated. The '/bgp:bgp/bgp:base-process/bgp-rt:bgp-route/bgp-rt:ipv6-vpn/bgp-rt:attributes/bgp-rt:attribute/bgp-rt:prefix-sids/bgp-rt:prefix-sid/bgp-rt:sid' is recommended instead.";
          }
        }
        leaf attribute-index {
          type leafref {
            path "/bgp:bgp/bgp:base-process/bgp-rt:bgp-route/bgp-rt:ipv6-vpn/bgp-rt:attributes/bgp-rt:attribute/bgp-rt:index";
          }
          description
            "The ID of attribute.";
        }
      }
    }
  }
  
  
  grouping peer-receive-active-route-type {
    description
      "Information about received active routes.";
    container peer-receive-active-routes {
      config false;
      description
        "List of displayed received active route information in an address family.";
      list peer-receive-active-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses routing-table-type;
        uses routing-table-attribute-deprecated-type;
      }
    }
  }
  grouping ipv4uni-routing-table-type {
    description
      "BGP routing-table attributes in an address family.";
    uses routing-table-type;
    uses routing-table-attribute-deprecated-type {
      refine prefix-sid {
        description
          "Prefix SID attribute information of route. The leaf prefix-sid is deprecated. The '/bgp:bgp/bgp:base-process/bgp-rt:bgp-route/bgp-rt:ipv4-unicast/bgp-rt:attributes/bgp-rt:attribute/bgp-rt:prefix-sids/bgp-rt:prefix-sid/bgp-rt:sid' is recommended instead.";
      }
    }
    leaf entropy-label-padding {
      type string {
        length "1..50";
      }
      description
        "The padding value of the entropy label attribute.";
    }
    leaf region-validation-result {
      type bgp-rt:region-validation-result-type;
      description
        "BGP region validation result.";
    }
    leaf label-index {
      type uint32;
      description
        "Label index.";
    }
    leaf start-of-srgb {
      type uint32;
      description
        "Start of segment routing global block.";
    }
    leaf range-size-of-srgb {
      type uint32;
      description
        "Range size of segment routing global block.";
    }
  }
  grouping ipv4uni-route-type {
    description
      "Information about routes.";
    container routes {
      config false;
      description
        "List of displayed route information in an address family.";
      list route {
        key "vpn-name route-distinguisher prefix mask-length route-type im-table-id from path-id";
        description
          "Statistics of routes.";
        uses routing-table-vpn-name;
        uses ipv4uni-routing-table-type;
        uses xsec-information;
        leaf attribute-index {
          type leafref {
            path "/bgp:bgp/bgp:base-process/bgp-rt:bgp-route/bgp-rt:ipv4-unicast/bgp-rt:attributes/bgp-rt:attribute/bgp-rt:index";
          }
          description
            "The ID of attribute.";
        }
        leaf default-color {
          type uint32;
          description
            "Default color.";
        }
      }
    }
  }
  grouping multi-inst-ipv4uni-route-type {
    description
      "Information about routes.";
    container routes {
      config false;
      description
        "List of displayed route information in an address family.";
      list route {
        key "vpn-name route-distinguisher prefix mask-length route-type im-table-id from path-id";
        description
          "Operational data of route.";
        uses routing-table-vpn-name;
        uses routing-table-prefix-type;
      }
    }
  }
  grouping ipv4uni-peer-advertise-route-type {
    description
      "Information about advertised routes.";
    container peer-advertise-routes {
      config false;
      description
        "List of displayed advertised route information in an address family.";
      list peer-advertise-route {
        key "vpn-name remote-peer-address route-distinguisher prefix mask-length route-type im-table-id from path-id";
        description
          "Statistics of advertised routes.";
        uses routing-table-vpn-name;
        leaf remote-peer-address {
          type inet:ip-address-no-zone;
          description
            "BGP neighbour address.";
        }
        uses ipv4uni-routing-table-type;
        leaf attribute-index {
          type leafref {
            path "/bgp:bgp/bgp:base-process/bgp-rt:bgp-route/bgp-rt:ipv4-unicast/bgp-rt:attributes/bgp-rt:attribute/bgp-rt:index";
          }
          description
            "The ID of attribute.";
        }
      }
    }
  }
  grouping ipv4uni-peer-receive-route-type {
    description
      "Information about received routes.";
    container peer-receive-routes {
      config false;
      description
        "List of displayed received route information in an address family.";
      list peer-receive-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses ipv4uni-routing-table-type;
        leaf attribute-index {
          type leafref {
            path "/bgp:bgp/bgp:base-process/bgp-rt:bgp-route/bgp-rt:ipv4-unicast/bgp-rt:attributes/bgp-rt:attribute/bgp-rt:index";
          }
          description
            "The ID of attribute.";
        }
      }
    }
  }
  grouping ipv6uni-routing-table-type {
    description
      "BGP routing-table attributes in an address family.";
    uses routing-table-type;
    uses routing-table-attribute-deprecated-type {
      refine prefix-sid {
        description
          "Prefix SID attribute information of route. The leaf prefix-sid is deprecated. The '/bgp:bgp/bgp:base-process/bgp-rt:bgp-route/bgp-rt:ipv6-unicast/bgp-rt:attributes/bgp-rt:attribute/bgp-rt:prefix-sids/bgp-rt:prefix-sid/bgp-rt:sid' is recommended instead.";
      }
    }
    leaf region-validation-result {
      type bgp-rt:region-validation-result-type;
      description
        "BGP region validation result.";
    }
  }
  grouping ipv6uni-route-type {
    description
      "Information about routes.";
    container routes {
      config false;
      description
        "List of displayed route information in an address family.";
      list route {
        key "vpn-name route-distinguisher prefix mask-length route-type im-table-id from path-id";
        description
          "Statistics of routes.";
        uses routing-table-vpn-name;
        uses ipv6uni-routing-table-type;
        uses xsec-information;
        leaf attribute-index {
          type leafref {
            path "/bgp:bgp/bgp:base-process/bgp-rt:bgp-route/bgp-rt:ipv6-unicast/bgp-rt:attributes/bgp-rt:attribute/bgp-rt:index";
          }
          description
            "The ID of attribute.";
        }
        leaf default-color {
          type uint32;
          description
            "Default color.";
        }
      }
    }
  }
  grouping ipv6uni-peer-advertise-route-type {
    description
      "Information about advertised routes.";
    container peer-advertise-routes {
      config false;
      description
        "List of displayed advertised route information in an address family.";
      list peer-advertise-route {
        key "vpn-name remote-peer-address route-distinguisher prefix mask-length route-type im-table-id from path-id";
        description
          "Statistics of advertised routes.";
        uses routing-table-vpn-name;
        leaf remote-peer-address {
          type inet:ip-address-no-zone;
          description
            "BGP neighbour address.";
        }
        uses ipv6uni-routing-table-type;
        leaf attribute-index {
          type leafref {
            path "/bgp:bgp/bgp:base-process/bgp-rt:bgp-route/bgp-rt:ipv6-unicast/bgp-rt:attributes/bgp-rt:attribute/bgp-rt:index";
          }
          description
            "The ID of attribute.";
        }
      }
    }
  }
  grouping ipv6uni-peer-receive-route-type {
    description
      "Information about received routes.";
    container peer-receive-routes {
      config false;
      description
        "List of displayed received route information in an address family.";
      list peer-receive-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses ipv6uni-routing-table-type;
        leaf attribute-index {
          type leafref {
            path "/bgp:bgp/bgp:base-process/bgp-rt:bgp-route/bgp-rt:ipv6-unicast/bgp-rt:attributes/bgp-rt:attribute/bgp-rt:index";
          }
          description
            "The ID of attribute.";
        }
      }
    }
  }
  grouping ipv4-labeluni-route-type {
    description
      "Information about routes.";
    container routes {
      config false;
      description
        "List of displayed route information in an address family.";
      list route {
        key "vpn-name route-distinguisher prefix mask-length route-type im-table-id from path-id";
        description
          "Operational data of route.";
        uses routing-table-vpn-name;
        uses routing-table-prefix-type;
        uses routing-public-attributes;
        leaf attribute-index {
          type leafref {
            path "/bgp:bgp/bgp:base-process/bgp-rt:bgp-route/bgp-rt:ipv4-labeluni/bgp-rt:attributes/bgp-rt:attribute/bgp-rt:index";
          }
          description
            "The ID of attribute.";
        }
        leaf path-label {
          type uint32;
          description
            "Path-label.";
        }
      }
    }
  }
  grouping ipv4-labeluni-peer-advertise-route-type {
    description
      "Information about advertised routes.";
    container peer-advertise-routes {
      config false;
      description
        "List of displayed advertised route information in an address family.";
      list peer-advertise-route {
        key "vpn-name remote-peer-address route-distinguisher prefix mask-length route-type im-table-id from path-id";
        description
          "Statistics of advertised routes.";
        uses routing-table-vpn-name;
        leaf remote-peer-address {
          type inet:ip-address-no-zone;
          description
            "BGP neighbour address.";
        }
        uses routing-table-prefix-type;
        uses advertise-nexthop;
        uses routing-public-attributes;
        leaf attribute-index {
          type leafref {
            path "/bgp:bgp/bgp:base-process/bgp-rt:bgp-route/bgp-rt:ipv4-labeluni/bgp-rt:attributes/bgp-rt:attribute/bgp-rt:index";
          }
          description
            "The ID of attribute.";
        }
        leaf path-label {
          type uint32;
          description
            "Path-label.";
        }
      }
    }
  }
  grouping ipv4-labeluni-peer-receive-route-type {
    description
      "Information about received routes.";
    container peer-receive-routes {
      config false;
      description
        "List of displayed received route information in an address family.";
      list peer-receive-route {
        key "vpn-name remote-peer-address route-distinguisher prefix mask-length route-type im-table-id from path-id";
        description
          "Statistics of received routes.";
        uses routing-table-vpn-name;
        leaf remote-peer-address {
          type inet:ip-address-no-zone;
          description
            "BGP neighbour address.";
        }
        uses routing-table-prefix-type;
        uses routing-public-attributes;
        leaf attribute-index {
          type leafref {
            path "/bgp:bgp/bgp:base-process/bgp-rt:bgp-route/bgp-rt:ipv4-labeluni/bgp-rt:attributes/bgp-rt:attribute/bgp-rt:index";
          }
          description
            "The ID of attribute.";
        }
        leaf path-label {
          type uint32;
          description
            "Path-label.";
        }
      }
    }
  }
  grouping active-route-st-type {
    description
      "BGP active routes statistics information.";
    leaf advertise-rm-total-number {
      type uint32;
      description
        "Total number of prefix advertised to RM.";
    }
    leaf active-route-number {
      type uint32;
      description
        "Total number of active route.";
    }
  }
  grouping best-route-st-type {
    description
      "BGP active routes statistics information.";
    leaf best-route-number {
      type uint32;
      description
        "Total number of best routes.";
    }
    leaf add-path-route-number {
      type uint32;
      description
        "Total number of add-path routes.";
    }
    leaf best-external-route-number {
      type uint32;
      description
        "Total number of best-external routes.";
    }
  }
  grouping cidr-route-st-type {
    description
      "BGP classless inter-domain routes statistics information.";
    leaf cidr-route-number {
      type uint32;
      description
        "Total number of cidr routes.";
    }
  }
  grouping community-route-st-type {
    description
      "BGP routes matched with communities statistics information.";
    leaf community-route-number {
      type uint32;
      description
        "Total number of community routes.";
    }
  }
  grouping different-origin-as-route-st-type {
    description
      "Routes with the same destination address&mask but originating from different origin ASs statistics information.";
    leaf different-origin-as-route-number {
      type uint32;
      description
        "Total number of different-origin-as routes.";
    }
  }
  grouping dampened-route-st-type {
    description
      "Routes with the same destination address&mask but originating from different origin ASs statistics information.";
    leaf dampened-route-number {
      type uint32;
      description
        "Total number of dampened routes.";
    }
  }
  grouping route-total-st-type {
    description
      "Labeled route statistics information.";
    leaf total-number {
      type uint32;
      description
        "Total number of routes.";
    }
  }
  grouping active-rt-num-type {
    description
      "BGP active routes statistics information.";
    leaf active-route-number {
      type uint32;
      description
        "Total number of active route.";
    }
  }
  grouping route-flap-type {
    description
      "Information about BGP route flapping.";
    container routing-flappings {
      config false;
      description
        "List of displayed BGP route flapping information.";
      list routing-flapping {
        key "vpn-name address-family prefix mask-length";
        description
          "Statistics of BGP route flapping.";
        uses routing-table-vpn-name;
        leaf address-family {
          type flapping-af-type;
          description
            "The address family type.";
        }
        leaf prefix {
          type inet:ip-address-no-zone;
          description
            "The network address in the BGP routing table.";
        }
        leaf mask-length {
          type uint8;
          description
            "Prefix mask length.";
        }
        leaf from {
          type inet:ip-address-no-zone;
          description
            "IP address of the neighbor that receives routes.";
        }
        leaf origin {
          type bgp-origin-type;
          description
            "The attributes of Origin.";
        }
        leaf flaps {
          type uint16 {
            range "0..65535";
          }
          description
            "Total number of route flapping.";
        }
        leaf reuse-time {
          type pub-type:time-tick;
          description
            "Reuse value.";
        }
        leaf duration-time {
          type pub-type:time-tick;
          description
            "Total duration since the flapping happens.";
        }
      }
    }
  }

  grouping ipv4multi-route-type {
    description
      "Information about routes.";
    container routes {
      config false;
      description
        "List of displayed route information in an address family.";
      list route {
        key "vpn-name route-distinguisher prefix mask-length route-type im-table-id from path-id";
        description
          "Statistics of routes.";
        uses routing-table-vpn-name;
        uses routing-table-type;
        uses routing-table-attribute-type;
        leaf attribute-index {
          type leafref {
            path "/bgp:bgp/bgp:base-process/bgp-rt:bgp-route/bgp-rt:ipv4-multicast/bgp-rt:attributes/bgp-rt:attribute/bgp-rt:index";
          }
          description
            "The ID of attribute.";
        }
      }
    }
    container peer-advertise-routes {
      description
        "List of displayed advertised route information in an address family.";
      list peer-advertise-route {
        key "vpn-name remote-peer-address route-distinguisher prefix mask-length route-type im-table-id from path-id";
        description
          "Statistics of advertised routes.";
        uses routing-table-vpn-name;
        uses routing-table-peer-address;
        uses routing-table-key-type;
        uses routing-table-prefix-base-peer;
        uses advertise-nexthop;
        uses routing-public-attributes;
        leaf attribute-index {
          type leafref {
            path "/bgp:bgp/bgp:base-process/bgp-rt:bgp-route/bgp-rt:ipv4-multicast/bgp-rt:attributes/bgp-rt:attribute/bgp-rt:index";
          }
          description
            "The ID of attribute.";
        }
      }
    }
    container peer-receive-routes {
      description
        "List of displayed received route information in an address family.";
      list peer-receive-route {
        key "vpn-name remote-peer-address route-distinguisher prefix mask-length route-type im-table-id from path-id";
        description
          "Statistics of received routes.";
        uses routing-table-vpn-name;
        uses routing-table-peer-address;
        uses routing-table-key-type;
        uses routing-table-prefix-base-type;
        uses routing-public-attributes;
        leaf attribute-index {
          type leafref {
            path "/bgp:bgp/bgp:base-process/bgp-rt:bgp-route/bgp-rt:ipv4-multicast/bgp-rt:attributes/bgp-rt:attribute/bgp-rt:index";
          }
          description
            "The ID of attribute.";
        }
      }
    }
  }
  grouping ipv4multi-st-type {
    description
      "Statistics of IPv4-multicast address family.";
    container statistic {
      description
        "Statistics of BGP routes information of IPv4-multicast address family.";
      uses route-total-st-type;
      uses active-route-st-type;
      uses dampened-route-st-type;
    }
  }
  grouping route-attribute-info {
    description
      "Configure address family common options.";
      container attributes {
        description
          "List of attributes of BGP routes.";
        list attribute {
          key "vpn-name index";
          description
            "BGP routes attributes state.";
          uses routing-table-vpn-name;
          leaf index {
            type uint32;
            description
              "BGP route attribute id.";
          }
          leaf origin {
            type bgp-rt:bgp-origin-type;
            description
              "The attributes of Origin.";
          }
          leaf med {
            type uint32;
            description
              "Route MED.The attribute is only fit for the routes from EBGP peer, not suit for which of IBGP peer.";
          }
          leaf local-preference {
            type uint32;
            description
              "Local priority. The attribute is only fit for the routes from IBGP peer, not suit for which of EBGP peer.";
          }
          leaf aggregator-as {
            type string {
              length "1..11";
            }
            description
              "AS number of the route summarizer.";
          }
          leaf aggregator-id {
            type inet:ip-address-no-zone;
            description
              "ID of the route summarizer.";
          }
          leaf originator {
            type inet:ip-address-no-zone;
            description
              "Router ID of the route initiator.";
          }
        }
      }
    }
  grouping route-attribute-info-ext {
    description
      "Configure address family common options.";
      container attributes {
        description
          "List of attributes of BGP routes.";
        list attribute {
          key "vpn-name index";
          description
            "BGP routes attributes state.";
          uses routing-table-vpn-name;
          leaf index {
            type uint32;
            description
              "BGP route attribute id.";
          }
          leaf origin {
            type bgp-rt:bgp-origin-type;
            description
              "The attributes of Origin.";
          }
          leaf med {
            type uint32;
            description
              "Route MED.The attribute is only fit for the routes from EBGP peer, not suit for which of IBGP peer.";
          }
          leaf local-preference {
            type uint32;
            description
              "Local priority. The attribute is only fit for the routes from IBGP peer, not suit for which of EBGP peer.";
          }
          leaf originator {
            type inet:ip-address-no-zone;
            description
              "Router ID of the route initiator.";
          }
        }
      }
    }
  grouping xsec-type {
    description
      "BGP Xsec information.";
    leaf esi {
      type bgp-rt:l3esi;
      description
        "ESI.";
    }
    leaf sa-id {
      type uint32;
      description
        "Sa ID.";
    }
    leaf router-id {
      type inet:ipv4-address-no-zone;
      description
        "Router ID.";
    }
    leaf nexthop {
      type inet:ip-address-no-zone;
      description
        "Next hop address.";
    }
  }
  augment /bgp:bgp/bgp:base-process {
    description
      "Top level container for BGP routes information.";
    container bgp-route {
      config false;
      description
        "Statistics of BGP routes information.";
      container ipv4-unicast {
        config false;
        description
          "Statistics of BGP routes information of IPv4-unicast address family.";
        uses ipv4uni-route-type;
        uses ipv4uni-peer-advertise-route-type;
        uses ipv4uni-peer-receive-route-type;
        uses peer-receive-active-route-type {
          refine peer-receive-active-routes/peer-receive-active-route/prefix-sid {
            description
              "Prefix SID attribute information of route. The leaf prefix-sid is deprecated. The '/bgp:bgp/bgp:base-process/bgp-rt:bgp-route/bgp-rt:ipv4-unicast/bgp-rt:attributes/bgp-rt:attribute/bgp-rt:prefix-sids/bgp-rt:prefix-sid/bgp-rt:sid' is recommended instead.";
          }
        }
        uses route-attribute-type;
        container statistics {
          description
            "List of BGP routes statistics information of IPv4-unicast address family.";
          list statistic {
            key "vpn-name";
            description
              "BGP IPv4-unicast address family routes statistics.";
            uses routing-table-vpn-name;
            uses route-total-st-type;
            uses active-route-st-type;
            uses best-route-st-type;
            uses cidr-route-st-type;
            uses community-route-st-type;
            uses different-origin-as-route-st-type;
            uses dampened-route-st-type;
          }
        }
        container xsecs {
          description
            "List of Xsec.";
          list xsec {
            key "vpn-name esi sa-id router-id nexthop";
            description
              "Statistics of BGP IPv4-unicast address family Xsec.";
            uses routing-table-vpn-name;
            uses xsec-type;
          }
        }
      }
      container ipv6-unicast {
        config false;
        description
          "Statistics of BGP routes information of IPv6-unicast address family.";
        uses ipv6uni-route-type;
        uses ipv6uni-peer-advertise-route-type;
        uses ipv6uni-peer-receive-route-type;
        uses peer-receive-active-route-type {
          refine peer-receive-active-routes/peer-receive-active-route/prefix-sid {
            description
              "Prefix SID attribute information of route. The leaf prefix-sid is deprecated. The '/bgp:bgp/bgp:base-process/bgp-rt:bgp-route/bgp-rt:ipv6-unicast/bgp-rt:attributes/bgp-rt:attribute/bgp-rt:prefix-sids/bgp-rt:prefix-sid/bgp-rt:sid' is recommended instead.";
          }
        }
        uses route-attribute-type;
        container statistics {
          description
            "List of BGP routes statistics information of IPv6-unicast address family.";
          list statistic {
            key "vpn-name";
            description
              "BGP IPv6-unicast address family routes statistics.";
            uses routing-table-vpn-name;
            uses route-total-st-type;
            uses active-route-st-type;
            uses best-route-st-type;
            uses community-route-st-type;
            uses dampened-route-st-type;
          }
        }
        container xsecs {
          description
            "List of Xsec.";
          list xsec {
            key "vpn-name esi sa-id router-id nexthop";
            description
              "Statistics of BGP IPv6-unicast address family Xsec.";
            uses routing-table-vpn-name;
            uses xsec-type;
          }
        }
      }
      container ipv4-vpn {
        config false;
        description
          "Statistics of BGP routes information of IPv4-VPN address family.";
        uses ipv4vpn-route-type;
        uses ipv4vpn-peer-advertise-route-type;
        uses ipv4vpn-peer-receive-route-type;
        uses peer-receive-active-route-type {
          refine peer-receive-active-routes/peer-receive-active-route/prefix-sid {
            description
              "Prefix SID attribute information of route. The leaf prefix-sid is deprecated. The '/bgp:bgp/bgp:base-process/bgp-rt:bgp-route/bgp-rt:ipv4-vpn/bgp-rt:attributes/bgp-rt:attribute/bgp-rt:prefix-sids/bgp-rt:prefix-sid/bgp-rt:sid' is recommended instead.";
          }
        }
        uses route-attribute-type;
        container statistic {
          description
            "Statistics of BGP routes information of IPv4-VPN address family.";
          uses route-total-st-type;
          uses active-rt-num-type;
          uses best-route-st-type;
          uses cidr-route-st-type;
          uses community-route-st-type;
          uses different-origin-as-route-st-type;
          uses dampened-route-st-type;
        }
      }
      container ipv6-vpn {
        config false;
        description
          "Statistics of BGP routes information of IPv6-VPN address family.";
        uses ipv6vpn-route-type;
        uses ipv6vpn-peer-advertise-route-type;
        uses ipv6vpn-peer-receive-route-type;
        uses peer-receive-active-route-type {
          refine peer-receive-active-routes/peer-receive-active-route/prefix-sid {
            description
              "Prefix SID attribute information of route. The leaf prefix-sid is deprecated. The '/bgp:bgp/bgp:base-process/bgp-rt:bgp-route/bgp-rt:ipv6-vpn/bgp-rt:attributes/bgp-rt:attribute/bgp-rt:prefix-sids/bgp-rt:prefix-sid/bgp-rt:sid' is recommended instead.";
          }
        }
        uses route-attribute-type;
        container statistic {
          description
            "Statistics of BGP routes information of IPv6-VPN address family.";
          uses route-total-st-type;
          uses active-rt-num-type;
          uses best-route-st-type;
          uses community-route-st-type;
          uses different-origin-as-route-st-type;
        }
      }
      container ipv4-labeluni {
        config false;
        description
          "Operational data of BGP routes of IPv4-label-uni address family.";
        uses ipv4-labeluni-route-type;
        uses ipv4-labeluni-peer-advertise-route-type;
        uses ipv4-labeluni-peer-receive-route-type;
        uses route-attribute-info-ext;
        container statistics {
          description
            "List of BGP routes statistics information of IPv4-label-uni address family.";
          list statistic {
            key "vpn-name";
            description
              "BGP IPv4-label-uni address family routes statistics.";
            uses routing-table-vpn-name;
            uses route-total-st-type;
            uses active-route-st-type;
            uses best-route-st-type;
            uses cidr-route-st-type;
            uses community-route-st-type;
            uses different-origin-as-route-st-type;
            uses dampened-route-st-type;
          }
        }
      }
      container ipv4-multicast {
        config false;
        description
          "Statistics of BGP routes information of IPv4-multicast address family.";
        uses ipv4multi-route-type;
        uses route-attribute-info;
        uses ipv4multi-st-type;
      }
      uses route-flap-type;
      uses ifit-nexthops;
    }
  }
  augment /bgp:bgp/bgp:instance-processs/bgp:instance-process {
    description
      "Top level container for BGP routes information.";
    container bgp-route {
      config false;
      description
        "Statistics of BGP routes information.";
      container ipv4-unicast {
        config false;
        description
          "Statistics of BGP routes information of IPv4-unicast address family.";
        uses multi-inst-ipv4uni-route-type;
      }
      uses instance-ifit-nexthops;
    }
  }
}
